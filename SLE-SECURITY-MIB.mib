--
-- SLE-SECURITY-MIB.my
-- MIB generated by MG-SOFT Visual MIB Builder Version 6.0  Build 88
-- Thursday, January 29, 2009 at 18:58:59
--

	SLE-SECURITY-MIB DEFINITIONS ::= BEGIN
 
		IMPORTS
			sleMgmt			
				FROM DASAN-SMI			
			InterfaceIndex			
				FROM IF-MIB			
			SleControlStatusType, SleControlRequestResultType			
				FROM SLE-TC-MIB			
			OBJECT-GROUP, NOTIFICATION-GROUP			
				FROM SNMPv2-CONF			
			TimeTicks, IpAddress, Integer32, Unsigned32, Gauge32, 
			Counter32, BITS, OBJECT-TYPE, MODULE-IDENTITY, NOTIFICATION-TYPE			
				FROM SNMPv2-SMI			
			DateAndTime, TimeStamp, MacAddress			
				FROM SNMPv2-TC;
	
	
		-- 1.3.6.1.4.1.6296.101.7
		sleSecurity MODULE-IDENTITY 
			LAST-UPDATED "200412100929Z"		-- December 10, 2004 at 09:29 GMT
			ORGANIZATION 
				"Organization."
			CONTACT-INFO 
				"Contact-info."
			DESCRIPTION 
				"Description."
			::= { sleMgmt 7 }

		
	
	
--
-- Node definitions
--
	
		-- 1.3.6.1.4.1.6296.101.7.1
		sleSecurityBase OBJECT IDENTIFIER ::= { sleSecurity 1 }

		
		-- 1.3.6.1.4.1.6296.101.7.1.1
		sleSecurityBaseInfo OBJECT IDENTIFIER ::= { sleSecurityBase 1 }

		
		-- 1.3.6.1.4.1.6296.101.7.1.1.1
		sleSecurityRadiusRetransmissions OBJECT-TYPE
			SYNTAX Integer32
			MAX-ACCESS read-only
			STATUS current
			DESCRIPTION
				"Description"
			::= { sleSecurityBaseInfo 1 }

		
		-- 1.3.6.1.4.1.6296.101.7.1.1.2
		sleSecurityRadiusTimeouts OBJECT-TYPE
			SYNTAX Integer32
			MAX-ACCESS read-only
			STATUS current
			DESCRIPTION
				"Description"
			::= { sleSecurityBaseInfo 2 }

		
		-- 1.3.6.1.4.1.6296.101.7.1.1.3
		sleSecurityRadiusInterfaceName OBJECT-TYPE
			SYNTAX OCTET STRING (SIZE (0..255))
			MAX-ACCESS read-only
			STATUS current
			DESCRIPTION
				"Description"
			::= { sleSecurityBaseInfo 3 }

		
		-- 1.3.6.1.4.1.6296.101.7.1.1.4
		sleSecurityRadiusInterfaceAddress OBJECT-TYPE
			SYNTAX IpAddress
			MAX-ACCESS read-only
			STATUS current
			DESCRIPTION
				"Description"
			::= { sleSecurityBaseInfo 4 }

		
		-- 1.3.6.1.4.1.6296.101.7.1.1.5
		sleSecurityTacacsInterfaceName OBJECT-TYPE
			SYNTAX OCTET STRING (SIZE (0..255))
			MAX-ACCESS read-only
			STATUS current
			DESCRIPTION
				"Description"
			::= { sleSecurityBaseInfo 5 }

		
		-- 1.3.6.1.4.1.6296.101.7.1.1.6
		sleSecurityTacacsInterfaceAddress OBJECT-TYPE
			SYNTAX IpAddress
			MAX-ACCESS read-only
			STATUS current
			DESCRIPTION
				"Description"
			::= { sleSecurityBaseInfo 6 }

		
		-- 1.3.6.1.4.1.6296.101.7.1.1.7
		sleSecurityTacacsPort OBJECT-TYPE
			SYNTAX Integer32 (0..65535)
			MAX-ACCESS read-only
			STATUS current
			DESCRIPTION
				"Description"
			::= { sleSecurityBaseInfo 7 }

		
		-- 1.3.6.1.4.1.6296.101.7.1.1.8
		sleSecurityTacacsAuthType OBJECT-TYPE
			SYNTAX INTEGER
				{
				ascii(0),
				pap(1),
				chap(2)
				}
			MAX-ACCESS read-only
			STATUS current
			DESCRIPTION
				"Description"
			DEFVAL { ascii }
			::= { sleSecurityBaseInfo 8 }

		
		-- 1.3.6.1.4.1.6296.101.7.1.1.9
		sleSecurityTacacsTimeouts OBJECT-TYPE
			SYNTAX Integer32
			MAX-ACCESS read-only
			STATUS current
			DESCRIPTION
				"Description"
			::= { sleSecurityBaseInfo 9 }

		
		-- 1.3.6.1.4.1.6296.101.7.1.1.10
		sleSecurityTacacsPriorityLevel OBJECT-TYPE
			SYNTAX INTEGER
				{
				max(0),
				min(1),
				root(2),
				user(3)
				}
			MAX-ACCESS read-only
			STATUS current
			DESCRIPTION
				"Description"
			DEFVAL { min }
			::= { sleSecurityBaseInfo 10 }

		
		-- 1.3.6.1.4.1.6296.101.7.1.1.11
		sleSecurityDot1xActivity OBJECT-TYPE
			SYNTAX INTEGER
				{
				disable(0),
				enable(1)
				}
			MAX-ACCESS read-only
			STATUS current
			DESCRIPTION
				"Description"
			::= { sleSecurityBaseInfo 11 }

		
		-- 1.3.6.1.4.1.6296.101.7.1.2
		sleSecurityBaseControl OBJECT IDENTIFIER ::= { sleSecurityBase 2 }

		
		-- 1.3.6.1.4.1.6296.101.7.1.2.1
		sleSecurityControlRequest OBJECT-TYPE
			SYNTAX INTEGER
				{
				setSecurityBaseRadiusProfile(1),
				setSecurityBaseTacacsProfile(2),
				setSecurityBaseDot1xActivity(3)
				}
			MAX-ACCESS read-write
			STATUS current
			DESCRIPTION
				"Description"
			::= { sleSecurityBaseControl 1 }

		
		-- 1.3.6.1.4.1.6296.101.7.1.2.2
		sleSecurityControlStatus OBJECT-TYPE
			SYNTAX SleControlStatusType
			MAX-ACCESS read-only
			STATUS current
			DESCRIPTION
				"Description"
			::= { sleSecurityBaseControl 2 }

		
		-- 1.3.6.1.4.1.6296.101.7.1.2.3
		sleSecurityControlTimer OBJECT-TYPE
			SYNTAX Gauge32
			MAX-ACCESS read-write
			STATUS current
			DESCRIPTION
				"Description"
			::= { sleSecurityBaseControl 3 }

		
		-- 1.3.6.1.4.1.6296.101.7.1.2.4
		sleSecurityControlTimeStamp OBJECT-TYPE
			SYNTAX TimeStamp
			MAX-ACCESS read-only
			STATUS current
			DESCRIPTION
				"Description"
			::= { sleSecurityBaseControl 4 }

		
		-- 1.3.6.1.4.1.6296.101.7.1.2.5
		sleSecurityControlReqResult OBJECT-TYPE
			SYNTAX SleControlRequestResultType
			MAX-ACCESS read-only
			STATUS current
			DESCRIPTION
				"Description"
			::= { sleSecurityBaseControl 5 }

		
		-- 1.3.6.1.4.1.6296.101.7.1.2.6
		sleSecurityControlRadiusRetransmissions OBJECT-TYPE
			SYNTAX Integer32
			MAX-ACCESS read-write
			STATUS current
			DESCRIPTION
				"Description"
			::= { sleSecurityBaseControl 6 }

		
		-- 1.3.6.1.4.1.6296.101.7.1.2.7
		sleSecurityControlRadiusTimeouts OBJECT-TYPE
			SYNTAX Integer32
			MAX-ACCESS read-write
			STATUS current
			DESCRIPTION
				"Description"
			::= { sleSecurityBaseControl 7 }

		
		-- 1.3.6.1.4.1.6296.101.7.1.2.8
		sleSecurityControlRadiusInterfaceName OBJECT-TYPE
			SYNTAX OCTET STRING (SIZE (0..255))
			MAX-ACCESS read-write
			STATUS current
			DESCRIPTION
				"Description"
			::= { sleSecurityBaseControl 8 }

		
		-- 1.3.6.1.4.1.6296.101.7.1.2.9
		sleSecurityControlRadiusInterfaceAddress OBJECT-TYPE
			SYNTAX IpAddress
			MAX-ACCESS read-write
			STATUS current
			DESCRIPTION
				"Description"
			::= { sleSecurityBaseControl 9 }

		
		-- 1.3.6.1.4.1.6296.101.7.1.2.10
		sleSecurityControlTacacsInterfaceName OBJECT-TYPE
			SYNTAX OCTET STRING (SIZE (0..255))
			MAX-ACCESS read-write
			STATUS current
			DESCRIPTION
				"Description"
			::= { sleSecurityBaseControl 10 }

		
		-- 1.3.6.1.4.1.6296.101.7.1.2.11
		sleSecurityControlTacacsInterfaceAddress OBJECT-TYPE
			SYNTAX IpAddress
			MAX-ACCESS read-write
			STATUS current
			DESCRIPTION
				"Description"
			::= { sleSecurityBaseControl 11 }

		
		-- 1.3.6.1.4.1.6296.101.7.1.2.12
		sleSecurityControlTacacsPort OBJECT-TYPE
			SYNTAX Integer32 (0..65535)
			MAX-ACCESS read-write
			STATUS current
			DESCRIPTION
				"Description"
			::= { sleSecurityBaseControl 12 }

		
		-- 1.3.6.1.4.1.6296.101.7.1.2.13
		sleSecurityControlTacacsAuthType OBJECT-TYPE
			SYNTAX INTEGER
				{
				ascii(0),
				pap(1),
				chap(2)
				}
			MAX-ACCESS read-write
			STATUS current
			DESCRIPTION
				"Description"
			DEFVAL { ascii }
			::= { sleSecurityBaseControl 13 }

		
		-- 1.3.6.1.4.1.6296.101.7.1.2.14
		sleSecurityControlTacacsTimeouts OBJECT-TYPE
			SYNTAX Integer32
			MAX-ACCESS read-write
			STATUS current
			DESCRIPTION
				"Description"
			::= { sleSecurityBaseControl 14 }

		
		-- 1.3.6.1.4.1.6296.101.7.1.2.15
		sleSecurityControlTacacsPriorityLevel OBJECT-TYPE
			SYNTAX INTEGER
				{
				max(0),
				min(1),
				root(2),
				user(3)
				}
			MAX-ACCESS read-write
			STATUS current
			DESCRIPTION
				"Description"
			DEFVAL { min }
			::= { sleSecurityBaseControl 15 }

		
		-- 1.3.6.1.4.1.6296.101.7.1.2.16
		sleSecurityControlDot1xActivity OBJECT-TYPE
			SYNTAX INTEGER
				{
				disable(0),
				enable(1)
				}
			MAX-ACCESS read-write
			STATUS current
			DESCRIPTION
				"Description"
			::= { sleSecurityBaseControl 16 }

		
		-- 1.3.6.1.4.1.6296.101.7.1.3
		sleSecurityBaseNotification OBJECT IDENTIFIER ::= { sleSecurityBase 3 }

		
		-- 1.3.6.1.4.1.6296.101.7.1.3.1
		sleSecurityRadiusProfileChanged NOTIFICATION-TYPE
			OBJECTS { sleSecurityRadiusRetransmissions, sleSecurityRadiusTimeouts, sleSecurityRadiusInterfaceName, sleSecurityRadiusInterfaceAddress, sleSecurityControlRequest, 
				sleSecurityControlTimeStamp, sleSecurityControlReqResult }
			STATUS current
			DESCRIPTION 
				"Description"
			::= { sleSecurityBaseNotification 1 }

		
		-- 1.3.6.1.4.1.6296.101.7.1.3.2
		sleSecurityTacacsProfileChanged NOTIFICATION-TYPE
			OBJECTS { sleSecurityTacacsInterfaceName, sleSecurityTacacsInterfaceAddress, sleSecurityTacacsPort, sleSecurityTacacsAuthType, sleSecurityTacacsTimeouts, 
				sleSecurityTacacsPriorityLevel, sleSecurityControlStatus, sleSecurityControlTimeStamp, sleSecurityControlReqResult }
			STATUS current
			DESCRIPTION 
				"Description"
			::= { sleSecurityBaseNotification 2 }

		
		-- 1.3.6.1.4.1.6296.101.7.1.3.3
		sleSecurityDot1xActivityChanged NOTIFICATION-TYPE
			OBJECTS { sleSecurityDot1xActivity, sleSecurityControlRequest, sleSecurityControlTimeStamp, sleSecurityControlReqResult }
			STATUS current
			DESCRIPTION 
				"Description"
			::= { sleSecurityBaseNotification 3 }

		
		-- 1.3.6.1.4.1.6296.101.7.2
		sleAAA OBJECT IDENTIFIER ::= { sleSecurity 2 }

		
		-- 1.3.6.1.4.1.6296.101.7.2.1
		sleAaaTable OBJECT-TYPE
			SYNTAX SEQUENCE OF SleAaaEntry
			MAX-ACCESS not-accessible
			STATUS current
			DESCRIPTION
				"Description."
			::= { sleAAA 1 }

		
		-- 1.3.6.1.4.1.6296.101.7.2.1.1
		sleAaaEntry OBJECT-TYPE
			SYNTAX SleAaaEntry
			MAX-ACCESS not-accessible
			STATUS current
			DESCRIPTION
				"Description."
			INDEX { sleAaaSession, sleAaaAuthen }
			::= { sleAaaTable 1 }

		
		SleAaaEntry ::=
			SEQUENCE { 
				sleAaaSession
					INTEGER,
				sleAaaAuthen
					INTEGER,
				sleAaaEnable
					INTEGER,
				sleAaaPrimarySequence
					INTEGER
			 }

		-- 1.3.6.1.4.1.6296.101.7.2.1.1.1
		sleAaaSession OBJECT-TYPE
			SYNTAX INTEGER
				{
				console(1),
				remote(2)
				}
			MAX-ACCESS read-only
			STATUS current
			DESCRIPTION
				"Location of authentication."
			::= { sleAaaEntry 1 }

		
		-- 1.3.6.1.4.1.6296.101.7.2.1.1.2
		sleAaaAuthen OBJECT-TYPE
			SYNTAX INTEGER
				{
				host(1),
				radius(2),
				tacacs(3)
				}
			MAX-ACCESS read-only
			STATUS current
			DESCRIPTION
				"The kind of authentication."
			::= { sleAaaEntry 2 }

		
		-- 1.3.6.1.4.1.6296.101.7.2.1.1.3
		sleAaaEnable OBJECT-TYPE
			SYNTAX INTEGER
				{
				disable(0),
				enable(1)
				}
			MAX-ACCESS read-only
			STATUS current
			DESCRIPTION
				"Enable or disable the corresponding authen method."
			::= { sleAaaEntry 3 }

		
		-- 1.3.6.1.4.1.6296.101.7.2.1.1.4
		sleAaaPrimarySequence OBJECT-TYPE
			SYNTAX INTEGER (1..3)
			MAX-ACCESS read-only
			STATUS current
			DESCRIPTION
				"The primary priority of the corresponding authen method"
			::= { sleAaaEntry 4 }

		
		-- 1.3.6.1.4.1.6296.101.7.2.2
		sleAaaControl OBJECT IDENTIFIER ::= { sleAAA 2 }

		
		-- 1.3.6.1.4.1.6296.101.7.2.2.1
		sleAaaControlRequest OBJECT-TYPE
			SYNTAX INTEGER { setAaaProfile(1) }
			MAX-ACCESS read-write
			STATUS current
			DESCRIPTION
				"Description"
			::= { sleAaaControl 1 }

		
		-- 1.3.6.1.4.1.6296.101.7.2.2.2
		sleAaaControlStatus OBJECT-TYPE
			SYNTAX SleControlStatusType
			MAX-ACCESS read-only
			STATUS current
			DESCRIPTION
				"Describes the status of a user command group, 
				used for block commands while a command execution in process."
			::= { sleAaaControl 2 }

		
		-- 1.3.6.1.4.1.6296.101.7.2.2.3
		sleAaaControlTimer OBJECT-TYPE
			SYNTAX Gauge32
			MAX-ACCESS read-write
			STATUS current
			DESCRIPTION
				"Maximum command duration time in case of long running."
			::= { sleAaaControl 3 }

		
		-- 1.3.6.1.4.1.6296.101.7.2.2.4
		sleAaaControlTimeStamp OBJECT-TYPE
			SYNTAX TimeStamp
			MAX-ACCESS read-only
			STATUS current
			DESCRIPTION
				"Time stamp attribute set at end of command."
			::= { sleAaaControl 4 }

		
		-- 1.3.6.1.4.1.6296.101.7.2.2.5
		sleAaaControlReqResult OBJECT-TYPE
			SYNTAX SleControlRequestResultType
			MAX-ACCESS read-only
			STATUS current
			DESCRIPTION
				"Command result attribute."
			::= { sleAaaControl 5 }

		
		-- 1.3.6.1.4.1.6296.101.7.2.2.6
		sleAaaControlSession OBJECT-TYPE
			SYNTAX INTEGER
				{
				console(1),
				remote(2)
				}
			MAX-ACCESS read-write
			STATUS current
			DESCRIPTION
				"Location of authentication."
			::= { sleAaaControl 6 }

		
		-- 1.3.6.1.4.1.6296.101.7.2.2.7
		sleAaaControlAuthen OBJECT-TYPE
			SYNTAX INTEGER
				{
				host(1),
				radius(2),
				tacacs(3)
				}
			MAX-ACCESS read-write
			STATUS current
			DESCRIPTION
				"The kind of authentication."
			::= { sleAaaControl 7 }

		
		-- 1.3.6.1.4.1.6296.101.7.2.2.8
		sleAaaControlEnable OBJECT-TYPE
			SYNTAX INTEGER
				{
				disable(0),
				enable(1)
				}
			MAX-ACCESS read-write
			STATUS current
			DESCRIPTION
				"Enable or disable the corresponding authen method."
			::= { sleAaaControl 8 }

		
		-- 1.3.6.1.4.1.6296.101.7.2.2.9
		sleAaaControlPrimaryFlag OBJECT-TYPE
			SYNTAX INTEGER
				{
				disable(0),
				enable(1)
				}
			MAX-ACCESS read-write
			STATUS current
			DESCRIPTION
				"The primary validation flag of the corresponding authen method"
			::= { sleAaaControl 9 }

		
		-- 1.3.6.1.4.1.6296.101.7.2.3
		sleAaaNotification OBJECT IDENTIFIER ::= { sleAAA 3 }

		
		-- 1.3.6.1.4.1.6296.101.7.2.3.1
		sleAaaProfileChanged NOTIFICATION-TYPE
			OBJECTS { sleAaaControlRequest, sleAaaControlTimeStamp, sleAaaControlReqResult, sleAaaEnable, sleAaaPrimarySequence
				 }
			STATUS current
			DESCRIPTION 
				"Description
				"
			::= { sleAaaNotification 1 }

		
		-- 1.3.6.1.4.1.6296.101.7.3
		sleRadiusServer OBJECT IDENTIFIER ::= { sleSecurity 3 }

		
		-- 1.3.6.1.4.1.6296.101.7.3.1
		sleRadiusServerTable OBJECT-TYPE
			SYNTAX SEQUENCE OF SleRadiusServerEntry
			MAX-ACCESS not-accessible
			STATUS current
			DESCRIPTION
				"Description."
			::= { sleRadiusServer 1 }

		
		-- 1.3.6.1.4.1.6296.101.7.3.1.1
		sleRadiusServerEntry OBJECT-TYPE
			SYNTAX SleRadiusServerEntry
			MAX-ACCESS not-accessible
			STATUS current
			DESCRIPTION
				"Description."
			INDEX { sleRadiusServerAddress }
			::= { sleRadiusServerTable 1 }

		
		SleRadiusServerEntry ::=
			SEQUENCE { 
				sleRadiusServerAddress
					IpAddress,
				sleRadiusServerClientKey
					OCTET STRING,
				sleRadiusServerAuthPort
					INTEGER,
				sleRadiusServerAccPort
					INTEGER,
				sleRadiusServerMode
					BITS
			 }

		-- 1.3.6.1.4.1.6296.101.7.3.1.1.1
		sleRadiusServerAddress OBJECT-TYPE
			SYNTAX IpAddress
			MAX-ACCESS read-only
			STATUS current
			DESCRIPTION
				"The IP address of the RADIUS server referred 
				to in this table entry."
			::= { sleRadiusServerEntry 1 }

		
		-- 1.3.6.1.4.1.6296.101.7.3.1.1.2
		sleRadiusServerClientKey OBJECT-TYPE
			SYNTAX OCTET STRING (SIZE (0..255))
			MAX-ACCESS read-only
			STATUS current
			DESCRIPTION
				"The key to be used in communication between the 
				device and the Radius server."
			::= { sleRadiusServerEntry 2 }

		
		-- 1.3.6.1.4.1.6296.101.7.3.1.1.3
		sleRadiusServerAuthPort OBJECT-TYPE
			SYNTAX INTEGER (0..65535)
			MAX-ACCESS read-only
			STATUS current
			DESCRIPTION
				"The UDP port the client is using to send requests to this server for authentication."
			::= { sleRadiusServerEntry 3 }

		
		-- 1.3.6.1.4.1.6296.101.7.3.1.1.4
		sleRadiusServerAccPort OBJECT-TYPE
			SYNTAX INTEGER (0..65535)
			MAX-ACCESS read-only
			STATUS current
			DESCRIPTION
				"The UDP port the client is using to send requests to this server for accounting."
			::= { sleRadiusServerEntry 4 }

		
		-- 1.3.6.1.4.1.6296.101.7.3.1.1.5
		sleRadiusServerMode OBJECT-TYPE
			SYNTAX BITS
				{
				aaa(0),
				dot1x(1)
				}
			MAX-ACCESS read-only
			STATUS current
			DESCRIPTION
				"Radius Server operation mode: if set bit 0, is used 
				in login, and if set bit 1, is used in 802.1X (dot1x)."
			::= { sleRadiusServerEntry 5 }

		
		-- 1.3.6.1.4.1.6296.101.7.3.2
		sleRadiusServerControl OBJECT IDENTIFIER ::= { sleRadiusServer 2 }

		
		-- 1.3.6.1.4.1.6296.101.7.3.2.1
		sleRadiusServerControlRequest OBJECT-TYPE
			SYNTAX INTEGER
				{
				createRadiusServer(1),
				destroyRadiusServer(2),
				setRadiusServerProfile (3)
				}
			MAX-ACCESS read-write
			STATUS current
			DESCRIPTION
				"The MIB object for the user command."
			::= { sleRadiusServerControl 1 }

		
		-- 1.3.6.1.4.1.6296.101.7.3.2.2
		sleRadiusServerControlStatus OBJECT-TYPE
			SYNTAX SleControlStatusType
			MAX-ACCESS read-only
			STATUS current
			DESCRIPTION
				"Describes the status of a user command group, 
				used for block commands while a command execution in process."
			::= { sleRadiusServerControl 2 }

		
		-- 1.3.6.1.4.1.6296.101.7.3.2.3
		sleRadiusServerControlTimer OBJECT-TYPE
			SYNTAX Gauge32
			MAX-ACCESS read-write
			STATUS current
			DESCRIPTION
				"Maximum command duration time in case of long running"
			::= { sleRadiusServerControl 3 }

		
		-- 1.3.6.1.4.1.6296.101.7.3.2.4
		sleRadiusServerControlTimeStamp OBJECT-TYPE
			SYNTAX TimeStamp
			MAX-ACCESS read-only
			STATUS current
			DESCRIPTION
				"Time stamp attribute set at end of command."
			::= { sleRadiusServerControl 4 }

		
		-- 1.3.6.1.4.1.6296.101.7.3.2.5
		sleRadiusServerControlReqResult OBJECT-TYPE
			SYNTAX SleControlRequestResultType
			MAX-ACCESS read-only
			STATUS current
			DESCRIPTION
				"Command result attribute."
			::= { sleRadiusServerControl 5 }

		
		-- 1.3.6.1.4.1.6296.101.7.3.2.6
		sleRadiusServerControlAddress OBJECT-TYPE
			SYNTAX IpAddress
			MAX-ACCESS read-write
			STATUS current
			DESCRIPTION
				"The IP address of the RADIUS server referred to 
				in this table entry."
			::= { sleRadiusServerControl 6 }

		
		-- 1.3.6.1.4.1.6296.101.7.3.2.7
		sleRadiusServerControlClientKey OBJECT-TYPE
			SYNTAX OCTET STRING (SIZE (0..255))
			MAX-ACCESS read-write
			STATUS current
			DESCRIPTION
				"The key to be used in communication between 
				the device and the Radius server."
			::= { sleRadiusServerControl 7 }

		
		-- 1.3.6.1.4.1.6296.101.7.3.2.8
		sleRadiusServerControlAuthPort OBJECT-TYPE
			SYNTAX Integer32 (0..65535)
			MAX-ACCESS read-write
			STATUS current
			DESCRIPTION
				"The service port  number for communication with server."
			::= { sleRadiusServerControl 8 }

		
		-- 1.3.6.1.4.1.6296.101.7.3.2.9
		sleRadiusServerControlAccPort OBJECT-TYPE
			SYNTAX Integer32 (0..65535)
			MAX-ACCESS read-write
			STATUS current
			DESCRIPTION
				"The service port  number for communication with server."
			::= { sleRadiusServerControl 9 }

		
		-- 1.3.6.1.4.1.6296.101.7.3.2.10
		sleRadiusServerControlMode OBJECT-TYPE
			SYNTAX BITS
				{
				aaa(0),
				dot1x(1)
				}
			MAX-ACCESS read-write
			STATUS current
			DESCRIPTION
				"Description."
			::= { sleRadiusServerControl 10 }
-- Radius Server operation mode: if set bit 0, is used 
-- in login, and if set bit 1, is used in 802.1X (dot1x).
		
		-- 1.3.6.1.4.1.6296.101.7.3.3
		sleRadiusServerNotification OBJECT IDENTIFIER ::= { sleRadiusServer 3 }

		
		-- 1.3.6.1.4.1.6296.101.7.3.3.1
		sleRadiusServerCreated NOTIFICATION-TYPE
			OBJECTS { sleRadiusServerControlRequest, sleRadiusServerControlTimeStamp, sleRadiusServerControlReqResult, sleRadiusServerClientKey, sleRadiusServerAccPort, 
				sleRadiusServerAuthPort, sleRadiusServerMode }
			STATUS current
			DESCRIPTION 
				"Description"
			::= { sleRadiusServerNotification 1 }

		
		-- 1.3.6.1.4.1.6296.101.7.3.3.2
		sleRadiusServerDestroyed NOTIFICATION-TYPE
			OBJECTS { sleRadiusServerControlRequest, sleRadiusServerControlTimeStamp, sleRadiusServerControlReqResult, sleRadiusServerControlAddress }
			STATUS current
			DESCRIPTION 
				"Description"
			::= { sleRadiusServerNotification 2 }

		
		-- 1.3.6.1.4.1.6296.101.7.3.3.3
		sleRadiusServerProfileChanged NOTIFICATION-TYPE
			OBJECTS { sleRadiusServerControlRequest, sleRadiusServerControlTimeStamp, sleRadiusServerControlReqResult, sleRadiusServerClientKey, sleRadiusServerAuthPort, 
				sleRadiusServerAccPort, sleRadiusServerMode }
			STATUS current
			DESCRIPTION 
				"Description"
			::= { sleRadiusServerNotification 3 }

		
		-- 1.3.6.1.4.1.6296.101.7.4
		sleTacacsServer OBJECT IDENTIFIER ::= { sleSecurity 4 }

		
		-- 1.3.6.1.4.1.6296.101.7.4.1
		sleTacacsServerTable OBJECT-TYPE
			SYNTAX SEQUENCE OF SleTacacsServerEntry
			MAX-ACCESS not-accessible
			STATUS current
			DESCRIPTION
				"Description."
			::= { sleTacacsServer 1 }

		
		-- 1.3.6.1.4.1.6296.101.7.4.1.1
		sleTacacsServerEntry OBJECT-TYPE
			SYNTAX SleTacacsServerEntry
			MAX-ACCESS not-accessible
			STATUS current
			DESCRIPTION
				"Description."
			INDEX { sleTacacsServerAddress }
			::= { sleTacacsServerTable 1 }

		
		SleTacacsServerEntry ::=
			SEQUENCE { 
				sleTacacsServerAddress
					IpAddress,
				sleTacacsServerClientKey
					OCTET STRING
			 }

		-- 1.3.6.1.4.1.6296.101.7.4.1.1.1
		sleTacacsServerAddress OBJECT-TYPE
			SYNTAX IpAddress
			MAX-ACCESS read-only
			STATUS current
			DESCRIPTION
				"The IP address of the TACACS accounting server 
				referred to in this table entry."
			::= { sleTacacsServerEntry 1 }

		
		-- 1.3.6.1.4.1.6296.101.7.4.1.1.2
		sleTacacsServerClientKey OBJECT-TYPE
			SYNTAX OCTET STRING (SIZE (0..255))
			MAX-ACCESS read-only
			STATUS current
			DESCRIPTION
				"The key to be used in communication between the 
				device and the Tacacs server."
			::= { sleTacacsServerEntry 2 }

		
		-- 1.3.6.1.4.1.6296.101.7.4.2
		sleTacacsServerControl OBJECT IDENTIFIER ::= { sleTacacsServer 2 }

		
		-- 1.3.6.1.4.1.6296.101.7.4.2.1
		sleTacacsServerControlRequest OBJECT-TYPE
			SYNTAX INTEGER
				{
				createTacacsServer(1),
				destroyTacacsServer (2),
				setTacacsServerClientKey(3)
				}
			MAX-ACCESS read-write
			STATUS current
			DESCRIPTION
				"The MIB object for the user command."
			::= { sleTacacsServerControl 1 }

		
		-- 1.3.6.1.4.1.6296.101.7.4.2.2
		sleTacacsServerControlStatus OBJECT-TYPE
			SYNTAX SleControlStatusType
			MAX-ACCESS read-only
			STATUS current
			DESCRIPTION
				"Describes the status of a user command group, used 
				for block commands while a command execution in process."
			::= { sleTacacsServerControl 2 }

		
		-- 1.3.6.1.4.1.6296.101.7.4.2.3
		sleTacacsServerControlTimer OBJECT-TYPE
			SYNTAX Gauge32
			MAX-ACCESS read-write
			STATUS current
			DESCRIPTION
				"Maximum command duration time in case of long running."
			::= { sleTacacsServerControl 3 }

		
		-- 1.3.6.1.4.1.6296.101.7.4.2.4
		sleTacacsServerControlTimeStamp OBJECT-TYPE
			SYNTAX TimeStamp
			MAX-ACCESS read-only
			STATUS current
			DESCRIPTION
				"Time stamp attribute set at end of command."
			::= { sleTacacsServerControl 4 }

		
		-- 1.3.6.1.4.1.6296.101.7.4.2.5
		sleTacacsServerControlReqResult OBJECT-TYPE
			SYNTAX SleControlRequestResultType
			MAX-ACCESS read-only
			STATUS current
			DESCRIPTION
				"Command result attribute."
			::= { sleTacacsServerControl 5 }

		
		-- 1.3.6.1.4.1.6296.101.7.4.2.6
		sleTacacsServerControlAddress OBJECT-TYPE
			SYNTAX IpAddress
			MAX-ACCESS read-write
			STATUS current
			DESCRIPTION
				"The IP address of the TACACS accounting server 
				referred to in this table entry."
			::= { sleTacacsServerControl 6 }

		
		-- 1.3.6.1.4.1.6296.101.7.4.2.7
		sleTacacsServerControlClientKey OBJECT-TYPE
			SYNTAX OCTET STRING (SIZE (0..255))
			MAX-ACCESS read-write
			STATUS current
			DESCRIPTION
				"The key to be used in communication between the 
				device and the Tacacs server."
			::= { sleTacacsServerControl 7 }

		
		-- 1.3.6.1.4.1.6296.101.7.4.3
		sleTacacsServerNotification OBJECT IDENTIFIER ::= { sleTacacsServer 3 }

		
		-- 1.3.6.1.4.1.6296.101.7.4.3.1
		sleTacacsServerCreated NOTIFICATION-TYPE
			OBJECTS { sleTacacsServerControlRequest, sleTacacsServerControlTimeStamp, sleTacacsServerControlReqResult, sleTacacsServerClientKey }
			STATUS current
			DESCRIPTION 
				"Description"
			::= { sleTacacsServerNotification 1 }

		
		-- 1.3.6.1.4.1.6296.101.7.4.3.2
		sleTacacsServerDestroyed NOTIFICATION-TYPE
			OBJECTS { sleTacacsServerControlRequest, sleTacacsServerControlTimeStamp, sleTacacsServerControlReqResult, sleTacacsServerControlAddress }
			STATUS current
			DESCRIPTION 
				"DescriptionDescription"
			::= { sleTacacsServerNotification 2 }

		
		-- 1.3.6.1.4.1.6296.101.7.4.3.3
		sleTacacsServerClientKeyChanged NOTIFICATION-TYPE
			OBJECTS { sleTacacsServerControlRequest, sleTacacsServerControlTimeStamp, sleTacacsServerControlReqResult, sleTacacsServerClientKey }
			STATUS current
			DESCRIPTION 
				"Description"
			::= { sleTacacsServerNotification 3 }

		
		-- 1.3.6.1.4.1.6296.101.7.5
		sleAcl OBJECT IDENTIFIER ::= { sleSecurity 5 }

		
		-- 1.3.6.1.4.1.6296.101.7.5.1
		sleAclTable OBJECT-TYPE
			SYNTAX SEQUENCE OF SleAclEntry
			MAX-ACCESS not-accessible
			STATUS current
			DESCRIPTION
				"Description"
			::= { sleAcl 1 }

		
		-- 1.3.6.1.4.1.6296.101.7.5.1.1
		sleAclEntry OBJECT-TYPE
			SYNTAX SleAclEntry
			MAX-ACCESS not-accessible
			STATUS current
			DESCRIPTION
				"Description."
			INDEX { sleAclName }
			::= { sleAclTable 1 }

		
		SleAclEntry ::=
			SEQUENCE { 
				sleAclName
					OCTET STRING,
				sleAclSrcIpAddr
					IpAddress,
				sleAclSrcPrefixLength
					Integer32,
				sleAclDstIpAddr
					IpAddress,
				sleAclDstPrefixLength
					Integer32,
				sleAclDscp
					Integer32,
				sleAclProtocolType
					Integer32,
				sleAclTcpFlag
					BITS,
				sleAclSrcL4Port
					Integer32,
				sleAclDstL4Port
					Integer32,
				sleAclPktLen
					Integer32,
				sleAclValidFlags
					BITS,
				sleAclMatchFlags
					BITS,
				sleAclMatchAction
					INTEGER,
				sleAclNomatchAction
					INTEGER,
				sleAclPriority
					INTEGER
			 }

		-- 1.3.6.1.4.1.6296.101.7.5.1.1.1
		sleAclName OBJECT-TYPE
			SYNTAX OCTET STRING (SIZE (0..63))
			MAX-ACCESS read-only
			STATUS current
			DESCRIPTION
				"Description"
			::= { sleAclEntry 1 }

		
		-- 1.3.6.1.4.1.6296.101.7.5.1.1.2
		sleAclSrcIpAddr OBJECT-TYPE
			SYNTAX IpAddress
			MAX-ACCESS read-only
			STATUS current
			DESCRIPTION
				"Description"
			::= { sleAclEntry 2 }

		
		-- 1.3.6.1.4.1.6296.101.7.5.1.1.3
		sleAclSrcPrefixLength OBJECT-TYPE
			SYNTAX Integer32 (0..31)
			MAX-ACCESS read-only
			STATUS current
			DESCRIPTION
				"Description"
			::= { sleAclEntry 3 }

		
		-- 1.3.6.1.4.1.6296.101.7.5.1.1.4
		sleAclDstIpAddr OBJECT-TYPE
			SYNTAX IpAddress
			MAX-ACCESS read-only
			STATUS current
			DESCRIPTION
				"Description"
			::= { sleAclEntry 4 }

		
		-- 1.3.6.1.4.1.6296.101.7.5.1.1.5
		sleAclDstPrefixLength OBJECT-TYPE
			SYNTAX Integer32 (0..31)
			MAX-ACCESS read-only
			STATUS current
			DESCRIPTION
				"Description"
			::= { sleAclEntry 5 }

		
		-- 1.3.6.1.4.1.6296.101.7.5.1.1.6
		sleAclDscp OBJECT-TYPE
			SYNTAX Integer32
			MAX-ACCESS read-only
			STATUS current
			DESCRIPTION
				"Description"
			DEFVAL { -1 }
			::= { sleAclEntry 6 }

		
		-- 1.3.6.1.4.1.6296.101.7.5.1.1.7
		sleAclProtocolType OBJECT-TYPE
			SYNTAX Integer32 (1..255)
			MAX-ACCESS read-only
			STATUS current
			DESCRIPTION
				"Description"
			::= { sleAclEntry 7 }

		
		-- 1.3.6.1.4.1.6296.101.7.5.1.1.8
		sleAclTcpFlag OBJECT-TYPE
			SYNTAX BITS
				{
				reserv(0),
				reserv1(1),
				urg(2),
				ack(3),
				psh(4),
				rst(5),
				syn(6),
				fin(7)
				}
			MAX-ACCESS read-only
			STATUS current
			DESCRIPTION
				"Description"
			::= { sleAclEntry 8 }

		
		-- 1.3.6.1.4.1.6296.101.7.5.1.1.9
		sleAclSrcL4Port OBJECT-TYPE
			SYNTAX Integer32 (1..65535)
			MAX-ACCESS read-only
			STATUS current
			DESCRIPTION
				"Description"
			::= { sleAclEntry 9 }

		
		-- 1.3.6.1.4.1.6296.101.7.5.1.1.10
		sleAclDstL4Port OBJECT-TYPE
			SYNTAX Integer32 (1..65535)
			MAX-ACCESS read-only
			STATUS current
			DESCRIPTION
				"Description"
			::= { sleAclEntry 10 }

		
		-- 1.3.6.1.4.1.6296.101.7.5.1.1.11
		sleAclPktLen OBJECT-TYPE
			SYNTAX Integer32 (21..65535)
			MAX-ACCESS read-only
			STATUS current
			DESCRIPTION
				"Description"
			::= { sleAclEntry 11 }

		
		-- 1.3.6.1.4.1.6296.101.7.5.1.1.12
		sleAclValidFlags OBJECT-TYPE
			SYNTAX BITS
				{
				aclSrcIpAddress(0),
				aclSrcPrefixLegth(1),
				aclDstIpAddress(2),
				aclDstPrefixLegth(3),
				aclDscp(4),
				aclProtocolType(5),
				aclTcpFlags(6),
				aclSrcL4Port(7),
				aclDstL4Port(8),
				aclPacketLength(9)
				}
			MAX-ACCESS read-only
			STATUS current
			DESCRIPTION
				"Description"
			::= { sleAclEntry 12 }

		
		-- 1.3.6.1.4.1.6296.101.7.5.1.1.13
		sleAclMatchFlags OBJECT-TYPE
			SYNTAX BITS
				{
				aclSrcIpAddress(0),
				aclSrcPrefixLegth(1),
				aclDstIpAddress(2),
				aclDstPrefixLength(3),
				aclDscp(4),
				aclProtocolType(5),
				aclTcpFlag(6),
				aclSrcL4Port(7),
				aclDstL4Port(8),
				aclPacketLength(9)
				}
			MAX-ACCESS read-only
			STATUS current
			DESCRIPTION
				"Description"
			::= { sleAclEntry 13 }

		
		-- 1.3.6.1.4.1.6296.101.7.5.1.1.14
		sleAclMatchAction OBJECT-TYPE
			SYNTAX INTEGER
				{
				permit(1),
				deny(2)
				}
			MAX-ACCESS read-only
			STATUS current
			DESCRIPTION
				"Description"
			::= { sleAclEntry 14 }

		
		-- 1.3.6.1.4.1.6296.101.7.5.1.1.15
		sleAclNomatchAction OBJECT-TYPE
			SYNTAX INTEGER
				{
				permit(1),
				deny(2)
				}
			MAX-ACCESS read-only
			STATUS current
			DESCRIPTION
				"DescriptionDescription"
			::= { sleAclEntry 15 }

		
		-- 1.3.6.1.4.1.6296.101.7.5.1.1.16
		sleAclPriority OBJECT-TYPE
			SYNTAX INTEGER
				{
				low(1),
				medium(2),
				high(3),
				highest(4)
				}
			MAX-ACCESS read-only
			STATUS current
			DESCRIPTION
				"Description"
			::= { sleAclEntry 16 }

		
		-- 1.3.6.1.4.1.6296.101.7.5.2
		sleAclControl OBJECT IDENTIFIER ::= { sleAcl 2 }

		
		-- 1.3.6.1.4.1.6296.101.7.5.2.1
		sleAclControlReqest OBJECT-TYPE
			SYNTAX INTEGER
				{
				createAclRule(1),
				destroyAclRule(2),
				setAclClassifierProfile(3),
				setAclMatchAction(10),
				setAclNomatchAction(11)
				}
			MAX-ACCESS read-write
			STATUS current
			DESCRIPTION
				"DescriptionDescription"
			::= { sleAclControl 1 }

		
		-- 1.3.6.1.4.1.6296.101.7.5.2.2
		sleAclControlStatus OBJECT-TYPE
			SYNTAX SleControlStatusType
			MAX-ACCESS read-only
			STATUS current
			DESCRIPTION
				"Description"
			::= { sleAclControl 2 }

		
		-- 1.3.6.1.4.1.6296.101.7.5.2.3
		sleAclControlTimer OBJECT-TYPE
			SYNTAX Gauge32
			MAX-ACCESS read-write
			STATUS current
			DESCRIPTION
				"Description"
			::= { sleAclControl 3 }

		
		-- 1.3.6.1.4.1.6296.101.7.5.2.4
		sleAclControlTimeStamp OBJECT-TYPE
			SYNTAX TimeStamp
			MAX-ACCESS read-only
			STATUS current
			DESCRIPTION
				"Description"
			::= { sleAclControl 4 }

		
		-- 1.3.6.1.4.1.6296.101.7.5.2.5
		sleAclControlReqResult OBJECT-TYPE
			SYNTAX SleControlRequestResultType
			MAX-ACCESS read-only
			STATUS current
			DESCRIPTION
				"Description"
			::= { sleAclControl 5 }

		
		-- 1.3.6.1.4.1.6296.101.7.5.2.6
		sleAclControlName OBJECT-TYPE
			SYNTAX OCTET STRING (SIZE (0..63))
			MAX-ACCESS read-write
			STATUS current
			DESCRIPTION
				"Description"
			::= { sleAclControl 6 }

		
		-- 1.3.6.1.4.1.6296.101.7.5.2.7
		sleAclControlSrcIpAddr OBJECT-TYPE
			SYNTAX IpAddress
			MAX-ACCESS read-write
			STATUS current
			DESCRIPTION
				"Description"
			::= { sleAclControl 7 }

		
		-- 1.3.6.1.4.1.6296.101.7.5.2.8
		sleAclControlSrcPrefixLength OBJECT-TYPE
			SYNTAX Integer32 (0..31)
			MAX-ACCESS read-write
			STATUS current
			DESCRIPTION
				"Description"
			::= { sleAclControl 8 }

		
		-- 1.3.6.1.4.1.6296.101.7.5.2.9
		sleAclControlDstIpAddr OBJECT-TYPE
			SYNTAX IpAddress
			MAX-ACCESS read-write
			STATUS current
			DESCRIPTION
				"DescriptionDescription"
			::= { sleAclControl 9 }

		
		-- 1.3.6.1.4.1.6296.101.7.5.2.10
		sleAclControlDstPrefixLength OBJECT-TYPE
			SYNTAX Integer32 (0..31)
			MAX-ACCESS read-write
			STATUS current
			DESCRIPTION
				"Description"
			::= { sleAclControl 10 }

		
		-- 1.3.6.1.4.1.6296.101.7.5.2.11
		sleAclControlDscp OBJECT-TYPE
			SYNTAX Integer32
			MAX-ACCESS read-write
			STATUS current
			DESCRIPTION
				"Description"
			DEFVAL { -1 }
			::= { sleAclControl 11 }

		
		-- 1.3.6.1.4.1.6296.101.7.5.2.12
		sleAclControlProtocolType OBJECT-TYPE
			SYNTAX Integer32 (1..255)
			MAX-ACCESS read-write
			STATUS current
			DESCRIPTION
				"Description"
			::= { sleAclControl 12 }

		
		-- 1.3.6.1.4.1.6296.101.7.5.2.13
		sleAclControlTcpFlag OBJECT-TYPE
			SYNTAX BITS
				{
				reserv(0),
				reserv1(1),
				urg(2),
				ack(3),
				psh(4),
				rst(5),
				syn(6),
				fin(7)
				}
			MAX-ACCESS read-write
			STATUS current
			DESCRIPTION
				"Description"
			::= { sleAclControl 13 }

		
		-- 1.3.6.1.4.1.6296.101.7.5.2.14
		sleAclControlSrcL4Port OBJECT-TYPE
			SYNTAX Integer32 (0..65535)
			MAX-ACCESS read-write
			STATUS current
			DESCRIPTION
				"Description"
			::= { sleAclControl 14 }

		
		-- 1.3.6.1.4.1.6296.101.7.5.2.15
		sleAclControlDstL4Port OBJECT-TYPE
			SYNTAX Integer32 (0..65535)
			MAX-ACCESS read-write
			STATUS current
			DESCRIPTION
				"Description"
			::= { sleAclControl 15 }

		
		-- 1.3.6.1.4.1.6296.101.7.5.2.16
		sleAclControlPktLen OBJECT-TYPE
			SYNTAX Integer32 (21..65535)
			MAX-ACCESS read-write
			STATUS current
			DESCRIPTION
				"Description"
			::= { sleAclControl 16 }

		
		-- 1.3.6.1.4.1.6296.101.7.5.2.17
		sleAclControlValidFlags OBJECT-TYPE
			SYNTAX BITS
				{
				aclSrcIpAddress(0),
				aclSrcPrefixLength(1),
				aclDstIpAddress(2),
				aclDstPrefixLength(3),
				aclDscp(4),
				aclProtocolType(5),
				aclTcpFlag(6),
				aclSrcL4Port(7),
				aclDstL4Port(8),
				aclPacketLength(9)
				}
			MAX-ACCESS read-write
			STATUS current
			DESCRIPTION
				"Description"
			::= { sleAclControl 17 }

		
		-- 1.3.6.1.4.1.6296.101.7.5.2.18
		sleAclControlMatchFlags OBJECT-TYPE
			SYNTAX BITS
				{
				aclSrcIpAddress(0),
				aclSrcPrefixLength(1),
				aclDstIpAddress(2),
				aclDstPrefixLength(3),
				aclDscp(4),
				aclProtocolType(5),
				aclTcpFlag(6),
				aclSrcL4Port(7),
				aclDstL4Port(8),
				aclPacketLength(9)
				}
			MAX-ACCESS read-write
			STATUS current
			DESCRIPTION
				"Description"
			::= { sleAclControl 18 }

		
		-- 1.3.6.1.4.1.6296.101.7.5.2.19
		sleAclControlMatchAction OBJECT-TYPE
			SYNTAX INTEGER
				{
				none(0),
				permit(1),
				deny(2)
				}
			MAX-ACCESS read-write
			STATUS current
			DESCRIPTION
				"Description"
			::= { sleAclControl 19 }

		
		-- 1.3.6.1.4.1.6296.101.7.5.2.20
		sleAclControlNomatchAction OBJECT-TYPE
			SYNTAX INTEGER
				{
				none(0),
				permit(1),
				deny(2)
				}
			MAX-ACCESS read-write
			STATUS current
			DESCRIPTION
				"Description"
			::= { sleAclControl 20 }

		
		-- 1.3.6.1.4.1.6296.101.7.5.2.21
		sleAclControlPriority OBJECT-TYPE
			SYNTAX INTEGER
				{
				low(1),
				medium(2),
				high(3),
				highest(4)
				}
			MAX-ACCESS read-write
			STATUS current
			DESCRIPTION
				"Description"
			::= { sleAclControl 21 }

		
		-- 1.3.6.1.4.1.6296.101.7.5.3
		sleAclNotification OBJECT IDENTIFIER ::= { sleAcl 3 }

		
		-- 1.3.6.1.4.1.6296.101.7.5.3.1
		sleAclCreated NOTIFICATION-TYPE
			OBJECTS { sleAclControlReqest, sleAclControlTimeStamp, sleAclControlReqResult, sleAclSrcIpAddr, sleAclSrcPrefixLength, 
				sleAclDstIpAddr, sleAclDstPrefixLength, sleAclDscp, sleAclProtocolType, sleAclTcpFlag, 
				sleAclSrcL4Port, sleAclDstL4Port, sleAclPktLen, sleAclValidFlags, sleAclMatchFlags, 
				sleAclMatchAction, sleAclNomatchAction, sleAclPriority }
			STATUS current
			DESCRIPTION 
				"Description"
			::= { sleAclNotification 1 }

		
		-- 1.3.6.1.4.1.6296.101.7.5.3.2
		sleAclDestroyed NOTIFICATION-TYPE
			OBJECTS { sleAclControlReqest, sleAclControlTimeStamp, sleAclControlReqResult, sleAclControlName }
			STATUS current
			DESCRIPTION 
				"Description"
			::= { sleAclNotification 2 }

		
		-- 1.3.6.1.4.1.6296.101.7.5.3.3
		sleAclClassifierProfileChanged NOTIFICATION-TYPE
			OBJECTS { sleAclControlReqest, sleAclControlTimeStamp, sleAclControlReqResult, sleAclSrcIpAddr, sleAclSrcPrefixLength, 
				sleAclDstIpAddr, sleAclDstPrefixLength, sleAclDscp, sleAclProtocolType, sleAclTcpFlag, 
				sleAclSrcL4Port, sleAclDstL4Port, sleAclPktLen, sleAclValidFlags, sleAclMatchFlags
				 }
			STATUS current
			DESCRIPTION 
				"Description"
			::= { sleAclNotification 3 }

		
		-- 1.3.6.1.4.1.6296.101.7.5.3.4
		sleAclMatchActionChanged NOTIFICATION-TYPE
			OBJECTS { sleAclControlReqest, sleAclControlTimeStamp, sleAclControlReqResult, sleAclMatchAction }
			STATUS current
			DESCRIPTION 
				"Description"
			::= { sleAclNotification 4 }

		
		-- 1.3.6.1.4.1.6296.101.7.5.3.5
		sleAclNomatchActionChanged NOTIFICATION-TYPE
			OBJECTS { sleAclControlReqest, sleAclControlTimeStamp, sleAclControlReqResult, sleAclNomatchAction }
			STATUS current
			DESCRIPTION 
				"Description"
			::= { sleAclNotification 5 }

		
		-- 1.3.6.1.4.1.6296.101.7.6
		sleDot1xPort OBJECT IDENTIFIER ::= { sleSecurity 6 }

		
		-- 1.3.6.1.4.1.6296.101.7.6.1
		sleDot1xPortTable OBJECT-TYPE
			SYNTAX SEQUENCE OF SleDot1xPortEntry
			MAX-ACCESS not-accessible
			STATUS current
			DESCRIPTION
				"The table that contains the configuration objects 
				for the Authenticator PAE associated with each port."
			::= { sleDot1xPort 1 }

		
		-- 1.3.6.1.4.1.6296.101.7.6.1.1
		sleDot1xPortEntry OBJECT-TYPE
			SYNTAX SleDot1xPortEntry
			MAX-ACCESS not-accessible
			STATUS current
			DESCRIPTION
				"The configuration information for an Authenticator PAE."
			INDEX { sleDot1xPortIndex }
			::= { sleDot1xPortTable 1 }

		
		SleDot1xPortEntry ::=
			SEQUENCE { 
				sleDot1xPortIndex
					InterfaceIndex,
				sleDot1xPortEnable
					INTEGER,
				sleDot1xPortMode
					INTEGER,
				sleDot1xPortReauthEnable
					INTEGER,
				sleDot1xPortQuietPeriod
					Integer32,
				sleDot1xPortReauthPeriod
					Integer32,
				sleDot1xPortAuthSuccess
					INTEGER
			 }

		-- 1.3.6.1.4.1.6296.101.7.6.1.1.1
		sleDot1xPortIndex OBJECT-TYPE
			SYNTAX InterfaceIndex
			MAX-ACCESS read-only
			STATUS current
			DESCRIPTION
				"The port number associated with this port."
			::= { sleDot1xPortEntry 1 }

		
		-- 1.3.6.1.4.1.6296.101.7.6.1.1.2
		sleDot1xPortEnable OBJECT-TYPE
			SYNTAX INTEGER
				{
				disable(1),
				portEnable(2),
				macEnable(3)
				}
			MAX-ACCESS read-only
			STATUS current
			DESCRIPTION
				"The administrativ state for each port."
			::= { sleDot1xPortEntry 2 }

		
		-- 1.3.6.1.4.1.6296.101.7.6.1.1.3
		sleDot1xPortMode OBJECT-TYPE
			SYNTAX INTEGER
				{
				auto(1),
				forceAuthorized(2),
				forceUnauthorized(3)
				}
			MAX-ACCESS read-only
			STATUS current
			DESCRIPTION
				"The control values of the Authenticator PAE controlled."
			::= { sleDot1xPortEntry 3 }

		
		-- 1.3.6.1.4.1.6296.101.7.6.1.1.4
		sleDot1xPortReauthEnable OBJECT-TYPE
			SYNTAX INTEGER
				{
				disable(0),
				enable(1)
				}
			MAX-ACCESS read-only
			STATUS current
			DESCRIPTION
				"The reauthentication control for this port."
			::= { sleDot1xPortEntry 4 }

		
		-- 1.3.6.1.4.1.6296.101.7.6.1.1.5
		sleDot1xPortQuietPeriod OBJECT-TYPE
			SYNTAX Integer32 (1..65535)
			MAX-ACCESS read-only
			STATUS current
			DESCRIPTION
				"The value, in seconds, of the quietPeriod constant
				currently in use by the Authenticator PAE state machine."
			::= { sleDot1xPortEntry 5 }

		
		-- 1.3.6.1.4.1.6296.101.7.6.1.1.6
		sleDot1xPortReauthPeriod OBJECT-TYPE
			SYNTAX Integer32 (1..65535)
			MAX-ACCESS read-only
			STATUS current
			DESCRIPTION
				"The value, in seconds, of the txPeriod constant
				currently in use by the Authenticator PAE state machine."
			::= { sleDot1xPortEntry 6 }

		
		-- 1.3.6.1.4.1.6296.101.7.6.1.1.7
		sleDot1xPortAuthSuccess OBJECT-TYPE
			SYNTAX INTEGER
				{
				fail(1),
				success(2)
				}
			MAX-ACCESS read-only
			STATUS current
			DESCRIPTION
				"The value result to authentication of the supplicator."
			::= { sleDot1xPortEntry 7 }

		
		-- 1.3.6.1.4.1.6296.101.7.6.2
		sleDot1xPortControl OBJECT IDENTIFIER ::= { sleDot1xPort 2 }

		
		-- 1.3.6.1.4.1.6296.101.7.6.2.1
		sleDot1xPortControlRequest OBJECT-TYPE
			SYNTAX INTEGER
				{
				setDot1xPortProfile(1),
				setDot1xPortReauthenticate(2),
				setDot1xPortInittialize(3)
				}
			MAX-ACCESS read-write
			STATUS current
			DESCRIPTION
				"The MIB object for the dot1x command.A SetRequest 
				on this attribute starts a command execution 
				process in the netElement."
			::= { sleDot1xPortControl 1 }

		
		-- 1.3.6.1.4.1.6296.101.7.6.2.2
		sleDot1xPortControlStatus OBJECT-TYPE
			SYNTAX SleControlStatusType
			MAX-ACCESS read-only
			STATUS current
			DESCRIPTION
				"Describes the status of a user command group, used
				for block commands while a command execution in process"
			::= { sleDot1xPortControl 2 }

		
		-- 1.3.6.1.4.1.6296.101.7.6.2.3
		sleDot1xPortControlTimer OBJECT-TYPE
			SYNTAX Gauge32
			MAX-ACCESS read-write
			STATUS current
			DESCRIPTION
				"Maximum command duration time in case of long running."
			::= { sleDot1xPortControl 3 }

		
		-- 1.3.6.1.4.1.6296.101.7.6.2.4
		sleDot1xPortControlTimeStamp OBJECT-TYPE
			SYNTAX TimeStamp
			MAX-ACCESS read-only
			STATUS current
			DESCRIPTION
				"Time stamp attribute set at end of command."
			::= { sleDot1xPortControl 4 }

		
		-- 1.3.6.1.4.1.6296.101.7.6.2.5
		sleDot1xPortControlReqResult OBJECT-TYPE
			SYNTAX SleControlRequestResultType
			MAX-ACCESS read-only
			STATUS current
			DESCRIPTION
				"Command result attribute."
			::= { sleDot1xPortControl 5 }

		
		-- 1.3.6.1.4.1.6296.101.7.6.2.6
		sleDot1xPortControlIndex OBJECT-TYPE
			SYNTAX Integer32
			MAX-ACCESS read-write
			STATUS current
			DESCRIPTION
				"The port number associated with this port."
			::= { sleDot1xPortControl 6 }

		
		-- 1.3.6.1.4.1.6296.101.7.6.2.7
		sleDot1xPortControlEnable OBJECT-TYPE
			SYNTAX INTEGER
				{
				default(-1),
				disable(1),
				portEnable(2),
				macEnable(3)
				}
			MAX-ACCESS read-write
			STATUS current
			DESCRIPTION
				"The administrativ state for each port."
			::= { sleDot1xPortControl 7 }

		
		-- 1.3.6.1.4.1.6296.101.7.6.2.8
		sleDot1xPortControlMode OBJECT-TYPE
			SYNTAX INTEGER
				{
				default(-1),
				auto(1),
				forceAuthorized(2),
				forceUnauthorized(3)
				}
			MAX-ACCESS read-write
			STATUS current
			DESCRIPTION
				"The control values of the Authenticator PAE controlled."
			::= { sleDot1xPortControl 8 }

		
		-- 1.3.6.1.4.1.6296.101.7.6.2.9
		sleDot1xPortControlReauthEnable OBJECT-TYPE
			SYNTAX INTEGER
				{
				default(-1),
				disable(0),
				enable(1)
				}
			MAX-ACCESS read-write
			STATUS current
			DESCRIPTION
				"The reauthentication control for this port. Setting
				this attribute TRUE causes the Authenticator PAE state
				machine for the Port to reauthenticate the Supplicant.
				Setting this attribute FALSE has no effect."
			::= { sleDot1xPortControl 9 }

		
		-- 1.3.6.1.4.1.6296.101.7.6.2.10
		sleDot1xPortControlQuietPeriod OBJECT-TYPE
			SYNTAX Integer32 (-1 | 1..65535)
			MAX-ACCESS read-write
			STATUS current
			DESCRIPTION
				"The value, in seconds, of the quietPeriod constant
				currently in use by the Authenticator PAE state machine."
			::= { sleDot1xPortControl 10 }

		
		-- 1.3.6.1.4.1.6296.101.7.6.2.11
		sleDot1xPortControlReauthPeriod OBJECT-TYPE
			SYNTAX Integer32 (-1 | 1..65535)
			MAX-ACCESS read-write
			STATUS current
			DESCRIPTION
				"The value, in seconds, of the txPeriod constant
				currently in use by the Authenticator PAE state machine."
			::= { sleDot1xPortControl 11 }

		
		-- 1.3.6.1.4.1.6296.101.7.6.3
		sleDot1xPortNotification OBJECT IDENTIFIER ::= { sleDot1xPort 3 }

		
		-- 1.3.6.1.4.1.6296.101.7.6.3.1
		sleDot1xPortProfileChanged NOTIFICATION-TYPE
			OBJECTS { sleDot1xPortControlRequest, sleDot1xPortControlReqResult, sleDot1xPortControlTimeStamp, sleDot1xPortEnable, sleDot1xPortMode, 
				sleDot1xPortReauthEnable, sleDot1xPortQuietPeriod, sleDot1xPortReauthPeriod }
			STATUS current
			DESCRIPTION 
				"The trap for CLI command."
			::= { sleDot1xPortNotification 1 }

		
		-- 1.3.6.1.4.1.6296.101.7.6.3.2
		sleDot1xPortAuthSuccessChanged NOTIFICATION-TYPE
			OBJECTS { sleDot1xPortControlRequest, sleDot1xPortControlTimeStamp, sleDot1xPortControlReqResult, sleDot1xPortAuthSuccess }
			STATUS current
			DESCRIPTION 
				"The trap for authentication result."
			::= { sleDot1xPortNotification 2 }

		
		-- 1.3.6.1.4.1.6296.101.7.7
		sleDot1xStatistics OBJECT IDENTIFIER ::= { sleSecurity 7 }

		
		-- 1.3.6.1.4.1.6296.101.7.7.1
		sleDot1xStatisticsTable OBJECT-TYPE
			SYNTAX SEQUENCE OF SleDot1xStatisticsEntry
			MAX-ACCESS not-accessible
			STATUS current
			DESCRIPTION
				"Description."
			::= { sleDot1xStatistics 1 }

		
		-- 1.3.6.1.4.1.6296.101.7.7.1.1
		sleDot1xStatisticsEntry OBJECT-TYPE
			SYNTAX SleDot1xStatisticsEntry
			MAX-ACCESS not-accessible
			STATUS current
			DESCRIPTION
				"Description."
			INDEX { sleDot1xStatsPortIndex }
			::= { sleDot1xStatisticsTable 1 }

		
		SleDot1xStatisticsEntry ::=
			SEQUENCE { 
				sleDot1xStatsPortIndex
					INTEGER,
				sleDot1xStatsEapolFramesRx
					Counter32,
				sleDot1xStatsEapolFramesTx
					Counter32,
				sleDot1xStatsEapolStartFramesRx
					Counter32,
				sleDot1xStatsEapolLogoffFramesRx
					Counter32,
				sleDot1xStatsEapolRespIdFramesRx
					Counter32,
				sleDot1xStatsEapolRespFramesRx
					Counter32,
				sleDot1xStatsEapolReqIdFramesTx
					Counter32,
				sleDot1xStatsEapolReqFramesTx
					Integer32,
				sleDot1xStatsInvalidEapolFramesRx
					Counter32,
				sleDot1xStatsEapLengthErrorFramesRx
					Counter32,
				sleDot1xStatsLastEapolFrameVersion
					Counter32,
				sleDot1xStatsLastEapolFrameSource
					MacAddress
			 }

		-- 1.3.6.1.4.1.6296.101.7.7.1.1.1
		sleDot1xStatsPortIndex OBJECT-TYPE
			SYNTAX INTEGER (1..255)
			MAX-ACCESS read-only
			STATUS current
			DESCRIPTION
				"Description"
			::= { sleDot1xStatisticsEntry 1 }

		
		-- 1.3.6.1.4.1.6296.101.7.7.1.1.2
		sleDot1xStatsEapolFramesRx OBJECT-TYPE
			SYNTAX Counter32
			MAX-ACCESS read-only
			STATUS current
			DESCRIPTION
				"Description"
			::= { sleDot1xStatisticsEntry 2 }

		
		-- 1.3.6.1.4.1.6296.101.7.7.1.1.3
		sleDot1xStatsEapolFramesTx OBJECT-TYPE
			SYNTAX Counter32
			MAX-ACCESS read-only
			STATUS current
			DESCRIPTION
				"Description"
			::= { sleDot1xStatisticsEntry 3 }

		
		-- 1.3.6.1.4.1.6296.101.7.7.1.1.4
		sleDot1xStatsEapolStartFramesRx OBJECT-TYPE
			SYNTAX Counter32
			MAX-ACCESS read-only
			STATUS current
			DESCRIPTION
				"Description"
			::= { sleDot1xStatisticsEntry 4 }

		
		-- 1.3.6.1.4.1.6296.101.7.7.1.1.5
		sleDot1xStatsEapolLogoffFramesRx OBJECT-TYPE
			SYNTAX Counter32
			MAX-ACCESS read-only
			STATUS current
			DESCRIPTION
				"Description"
			::= { sleDot1xStatisticsEntry 5 }

		
		-- 1.3.6.1.4.1.6296.101.7.7.1.1.6
		sleDot1xStatsEapolRespIdFramesRx OBJECT-TYPE
			SYNTAX Counter32
			MAX-ACCESS read-only
			STATUS current
			DESCRIPTION
				"Description"
			::= { sleDot1xStatisticsEntry 6 }

		
		-- 1.3.6.1.4.1.6296.101.7.7.1.1.7
		sleDot1xStatsEapolRespFramesRx OBJECT-TYPE
			SYNTAX Counter32
			MAX-ACCESS read-only
			STATUS current
			DESCRIPTION
				"Description"
			::= { sleDot1xStatisticsEntry 7 }

		
		-- 1.3.6.1.4.1.6296.101.7.7.1.1.8
		sleDot1xStatsEapolReqIdFramesTx OBJECT-TYPE
			SYNTAX Counter32
			MAX-ACCESS read-only
			STATUS current
			DESCRIPTION
				"Description"
			::= { sleDot1xStatisticsEntry 8 }

		
		-- 1.3.6.1.4.1.6296.101.7.7.1.1.9
		sleDot1xStatsEapolReqFramesTx OBJECT-TYPE
			SYNTAX Integer32
			MAX-ACCESS read-only
			STATUS current
			DESCRIPTION
				"Description"
			::= { sleDot1xStatisticsEntry 9 }

		
		-- 1.3.6.1.4.1.6296.101.7.7.1.1.10
		sleDot1xStatsInvalidEapolFramesRx OBJECT-TYPE
			SYNTAX Counter32
			MAX-ACCESS read-only
			STATUS current
			DESCRIPTION
				"Description"
			::= { sleDot1xStatisticsEntry 10 }

		
		-- 1.3.6.1.4.1.6296.101.7.7.1.1.11
		sleDot1xStatsEapLengthErrorFramesRx OBJECT-TYPE
			SYNTAX Counter32
			MAX-ACCESS read-only
			STATUS current
			DESCRIPTION
				"Description"
			::= { sleDot1xStatisticsEntry 11 }

		
		-- 1.3.6.1.4.1.6296.101.7.7.1.1.12
		sleDot1xStatsLastEapolFrameVersion OBJECT-TYPE
			SYNTAX Counter32
			MAX-ACCESS read-only
			STATUS current
			DESCRIPTION
				"Description"
			::= { sleDot1xStatisticsEntry 12 }

		
		-- 1.3.6.1.4.1.6296.101.7.7.1.1.13
		sleDot1xStatsLastEapolFrameSource OBJECT-TYPE
			SYNTAX MacAddress
			MAX-ACCESS read-only
			STATUS current
			DESCRIPTION
				"Description"
			::= { sleDot1xStatisticsEntry 13 }

		
		-- 1.3.6.1.4.1.6296.101.7.7.2
		sleDot1xStatisticsControl OBJECT IDENTIFIER ::= { sleDot1xStatistics 2 }

		
		-- 1.3.6.1.4.1.6296.101.7.7.2.1
		sleDot1xStatsControlRequest OBJECT-TYPE
			SYNTAX INTEGER { clearDot1xStatistics(1) }
			MAX-ACCESS read-write
			STATUS current
			DESCRIPTION
				"Description"
			::= { sleDot1xStatisticsControl 1 }

		
		-- 1.3.6.1.4.1.6296.101.7.7.2.2
		sleDot1xStatsControlStatus OBJECT-TYPE
			SYNTAX SleControlStatusType
			MAX-ACCESS read-only
			STATUS current
			DESCRIPTION
				"Description"
			::= { sleDot1xStatisticsControl 2 }

		
		-- 1.3.6.1.4.1.6296.101.7.7.2.3
		sleDot1xStatsControlTimer OBJECT-TYPE
			SYNTAX Gauge32
			MAX-ACCESS read-write
			STATUS current
			DESCRIPTION
				"Description"
			::= { sleDot1xStatisticsControl 3 }

		
		-- 1.3.6.1.4.1.6296.101.7.7.2.4
		sleDot1xStatsControlTimeStamp OBJECT-TYPE
			SYNTAX TimeTicks
			MAX-ACCESS read-only
			STATUS current
			DESCRIPTION
				"Description"
			::= { sleDot1xStatisticsControl 4 }

		
		-- 1.3.6.1.4.1.6296.101.7.7.2.5
		sleDot1xStatsControlReqResult OBJECT-TYPE
			SYNTAX SleControlRequestResultType
			MAX-ACCESS read-only
			STATUS current
			DESCRIPTION
				"Description"
			::= { sleDot1xStatisticsControl 5 }

		
		-- 1.3.6.1.4.1.6296.101.7.7.2.6
		sleDot1xStatsControlPortIndex OBJECT-TYPE
			SYNTAX Unsigned32 (1..255)
			MAX-ACCESS read-write
			STATUS current
			DESCRIPTION
				"Description"
			::= { sleDot1xStatisticsControl 6 }

		
		-- 1.3.6.1.4.1.6296.101.7.7.3
		sleDot1xStatisticsNotification OBJECT IDENTIFIER ::= { sleDot1xStatistics 3 }

		
		-- 1.3.6.1.4.1.6296.101.7.7.3.1
		sleDot1xStatisticsCleared NOTIFICATION-TYPE
			OBJECTS { sleDot1xStatsControlRequest, sleDot1xStatsControlTimeStamp, sleDot1xStatsControlReqResult, sleDot1xStatsControlPortIndex }
			STATUS current
			DESCRIPTION 
				"Description"
			::= { sleDot1xStatisticsNotification 1 }

		
		-- 1.3.6.1.4.1.6296.101.7.8
		sleArpInspection OBJECT IDENTIFIER ::= { sleSecurity 8 }

		
		-- 1.3.6.1.4.1.6296.101.7.8.1
		sleArpInspectBase OBJECT IDENTIFIER ::= { sleArpInspection 1 }

		
		-- 1.3.6.1.4.1.6296.101.7.8.1.1
		sleArpInspectBaseInfo OBJECT IDENTIFIER ::= { sleArpInspectBase 1 }

		
		-- 1.3.6.1.4.1.6296.101.7.8.1.1.1
		sleArpInspectValidateSrcMac OBJECT-TYPE
			SYNTAX INTEGER
				{
				disable(0),
				enable(1)
				}
			MAX-ACCESS read-only
			STATUS current
			DESCRIPTION
				"Validate Source Mac"
			::= { sleArpInspectBaseInfo 1 }

		
		-- 1.3.6.1.4.1.6296.101.7.8.1.1.2
		sleArpInspectValidateDstMac OBJECT-TYPE
			SYNTAX INTEGER
				{
				disable(0),
				enable(1)
				}
			MAX-ACCESS read-only
			STATUS current
			DESCRIPTION
				"Validate Destination Mac"
			::= { sleArpInspectBaseInfo 2 }

		
		-- 1.3.6.1.4.1.6296.101.7.8.1.1.3
		sleArpInspectValidateIpAddr OBJECT-TYPE
			SYNTAX INTEGER
				{
				disable(0),
				enable(1)
				}
			MAX-ACCESS read-only
			STATUS current
			DESCRIPTION
				"Validate IP Address"
			::= { sleArpInspectBaseInfo 3 }

		
		-- 1.3.6.1.4.1.6296.101.7.8.1.1.4
		sleArpInspectLogBufferSize OBJECT-TYPE
			SYNTAX Integer32 (0..1024)
			MAX-ACCESS read-only
			STATUS current
			DESCRIPTION
				"Description."
			::= { sleArpInspectBaseInfo 4 }

		
		-- 1.3.6.1.4.1.6296.101.7.8.1.1.5
		sleArpInspectLogEntry OBJECT-TYPE
			SYNTAX Integer32 (0..1024)
			MAX-ACCESS read-only
			STATUS current
			DESCRIPTION
				"Description."
			::= { sleArpInspectBaseInfo 5 }

		
		-- 1.3.6.1.4.1.6296.101.7.8.1.1.6
		sleArpInspectLogInterval OBJECT-TYPE
			SYNTAX Integer32 (0..86400)
			MAX-ACCESS read-only
			STATUS current
			DESCRIPTION
				"Description."
			::= { sleArpInspectBaseInfo 6 }

		
		-- 1.3.6.1.4.1.6296.101.7.8.1.2
		sleArpInspectBaseControl OBJECT IDENTIFIER ::= { sleArpInspectBase 2 }

		
		-- 1.3.6.1.4.1.6296.101.7.8.1.2.1
		sleArpInspectControlRequest OBJECT-TYPE
			SYNTAX INTEGER
				{
				setArpInspectValidateProfile(1),
				setArpInspectLogBufferSize(2),
				setArpInspectLogRate(3)
				}
			MAX-ACCESS read-write
			STATUS current
			DESCRIPTION
				"Description"
			::= { sleArpInspectBaseControl 1 }

		
		-- 1.3.6.1.4.1.6296.101.7.8.1.2.2
		sleArpInspectControlStatus OBJECT-TYPE
			SYNTAX SleControlStatusType
			MAX-ACCESS read-only
			STATUS current
			DESCRIPTION
				"Description"
			::= { sleArpInspectBaseControl 2 }

		
		-- 1.3.6.1.4.1.6296.101.7.8.1.2.3
		sleArpInspectControlTimer OBJECT-TYPE
			SYNTAX Gauge32
			MAX-ACCESS read-write
			STATUS current
			DESCRIPTION
				"Description"
			::= { sleArpInspectBaseControl 3 }

		
		-- 1.3.6.1.4.1.6296.101.7.8.1.2.4
		sleArpInspectControlTimeStamp OBJECT-TYPE
			SYNTAX TimeTicks
			MAX-ACCESS read-only
			STATUS current
			DESCRIPTION
				"Description"
			::= { sleArpInspectBaseControl 4 }

		
		-- 1.3.6.1.4.1.6296.101.7.8.1.2.5
		sleArpInspectControlReqResult OBJECT-TYPE
			SYNTAX SleControlRequestResultType
			MAX-ACCESS read-only
			STATUS current
			DESCRIPTION
				"Result of the last command."
			::= { sleArpInspectBaseControl 5 }

		
		-- 1.3.6.1.4.1.6296.101.7.8.1.2.6
		sleArpInspectControlValidateSrcMac OBJECT-TYPE
			SYNTAX INTEGER
				{
				disable(0),
				enable(1)
				}
			MAX-ACCESS read-write
			STATUS current
			DESCRIPTION
				"Description."
			::= { sleArpInspectBaseControl 6 }

		
		-- 1.3.6.1.4.1.6296.101.7.8.1.2.7
		sleArpInspectControlValidateDstMac OBJECT-TYPE
			SYNTAX INTEGER
				{
				disable(0),
				enable(1)
				}
			MAX-ACCESS read-write
			STATUS current
			DESCRIPTION
				"Description."
			::= { sleArpInspectBaseControl 7 }

		
		-- 1.3.6.1.4.1.6296.101.7.8.1.2.8
		sleArpInspectControlValidateIpAddr OBJECT-TYPE
			SYNTAX INTEGER
				{
				disable(0),
				enable(1)
				}
			MAX-ACCESS read-write
			STATUS current
			DESCRIPTION
				"Description."
			::= { sleArpInspectBaseControl 8 }

		
		-- 1.3.6.1.4.1.6296.101.7.8.1.2.9
		sleArpInspectControlLogBufferSize OBJECT-TYPE
			SYNTAX Integer32 (0..1024)
			MAX-ACCESS read-write
			STATUS current
			DESCRIPTION
				"Description."
			::= { sleArpInspectBaseControl 9 }

		
		-- 1.3.6.1.4.1.6296.101.7.8.1.2.10
		sleArpInspectControlLogEntry OBJECT-TYPE
			SYNTAX Integer32 (0..1024)
			MAX-ACCESS read-write
			STATUS current
			DESCRIPTION
				"Description."
			::= { sleArpInspectBaseControl 10 }

		
		-- 1.3.6.1.4.1.6296.101.7.8.1.2.11
		sleArpInspectControlLogInterval OBJECT-TYPE
			SYNTAX Integer32 (0..86400)
			MAX-ACCESS read-write
			STATUS current
			DESCRIPTION
				"Description."
			::= { sleArpInspectBaseControl 11 }

		
		-- 1.3.6.1.4.1.6296.101.7.8.1.3
		sleArpInspectBaseNotifications OBJECT IDENTIFIER ::= { sleArpInspectBase 3 }

		
		-- 1.3.6.1.4.1.6296.101.7.8.1.3.1
		sleArpInspectValidateChanged NOTIFICATION-TYPE
			OBJECTS { sleArpInspectControlRequest, sleArpInspectControlTimeStamp, sleArpInspectControlReqResult, sleArpInspectControlValidateSrcMac, sleArpInspectControlValidateDstMac, 
				sleArpInspectControlValidateIpAddr }
			STATUS current
			DESCRIPTION 
				"sleArpInspectValidateControl"
			::= { sleArpInspectBaseNotifications 1 }

		
		-- 1.3.6.1.4.1.6296.101.7.8.1.3.2
		sleArpInspectLogBufferSizeChanged NOTIFICATION-TYPE
			OBJECTS { sleArpInspectControlRequest, sleArpInspectControlTimeStamp, sleArpInspectControlReqResult, sleArpInspectControlLogBufferSize }
			STATUS current
			DESCRIPTION 
				"Description."
			::= { sleArpInspectBaseNotifications 2 }

		
		-- 1.3.6.1.4.1.6296.101.7.8.1.3.3
		sleArpInspectLogRateChanged NOTIFICATION-TYPE
			OBJECTS { sleArpInspectControlRequest, sleArpInspectControlTimeStamp, sleArpInspectControlReqResult, sleArpInspectControlLogEntry, sleArpInspectControlLogInterval
				 }
			STATUS current
			DESCRIPTION 
				"Description."
			::= { sleArpInspectBaseNotifications 3 }

		
		-- 1.3.6.1.4.1.6296.101.7.8.2
		sleArpACL OBJECT IDENTIFIER ::= { sleArpInspection 2 }

		
		-- 1.3.6.1.4.1.6296.101.7.8.2.1
		sleArpAclTable OBJECT-TYPE
			SYNTAX SEQUENCE OF SleArpAclEntry
			MAX-ACCESS not-accessible
			STATUS current
			DESCRIPTION
				"Description."
			::= { sleArpACL 1 }

		
		-- 1.3.6.1.4.1.6296.101.7.8.2.1.1
		sleArpAclEntry OBJECT-TYPE
			SYNTAX SleArpAclEntry
			MAX-ACCESS not-accessible
			STATUS current
			DESCRIPTION
				"Description."
			INDEX { sleArpAclIndex }
			::= { sleArpAclTable 1 }

		
		SleArpAclEntry ::=
			SEQUENCE { 
				sleArpAclIndex
					INTEGER,
				sleArpAclName
					OCTET STRING,
				sleArpAclNumEntries
					INTEGER
			 }

		-- 1.3.6.1.4.1.6296.101.7.8.2.1.1.1
		sleArpAclIndex OBJECT-TYPE
			SYNTAX INTEGER (1..2147483647)
			MAX-ACCESS read-only
			STATUS current
			DESCRIPTION
				"Description."
			::= { sleArpAclEntry 1 }

		
		-- 1.3.6.1.4.1.6296.101.7.8.2.1.1.2
		sleArpAclName OBJECT-TYPE
			SYNTAX OCTET STRING (SIZE (1..255))
			MAX-ACCESS read-only
			STATUS current
			DESCRIPTION
				"Description."
			::= { sleArpAclEntry 2 }

		
		-- 1.3.6.1.4.1.6296.101.7.8.2.1.1.3
		sleArpAclNumEntries OBJECT-TYPE
			SYNTAX INTEGER (1..2147483647)
			MAX-ACCESS read-only
			STATUS current
			DESCRIPTION
				"Number of Entries"
			::= { sleArpAclEntry 3 }

		
		-- 1.3.6.1.4.1.6296.101.7.8.2.2
		sleArpAclControl OBJECT IDENTIFIER ::= { sleArpACL 2 }

		
		-- 1.3.6.1.4.1.6296.101.7.8.2.2.1
		sleArpAclControlRequest OBJECT-TYPE
			SYNTAX INTEGER
				{
				createArpAcl(1),
				destroyArpAcl(2)
				}
			MAX-ACCESS read-write
			STATUS current
			DESCRIPTION
				"Description"
			::= { sleArpAclControl 1 }

		
		-- 1.3.6.1.4.1.6296.101.7.8.2.2.2
		sleArpAclControlStatus OBJECT-TYPE
			SYNTAX SleControlStatusType
			MAX-ACCESS read-only
			STATUS current
			DESCRIPTION
				"Description"
			::= { sleArpAclControl 2 }

		
		-- 1.3.6.1.4.1.6296.101.7.8.2.2.3
		sleArpAclControlTimer OBJECT-TYPE
			SYNTAX Gauge32
			MAX-ACCESS read-write
			STATUS current
			DESCRIPTION
				"Description"
			::= { sleArpAclControl 3 }

		
		-- 1.3.6.1.4.1.6296.101.7.8.2.2.4
		sleArpAclControlTimeStamp OBJECT-TYPE
			SYNTAX TimeTicks
			MAX-ACCESS read-only
			STATUS current
			DESCRIPTION
				"Description"
			::= { sleArpAclControl 4 }

		
		-- 1.3.6.1.4.1.6296.101.7.8.2.2.5
		sleArpAclControlReqResult OBJECT-TYPE
			SYNTAX SleControlRequestResultType
			MAX-ACCESS read-only
			STATUS current
			DESCRIPTION
				"Result of the last command."
			::= { sleArpAclControl 5 }

		
		-- 1.3.6.1.4.1.6296.101.7.8.2.2.6
		sleArpAclControlIndex OBJECT-TYPE
			SYNTAX Integer32
			MAX-ACCESS read-write
			STATUS current
			DESCRIPTION
				"Description."
			::= { sleArpAclControl 6 }

		
		-- 1.3.6.1.4.1.6296.101.7.8.2.2.7
		sleArpAclControlName OBJECT-TYPE
			SYNTAX OCTET STRING (SIZE (1..255))
			MAX-ACCESS read-write
			STATUS current
			DESCRIPTION
				"The name of acl."
			::= { sleArpAclControl 7 }

		
		-- 1.3.6.1.4.1.6296.101.7.8.2.3
		sleArpAclNotifications OBJECT IDENTIFIER ::= { sleArpACL 3 }

		
		-- 1.3.6.1.4.1.6296.101.7.8.2.3.1
		sleArpAclCreated NOTIFICATION-TYPE
			OBJECTS { sleArpAclControlRequest, sleArpAclControlTimeStamp, sleArpAclControlReqResult, sleArpAclName }
			STATUS current
			DESCRIPTION 
				"sleArpInspectValidateControl"
			::= { sleArpAclNotifications 1 }

		
		-- 1.3.6.1.4.1.6296.101.7.8.2.3.2
		sleArpAclDestroyed NOTIFICATION-TYPE
			OBJECTS { sleArpAclControlRequest, sleArpAclControlTimeStamp, sleArpAclControlReqResult, sleArpAclControlIndex }
			STATUS current
			DESCRIPTION 
				"sleArpInspectValidateControl"
			::= { sleArpAclNotifications 2 }

		
		-- 1.3.6.1.4.1.6296.101.7.8.3
		sleArpACLRule OBJECT IDENTIFIER ::= { sleArpInspection 3 }

		
		-- 1.3.6.1.4.1.6296.101.7.8.3.1
		sleArpAclRuleTable OBJECT-TYPE
			SYNTAX SEQUENCE OF SleArpAclRuleEntry
			MAX-ACCESS not-accessible
			STATUS current
			DESCRIPTION
				"Description."
			::= { sleArpACLRule 1 }

		
		-- 1.3.6.1.4.1.6296.101.7.8.3.1.1
		sleArpAclRuleEntry OBJECT-TYPE
			SYNTAX SleArpAclRuleEntry
			MAX-ACCESS not-accessible
			STATUS current
			DESCRIPTION
				"Description."
			INDEX { sleArpAclRuleAclIndex, sleArpAclRuleIndex }
			::= { sleArpAclRuleTable 1 }

		
		SleArpAclRuleEntry ::=
			SEQUENCE { 
				sleArpAclRuleAclIndex
					Integer32,
				sleArpAclRuleIndex
					Integer32,
				sleArpAclRuleAction
					INTEGER,
				sleArpAclRuleType
					INTEGER,
				sleArpAclRuleRangeStartIP
					IpAddress,
				sleArpAclRuleRangeEndIP
					IpAddress,
				sleArpAclRuleIPAddress
					IpAddress,
				sleArpAclRuleIPMask
					Integer32,
				sleArpAclRuleMacAddr
					MacAddress,
				sleArpAclRuleMacType
					INTEGER
			 }

		-- 1.3.6.1.4.1.6296.101.7.8.3.1.1.1
		sleArpAclRuleAclIndex OBJECT-TYPE
			SYNTAX Integer32 (1..2147483647)
			MAX-ACCESS read-only
			STATUS current
			DESCRIPTION
				"Description."
			::= { sleArpAclRuleEntry 1 }

		
		-- 1.3.6.1.4.1.6296.101.7.8.3.1.1.2
		sleArpAclRuleIndex OBJECT-TYPE
			SYNTAX Integer32 (1..2147483647)
			MAX-ACCESS read-only
			STATUS current
			DESCRIPTION
				"ACL entry Index"
			::= { sleArpAclRuleEntry 2 }

		
		-- 1.3.6.1.4.1.6296.101.7.8.3.1.1.3
		sleArpAclRuleAction OBJECT-TYPE
			SYNTAX INTEGER
				{
				deny(0),
				permit(1)
				}
			MAX-ACCESS read-only
			STATUS current
			DESCRIPTION
				"The permit/deny control used per entry"
			::= { sleArpAclRuleEntry 3 }

		
		-- 1.3.6.1.4.1.6296.101.7.8.3.1.1.4
		sleArpAclRuleType OBJECT-TYPE
			SYNTAX INTEGER
				{
				subnet(0),
				range(1),
				dhcpSnooping(2)
				}
			MAX-ACCESS read-only
			STATUS current
			DESCRIPTION
				"Specify IP address is host or range."
			::= { sleArpAclRuleEntry 4 }

		
		-- 1.3.6.1.4.1.6296.101.7.8.3.1.1.5
		sleArpAclRuleRangeStartIP OBJECT-TYPE
			SYNTAX IpAddress
			MAX-ACCESS read-only
			STATUS current
			DESCRIPTION
				"Valid if sleArpAclEntryRange is 1,Otherwise this value is invalid."
			::= { sleArpAclRuleEntry 5 }

		
		-- 1.3.6.1.4.1.6296.101.7.8.3.1.1.6
		sleArpAclRuleRangeEndIP OBJECT-TYPE
			SYNTAX IpAddress
			MAX-ACCESS read-only
			STATUS current
			DESCRIPTION
				"Valid if sleArpAclEntryRange is 1,Otherwise this value is invalid."
			::= { sleArpAclRuleEntry 6 }

		
		-- 1.3.6.1.4.1.6296.101.7.8.3.1.1.7
		sleArpAclRuleIPAddress OBJECT-TYPE
			SYNTAX IpAddress
			MAX-ACCESS read-only
			STATUS current
			DESCRIPTION
				"IP Address.Valid if sleArpAclEntryRange is 0."
			::= { sleArpAclRuleEntry 7 }

		
		-- 1.3.6.1.4.1.6296.101.7.8.3.1.1.8
		sleArpAclRuleIPMask OBJECT-TYPE
			SYNTAX Integer32 (1..32)
			MAX-ACCESS read-only
			STATUS current
			DESCRIPTION
				"SubnetMask.Valid if sleArpAclEntryRange is 0."
			::= { sleArpAclRuleEntry 8 }

		
		-- 1.3.6.1.4.1.6296.101.7.8.3.1.1.9
		sleArpAclRuleMacAddr OBJECT-TYPE
			SYNTAX MacAddress
			MAX-ACCESS read-only
			STATUS current
			DESCRIPTION
				"Mac Address. If  sleArpAclEntryMacType is 0 , this value is invalid."
			::= { sleArpAclRuleEntry 9 }

		
		-- 1.3.6.1.4.1.6296.101.7.8.3.1.1.10
		sleArpAclRuleMacType OBJECT-TYPE
			SYNTAX INTEGER
				{
				any(0),
				host(1)
				}
			MAX-ACCESS read-only
			STATUS current
			DESCRIPTION
				"Description."
			::= { sleArpAclRuleEntry 10 }

		
		-- 1.3.6.1.4.1.6296.101.7.8.3.2
		sleArpAclRuleControl OBJECT IDENTIFIER ::= { sleArpACLRule 2 }

		
		-- 1.3.6.1.4.1.6296.101.7.8.3.2.1
		sleArpAclRuleControlRequest OBJECT-TYPE
			SYNTAX INTEGER
				{
				createArpAclRule(1),
				destroyArpAclRule(2)
				}
			MAX-ACCESS read-write
			STATUS current
			DESCRIPTION
				"Description"
			::= { sleArpAclRuleControl 1 }

		
		-- 1.3.6.1.4.1.6296.101.7.8.3.2.2
		sleArpAclRuleControlStatus OBJECT-TYPE
			SYNTAX SleControlStatusType
			MAX-ACCESS read-only
			STATUS current
			DESCRIPTION
				"Description"
			::= { sleArpAclRuleControl 2 }

		
		-- 1.3.6.1.4.1.6296.101.7.8.3.2.3
		sleArpAclRuleControlTimer OBJECT-TYPE
			SYNTAX Gauge32
			MAX-ACCESS read-write
			STATUS current
			DESCRIPTION
				"Description"
			::= { sleArpAclRuleControl 3 }

		
		-- 1.3.6.1.4.1.6296.101.7.8.3.2.4
		sleArpAclRuleControlTimeStamp OBJECT-TYPE
			SYNTAX TimeTicks
			MAX-ACCESS read-only
			STATUS current
			DESCRIPTION
				"Description"
			::= { sleArpAclRuleControl 4 }

		
		-- 1.3.6.1.4.1.6296.101.7.8.3.2.5
		sleArpAclRuleControlReqResult OBJECT-TYPE
			SYNTAX SleControlRequestResultType
			MAX-ACCESS read-only
			STATUS current
			DESCRIPTION
				"Result of the last command."
			::= { sleArpAclRuleControl 5 }

		
		-- 1.3.6.1.4.1.6296.101.7.8.3.2.6
		sleArpAclRuleControlAclIndex OBJECT-TYPE
			SYNTAX Integer32
			MAX-ACCESS read-write
			STATUS current
			DESCRIPTION
				"The name of acl."
			::= { sleArpAclRuleControl 6 }

		
		-- 1.3.6.1.4.1.6296.101.7.8.3.2.7
		sleArpAclRuleControlIndex OBJECT-TYPE
			SYNTAX Integer32
			MAX-ACCESS read-write
			STATUS current
			DESCRIPTION
				"The entry index within ACL"
			::= { sleArpAclRuleControl 7 }

		
		-- 1.3.6.1.4.1.6296.101.7.8.3.2.8
		sleArpAclRuleControlAction OBJECT-TYPE
			SYNTAX INTEGER
				{
				deny(0),
				permit(1)
				}
			MAX-ACCESS read-write
			STATUS current
			DESCRIPTION
				"The permit/deny control used per entry"
			::= { sleArpAclRuleControl 8 }

		
		-- 1.3.6.1.4.1.6296.101.7.8.3.2.9
		sleArpAclRuleControlType OBJECT-TYPE
			SYNTAX INTEGER
				{
				subnet(0),
				range(1),
				dhcpSnooping(2)
				}
			MAX-ACCESS read-write
			STATUS current
			DESCRIPTION
				"If  type of entry is 1, sleArpAclEntryControlType must be 0.
				"
			::= { sleArpAclRuleControl 9 }

		
		-- 1.3.6.1.4.1.6296.101.7.8.3.2.10
		sleArpAclRuleControlRangeStartIP OBJECT-TYPE
			SYNTAX IpAddress
			MAX-ACCESS read-write
			STATUS current
			DESCRIPTION
				"Description"
			::= { sleArpAclRuleControl 10 }

		
		-- 1.3.6.1.4.1.6296.101.7.8.3.2.11
		sleArpAclRuleControlRangeEndIP OBJECT-TYPE
			SYNTAX IpAddress
			MAX-ACCESS read-write
			STATUS current
			DESCRIPTION
				"Description"
			::= { sleArpAclRuleControl 11 }

		
		-- 1.3.6.1.4.1.6296.101.7.8.3.2.12
		sleArpAclRuleControlIPAddress OBJECT-TYPE
			SYNTAX IpAddress
			MAX-ACCESS read-write
			STATUS current
			DESCRIPTION
				"Description"
			::= { sleArpAclRuleControl 12 }

		
		-- 1.3.6.1.4.1.6296.101.7.8.3.2.13
		sleArpAclRuleControlIPMask OBJECT-TYPE
			SYNTAX INTEGER (1..32)
			MAX-ACCESS read-write
			STATUS current
			DESCRIPTION
				"Description"
			::= { sleArpAclRuleControl 13 }

		
		-- 1.3.6.1.4.1.6296.101.7.8.3.2.14
		sleArpAclRuleControlMacAddr OBJECT-TYPE
			SYNTAX MacAddress
			MAX-ACCESS read-write
			STATUS current
			DESCRIPTION
				"Description"
			::= { sleArpAclRuleControl 14 }

		
		-- 1.3.6.1.4.1.6296.101.7.8.3.2.15
		sleArpAclRuleControlMacType OBJECT-TYPE
			SYNTAX INTEGER
				{
				any(0),
				host(1)
				}
			MAX-ACCESS read-write
			STATUS current
			DESCRIPTION
				"Description"
			::= { sleArpAclRuleControl 15 }

		
		-- 1.3.6.1.4.1.6296.101.7.8.3.3
		sleArpAclRuleNotifications OBJECT IDENTIFIER ::= { sleArpACLRule 3 }

		
		-- 1.3.6.1.4.1.6296.101.7.8.3.3.1
		sleArpAclRuleCreated NOTIFICATION-TYPE
			OBJECTS { sleArpAclRuleControlRequest, sleArpAclRuleControlTimeStamp, sleArpAclRuleControlReqResult, sleArpAclRuleAction, sleArpAclRuleType, 
				sleArpAclRuleRangeStartIP, sleArpAclRuleRangeEndIP, sleArpAclRuleIPAddress, sleArpAclRuleIPMask, sleArpAclRuleMacAddr, 
				sleArpAclRuleMacType }
			STATUS current
			DESCRIPTION 
				"createArpAclEntry"
			::= { sleArpAclRuleNotifications 1 }

		
		-- 1.3.6.1.4.1.6296.101.7.8.3.3.2
		sleArpAclRuleDestroyed NOTIFICATION-TYPE
			OBJECTS { sleArpAclRuleControlRequest, sleArpAclRuleControlTimeStamp, sleArpAclRuleControlReqResult, sleArpAclRuleControlAclIndex, sleArpAclRuleControlIndex
				 }
			STATUS current
			DESCRIPTION 
				"destroyArpAclEntry"
			::= { sleArpAclRuleNotifications 2 }

		
		-- 1.3.6.1.4.1.6296.101.7.8.4
		sleArpInspectVlan OBJECT IDENTIFIER ::= { sleArpInspection 4 }

		
		-- 1.3.6.1.4.1.6296.101.7.8.4.1
		sleArpInspectVlanTable OBJECT-TYPE
			SYNTAX SEQUENCE OF SleArpInspectVlanEntry
			MAX-ACCESS not-accessible
			STATUS current
			DESCRIPTION
				"Description."
			::= { sleArpInspectVlan 1 }

		
		-- 1.3.6.1.4.1.6296.101.7.8.4.1.1
		sleArpInspectVlanEntry OBJECT-TYPE
			SYNTAX SleArpInspectVlanEntry
			MAX-ACCESS not-accessible
			STATUS current
			DESCRIPTION
				"Description."
			INDEX { sleArpInspectVlanIndex }
			::= { sleArpInspectVlanTable 1 }

		
		SleArpInspectVlanEntry ::=
			SEQUENCE { 
				sleArpInspectVlanIndex
					Integer32,
				sleArpInspectVlanEnable
					INTEGER,
				sleArpInspectVlanFilterAcl
					Integer32,
				sleArpInspectVlanFwdPktCnt
					Integer32,
				sleArpInspectVlanDropPktCnt
					Integer32,
				sleArpInspectVlanAclPermits
					Integer32,
				sleArpInspectVlanAclDrops
					Integer32,
				sleArpInspectVlanSrcMacFailurs
					Integer32,
				sleArpInspectVlanDstMacFailurs
					Integer32,
				sleArpInspectVlanIpAddrFailurs
					Integer32,
				sleArpInspectVlanFilterAclName
					OCTET STRING
			 }

		-- 1.3.6.1.4.1.6296.101.7.8.4.1.1.1
		sleArpInspectVlanIndex OBJECT-TYPE
			SYNTAX Integer32 (1..4094)
			MAX-ACCESS read-only
			STATUS current
			DESCRIPTION
				"The index of vlan."
			::= { sleArpInspectVlanEntry 1 }

		
		-- 1.3.6.1.4.1.6296.101.7.8.4.1.1.2
		sleArpInspectVlanEnable OBJECT-TYPE
			SYNTAX INTEGER
				{
				disable(0),
				enable(1)
				}
			MAX-ACCESS read-only
			STATUS current
			DESCRIPTION
				"The enable/disable control used per vlan."
			::= { sleArpInspectVlanEntry 2 }

		
		-- 1.3.6.1.4.1.6296.101.7.8.4.1.1.3
		sleArpInspectVlanFilterAcl OBJECT-TYPE
			SYNTAX Integer32
			MAX-ACCESS read-only
			STATUS current
			DESCRIPTION
				"Description."
			::= { sleArpInspectVlanEntry 3 }

		
		-- 1.3.6.1.4.1.6296.101.7.8.4.1.1.4
		sleArpInspectVlanFwdPktCnt OBJECT-TYPE
			SYNTAX Integer32
			MAX-ACCESS read-only
			STATUS current
			DESCRIPTION
				"Forwarded arp packet count."
			::= { sleArpInspectVlanEntry 4 }

		
		-- 1.3.6.1.4.1.6296.101.7.8.4.1.1.5
		sleArpInspectVlanDropPktCnt OBJECT-TYPE
			SYNTAX Integer32
			MAX-ACCESS read-only
			STATUS current
			DESCRIPTION
				"Droped arp packet count."
			::= { sleArpInspectVlanEntry 5 }

		
		-- 1.3.6.1.4.1.6296.101.7.8.4.1.1.6
		sleArpInspectVlanAclPermits OBJECT-TYPE
			SYNTAX Integer32
			MAX-ACCESS read-only
			STATUS current
			DESCRIPTION
				"Description."
			::= { sleArpInspectVlanEntry 6 }

		
		-- 1.3.6.1.4.1.6296.101.7.8.4.1.1.7
		sleArpInspectVlanAclDrops OBJECT-TYPE
			SYNTAX Integer32
			MAX-ACCESS read-only
			STATUS current
			DESCRIPTION
				"Description."
			::= { sleArpInspectVlanEntry 7 }

		
		-- 1.3.6.1.4.1.6296.101.7.8.4.1.1.8
		sleArpInspectVlanSrcMacFailurs OBJECT-TYPE
			SYNTAX Integer32
			MAX-ACCESS read-only
			STATUS current
			DESCRIPTION
				"Description."
			::= { sleArpInspectVlanEntry 8 }

		
		-- 1.3.6.1.4.1.6296.101.7.8.4.1.1.9
		sleArpInspectVlanDstMacFailurs OBJECT-TYPE
			SYNTAX Integer32
			MAX-ACCESS read-only
			STATUS current
			DESCRIPTION
				"Description."
			::= { sleArpInspectVlanEntry 9 }

		
		-- 1.3.6.1.4.1.6296.101.7.8.4.1.1.10
		sleArpInspectVlanIpAddrFailurs OBJECT-TYPE
			SYNTAX Integer32
			MAX-ACCESS read-only
			STATUS current
			DESCRIPTION
				"Description."
			::= { sleArpInspectVlanEntry 10 }

		
		-- 1.3.6.1.4.1.6296.101.7.8.4.1.1.11
		sleArpInspectVlanFilterAclName OBJECT-TYPE
			SYNTAX OCTET STRING (SIZE (1..255))
			MAX-ACCESS read-only
			STATUS current
			DESCRIPTION
				"Description."
			::= { sleArpInspectVlanEntry 11 }

		
		-- 1.3.6.1.4.1.6296.101.7.8.4.2
		sleArpInspectVlanControl OBJECT IDENTIFIER ::= { sleArpInspectVlan 2 }

		
		-- 1.3.6.1.4.1.6296.101.7.8.4.2.1
		sleArpInspectVlanControlRequest OBJECT-TYPE
			SYNTAX INTEGER
				{
				setArpInspectVlanProfile(1),
				clearArpInspectVlanStatistics(2)
				}
			MAX-ACCESS read-write
			STATUS current
			DESCRIPTION
				"Description"
			::= { sleArpInspectVlanControl 1 }

		
		-- 1.3.6.1.4.1.6296.101.7.8.4.2.2
		sleArpInspectVlanControlStatus OBJECT-TYPE
			SYNTAX SleControlStatusType
			MAX-ACCESS read-only
			STATUS current
			DESCRIPTION
				"Description"
			::= { sleArpInspectVlanControl 2 }

		
		-- 1.3.6.1.4.1.6296.101.7.8.4.2.3
		sleArpInspectVlanControlTimer OBJECT-TYPE
			SYNTAX Gauge32
			MAX-ACCESS read-write
			STATUS current
			DESCRIPTION
				"Description"
			::= { sleArpInspectVlanControl 3 }

		
		-- 1.3.6.1.4.1.6296.101.7.8.4.2.4
		sleArpInspectVlanControlTimeStamp OBJECT-TYPE
			SYNTAX TimeTicks
			MAX-ACCESS read-only
			STATUS current
			DESCRIPTION
				"Description"
			::= { sleArpInspectVlanControl 4 }

		
		-- 1.3.6.1.4.1.6296.101.7.8.4.2.5
		sleArpInspectVlanControlReqResult OBJECT-TYPE
			SYNTAX SleControlRequestResultType
			MAX-ACCESS read-only
			STATUS current
			DESCRIPTION
				"Result of the last command."
			::= { sleArpInspectVlanControl 5 }

		
		-- 1.3.6.1.4.1.6296.101.7.8.4.2.6
		sleArpInspectVlanControlIndex OBJECT-TYPE
			SYNTAX INTEGER (1..4094)
			MAX-ACCESS read-write
			STATUS current
			DESCRIPTION
				"The index of vlan."
			::= { sleArpInspectVlanControl 6 }

		
		-- 1.3.6.1.4.1.6296.101.7.8.4.2.7
		sleArpInspectVlanControlEnable OBJECT-TYPE
			SYNTAX INTEGER
				{
				disable(0),
				enable(1)
				}
			MAX-ACCESS read-write
			STATUS current
			DESCRIPTION
				"The enable/disable control used per vlan."
			::= { sleArpInspectVlanControl 7 }

		
		-- 1.3.6.1.4.1.6296.101.7.8.4.2.8
		sleArpInspectVlanControlFilterAcl OBJECT-TYPE
			SYNTAX Integer32
			MAX-ACCESS read-write
			STATUS current
			DESCRIPTION
				"The ARP Access-list Name to be applied to vlan"
			::= { sleArpInspectVlanControl 8 }

		
		-- 1.3.6.1.4.1.6296.101.7.8.4.3
		sleArpInspectVlanNotifications OBJECT IDENTIFIER ::= { sleArpInspectVlan 3 }

		
		-- 1.3.6.1.4.1.6296.101.7.8.4.3.1
		sleArpInspectVlanChanged NOTIFICATION-TYPE
			OBJECTS { sleArpInspectVlanControlRequest, sleArpInspectVlanControlTimeStamp, sleArpInspectVlanControlReqResult, sleArpInspectVlanEnable, sleArpInspectVlanFilterAcl
				 }
			STATUS current
			DESCRIPTION 
				"setArpInspectVlanProfile"
			::= { sleArpInspectVlanNotifications 1 }

		
		-- 1.3.6.1.4.1.6296.101.7.8.5
		sleArpInspectPort OBJECT IDENTIFIER ::= { sleArpInspection 5 }

		
		-- 1.3.6.1.4.1.6296.101.7.8.5.1
		sleArpInspectPortTable OBJECT-TYPE
			SYNTAX SEQUENCE OF SleArpInspectPortEntry
			MAX-ACCESS not-accessible
			STATUS current
			DESCRIPTION
				"Description."
			::= { sleArpInspectPort 1 }

		
		-- 1.3.6.1.4.1.6296.101.7.8.5.1.1
		sleArpInspectPortEntry OBJECT-TYPE
			SYNTAX SleArpInspectPortEntry
			MAX-ACCESS not-accessible
			STATUS current
			DESCRIPTION
				"Description."
			INDEX { sleArpInspectPortIndex }
			::= { sleArpInspectPortTable 1 }

		
		SleArpInspectPortEntry ::=
			SEQUENCE { 
				sleArpInspectPortIndex
					Integer32,
				sleArpInspectPortTrust
					INTEGER
			 }

		-- 1.3.6.1.4.1.6296.101.7.8.5.1.1.1
		sleArpInspectPortIndex OBJECT-TYPE
			SYNTAX Integer32 (1..255)
			MAX-ACCESS read-only
			STATUS current
			DESCRIPTION
				"The index of port."
			::= { sleArpInspectPortEntry 1 }

		
		-- 1.3.6.1.4.1.6296.101.7.8.5.1.1.2
		sleArpInspectPortTrust OBJECT-TYPE
			SYNTAX INTEGER
				{
				untrust(0),
				trust(1)
				}
			MAX-ACCESS read-only
			STATUS current
			DESCRIPTION
				"The trust/untrust control used per port."
			::= { sleArpInspectPortEntry 2 }

		
		-- 1.3.6.1.4.1.6296.101.7.8.5.2
		sleArpInspectPortControl OBJECT IDENTIFIER ::= { sleArpInspectPort 2 }

		
		-- 1.3.6.1.4.1.6296.101.7.8.5.2.1
		sleArpInspectPortControlRequest OBJECT-TYPE
			SYNTAX INTEGER { setArpInspectTrustPort(1) }
			MAX-ACCESS read-write
			STATUS current
			DESCRIPTION
				"Description"
			::= { sleArpInspectPortControl 1 }

		
		-- 1.3.6.1.4.1.6296.101.7.8.5.2.2
		sleArpInspectPortControlStatus OBJECT-TYPE
			SYNTAX SleControlStatusType
			MAX-ACCESS read-only
			STATUS current
			DESCRIPTION
				"Description"
			::= { sleArpInspectPortControl 2 }

		
		-- 1.3.6.1.4.1.6296.101.7.8.5.2.3
		sleArpInspectPortControlTimer OBJECT-TYPE
			SYNTAX Gauge32
			MAX-ACCESS read-write
			STATUS current
			DESCRIPTION
				"Description"
			::= { sleArpInspectPortControl 3 }

		
		-- 1.3.6.1.4.1.6296.101.7.8.5.2.4
		sleArpInspectPortControlTimeStamp OBJECT-TYPE
			SYNTAX TimeTicks
			MAX-ACCESS read-only
			STATUS current
			DESCRIPTION
				"Description"
			::= { sleArpInspectPortControl 4 }

		
		-- 1.3.6.1.4.1.6296.101.7.8.5.2.5
		sleArpInspectPortControlReqResult OBJECT-TYPE
			SYNTAX SleControlRequestResultType
			MAX-ACCESS read-only
			STATUS current
			DESCRIPTION
				"Result of the last command."
			::= { sleArpInspectPortControl 5 }

		
		-- 1.3.6.1.4.1.6296.101.7.8.5.2.6
		sleArpInspectPortControlIndex OBJECT-TYPE
			SYNTAX INTEGER (1..255)
			MAX-ACCESS read-write
			STATUS current
			DESCRIPTION
				"The index of port."
			::= { sleArpInspectPortControl 6 }

		
		-- 1.3.6.1.4.1.6296.101.7.8.5.2.7
		sleArpInspectPortControlTrust OBJECT-TYPE
			SYNTAX INTEGER
				{
				untrust(0),
				trust(1)
				}
			MAX-ACCESS read-write
			STATUS current
			DESCRIPTION
				"The enable/disable control used per port"
			::= { sleArpInspectPortControl 7 }

		
		-- 1.3.6.1.4.1.6296.101.7.8.5.3
		sleArpInspectPortNotifications OBJECT IDENTIFIER ::= { sleArpInspectPort 3 }

		
		-- 1.3.6.1.4.1.6296.101.7.8.5.3.1
		sleArpInspectPortChanged NOTIFICATION-TYPE
			OBJECTS { sleArpInspectPortControlRequest, sleArpInspectPortControlTimeStamp, sleArpInspectPortControlTrust, sleArpInspectPortControlReqResult }
			STATUS current
			DESCRIPTION 
				"setArpInspectTrustPort"
			::= { sleArpInspectPortNotifications 1 }

		
		-- 1.3.6.1.4.1.6296.101.7.8.6
		sleArpInspectInvalidLog OBJECT IDENTIFIER ::= { sleArpInspection 6 }

		
		-- 1.3.6.1.4.1.6296.101.7.8.6.1
		sleArpInspectInvalidLogTable OBJECT-TYPE
			SYNTAX SEQUENCE OF SleArpInspectInvalidLogEntry
			MAX-ACCESS not-accessible
			STATUS current
			DESCRIPTION
				"Description."
			::= { sleArpInspectInvalidLog 1 }

		
		-- 1.3.6.1.4.1.6296.101.7.8.6.1.1
		sleArpInspectInvalidLogEntry OBJECT-TYPE
			SYNTAX SleArpInspectInvalidLogEntry
			MAX-ACCESS not-accessible
			STATUS current
			DESCRIPTION
				"Description."
			INDEX { sleArpInspectInvalidLogId }
			::= { sleArpInspectInvalidLogTable 1 }

		
		SleArpInspectInvalidLogEntry ::=
			SEQUENCE { 
				sleArpInspectInvalidLogId
					INTEGER,
				sleArpInspectInvalidLogReason
					INTEGER,
				sleArpInspectInvalidLogSamePktCnt
					Counter32,
				sleArpInspectInvalidLogOpcode
					INTEGER,
				sleArpInspectInvalidLogPortNumber
					INTEGER,
				sleArpInspectInvalidLogVlanId
					INTEGER,
				sleArpInspectInvalidLogSrcMacAddr
					OCTET STRING,
				sleArpInspectInvalidLogSrcIpAddr
					IpAddress,
				sleArpInspectInvalidLogDstMacAddr
					OCTET STRING,
				sleArpInspectInvalidLogDstIpAddr
					IpAddress,
				sleArpInspectInvalidLogLastRecvTime
					OCTET STRING
			 }

		-- 1.3.6.1.4.1.6296.101.7.8.6.1.1.1
		sleArpInspectInvalidLogId OBJECT-TYPE
			SYNTAX INTEGER
			MAX-ACCESS read-only
			STATUS current
			DESCRIPTION
				"ARP inspection invalid index."
			::= { sleArpInspectInvalidLogEntry 1 }

		
		-- 1.3.6.1.4.1.6296.101.7.8.6.1.1.2
		sleArpInspectInvalidLogReason OBJECT-TYPE
			SYNTAX INTEGER
				{
				ali_reason_none(0),
				ali_reason_dhcp_permit(1),
				ali_reason_dhcp_deny(2),
				ali_reason_acl_permit(3),
				ali_reason_acl_deny(4),
				ali_reason_valid_srcfail(5),
				ali_reason_valid_dstfail(6),
				ali_reason_valid_ipfail(7)
				}
			MAX-ACCESS read-only
			STATUS current
			DESCRIPTION
				"ARP inspection invalid reason."
			::= { sleArpInspectInvalidLogEntry 2 }

		
		-- 1.3.6.1.4.1.6296.101.7.8.6.1.1.3
		sleArpInspectInvalidLogSamePktCnt OBJECT-TYPE
			SYNTAX Counter32
			MAX-ACCESS read-only
			STATUS current
			DESCRIPTION
				"ARP inspection invalid same packet counters."
			::= { sleArpInspectInvalidLogEntry 3 }

		
		-- 1.3.6.1.4.1.6296.101.7.8.6.1.1.4
		sleArpInspectInvalidLogOpcode OBJECT-TYPE
			SYNTAX INTEGER
				{
				arpop_request(1),
				arpop_reply(2)
				}
			MAX-ACCESS read-only
			STATUS current
			DESCRIPTION
				"ARP protocol opcodes."
			::= { sleArpInspectInvalidLogEntry 4 }

		
		-- 1.3.6.1.4.1.6296.101.7.8.6.1.1.5
		sleArpInspectInvalidLogPortNumber OBJECT-TYPE
			SYNTAX INTEGER
			MAX-ACCESS read-only
			STATUS current
			DESCRIPTION
				"ARP inspection invalid port number."
			::= { sleArpInspectInvalidLogEntry 5 }

		
		-- 1.3.6.1.4.1.6296.101.7.8.6.1.1.6
		sleArpInspectInvalidLogVlanId OBJECT-TYPE
			SYNTAX INTEGER
			MAX-ACCESS read-only
			STATUS current
			DESCRIPTION
				"ARP inspection invalid vlan id."
			::= { sleArpInspectInvalidLogEntry 6 }

		
		-- 1.3.6.1.4.1.6296.101.7.8.6.1.1.7
		sleArpInspectInvalidLogSrcMacAddr OBJECT-TYPE
			SYNTAX OCTET STRING (SIZE (0..6))
			MAX-ACCESS read-only
			STATUS current
			DESCRIPTION
				"ARP inspection invalid source mac address."
			::= { sleArpInspectInvalidLogEntry 7 }

		
		-- 1.3.6.1.4.1.6296.101.7.8.6.1.1.8
		sleArpInspectInvalidLogSrcIpAddr OBJECT-TYPE
			SYNTAX IpAddress
			MAX-ACCESS read-only
			STATUS current
			DESCRIPTION
				"ARP inspection invalid source IP address."
			::= { sleArpInspectInvalidLogEntry 8 }

		
		-- 1.3.6.1.4.1.6296.101.7.8.6.1.1.9
		sleArpInspectInvalidLogDstMacAddr OBJECT-TYPE
			SYNTAX OCTET STRING (SIZE (0..6))
			MAX-ACCESS read-only
			STATUS current
			DESCRIPTION
				"ARP inspection invalid destination mac address."
			::= { sleArpInspectInvalidLogEntry 9 }

		
		-- 1.3.6.1.4.1.6296.101.7.8.6.1.1.10
		sleArpInspectInvalidLogDstIpAddr OBJECT-TYPE
			SYNTAX IpAddress
			MAX-ACCESS read-only
			STATUS current
			DESCRIPTION
				"ARP inspection invalid destination IP address."
			::= { sleArpInspectInvalidLogEntry 10 }

		
		-- 1.3.6.1.4.1.6296.101.7.8.6.1.1.11
		sleArpInspectInvalidLogLastRecvTime OBJECT-TYPE
			SYNTAX OCTET STRING
			MAX-ACCESS read-only
			STATUS current
			DESCRIPTION
				"ARP inspection invalid packet last received time."
			::= { sleArpInspectInvalidLogEntry 11 }

		
		-- 1.3.6.1.4.1.6296.101.7.9
		sleSecurityGroup OBJECT-GROUP
			OBJECTS { sleArpAclIndex, sleArpAclName, sleArpAclNumEntries, sleArpAclControlRequest, sleArpAclControlStatus, 
				sleArpAclControlTimer, sleArpAclControlTimeStamp, sleArpAclControlReqResult, sleArpAclControlIndex, sleArpAclControlName, 
				sleArpInspectVlanIndex, sleArpInspectVlanEnable, sleArpInspectVlanFilterAcl, sleArpInspectVlanFwdPktCnt, sleArpInspectVlanDropPktCnt, 
				sleArpInspectVlanAclPermits, sleArpInspectVlanAclDrops, sleArpInspectVlanSrcMacFailurs, sleArpInspectVlanDstMacFailurs, sleArpInspectVlanIpAddrFailurs, 
				sleArpInspectVlanControlRequest, sleArpInspectVlanControlStatus, sleArpInspectVlanControlTimer, sleArpInspectVlanControlTimeStamp, sleArpInspectVlanControlReqResult, 
				sleArpInspectVlanControlIndex, sleArpInspectVlanControlEnable, sleArpInspectVlanControlFilterAcl, sleArpInspectPortIndex, sleArpInspectPortTrust, 
				sleArpInspectPortControlRequest, sleArpInspectPortControlStatus, sleArpInspectPortControlTimer, sleArpInspectPortControlTimeStamp, sleArpInspectPortControlReqResult, 
				sleArpInspectPortControlIndex, sleArpInspectPortControlTrust, sleSecurityRadiusRetransmissions, sleSecurityRadiusTimeouts, sleSecurityRadiusInterfaceName, 
				sleSecurityTacacsInterfaceName, sleSecurityTacacsInterfaceAddress, sleSecurityTacacsPort, sleSecurityTacacsAuthType, sleSecurityTacacsTimeouts, 
				sleSecurityTacacsPriorityLevel, sleSecurityDot1xActivity, sleSecurityControlRequest, sleSecurityControlStatus, sleSecurityControlTimer, 
				sleSecurityControlTimeStamp, sleSecurityControlRadiusRetransmissions, sleSecurityControlRadiusTimeouts, sleSecurityControlRadiusInterfaceName, sleSecurityControlRadiusInterfaceAddress, 
				sleSecurityControlTacacsInterfaceName, sleSecurityControlTacacsPort, sleSecurityControlTacacsInterfaceAddress, sleSecurityControlTacacsAuthType, sleSecurityControlTacacsTimeouts, 
				sleSecurityControlTacacsPriorityLevel, sleSecurityControlDot1xActivity, sleSecurityControlReqResult, sleAaaAuthen, sleAaaSession, 
				sleAaaPrimarySequence, sleArpInspectValidateDstMac, sleArpInspectValidateSrcMac, sleArpInspectValidateIpAddr, sleAaaControlStatus, 
				sleSecurityRadiusInterfaceAddress, sleAaaEnable, sleAaaControlRequest, sleAaaControlTimer, sleAaaControlTimeStamp, 
				sleAaaControlReqResult, sleAaaControlSession, sleAaaControlAuthen, sleAaaControlEnable, sleAaaControlPrimaryFlag, 
				sleRadiusServerAddress, sleRadiusServerClientKey, sleRadiusServerAuthPort, sleRadiusServerAccPort, sleRadiusServerMode, 
				sleRadiusServerControlRequest, sleRadiusServerControlStatus, sleRadiusServerControlTimer, sleRadiusServerControlTimeStamp, sleRadiusServerControlReqResult, 
				sleRadiusServerControlAddress, sleRadiusServerControlClientKey, sleRadiusServerControlAuthPort, sleRadiusServerControlAccPort, sleRadiusServerControlMode, 
				sleTacacsServerAddress, sleTacacsServerClientKey, sleTacacsServerControlRequest, sleTacacsServerControlStatus, sleTacacsServerControlTimer, 
				sleTacacsServerControlTimeStamp, sleTacacsServerControlReqResult, sleTacacsServerControlAddress, sleTacacsServerControlClientKey, sleAclName, 
				sleAclSrcIpAddr, sleAclSrcPrefixLength, sleAclDstIpAddr, sleAclDstPrefixLength, sleAclDscp, 
				sleAclProtocolType, sleAclTcpFlag, sleAclSrcL4Port, sleAclDstL4Port, sleAclPktLen, 
				sleAclValidFlags, sleAclMatchFlags, sleAclMatchAction, sleAclNomatchAction, sleAclPriority, 
				sleAclControlReqest, sleAclControlStatus, sleAclControlTimer, sleAclControlTimeStamp, sleAclControlReqResult, 
				sleAclControlName, sleAclControlSrcIpAddr, sleAclControlSrcPrefixLength, sleAclControlDstIpAddr, sleAclControlDstPrefixLength, 
				sleAclControlDscp, sleAclControlProtocolType, sleAclControlTcpFlag, sleAclControlSrcL4Port, sleAclControlDstL4Port, 
				sleAclControlPktLen, sleAclControlValidFlags, sleAclControlMatchFlags, sleAclControlMatchAction, sleAclControlNomatchAction, 
				sleAclControlPriority, sleDot1xPortIndex, sleDot1xPortEnable, sleDot1xPortMode, sleDot1xPortReauthEnable, 
				sleDot1xPortQuietPeriod, sleDot1xPortReauthPeriod, sleDot1xPortAuthSuccess, sleDot1xPortControlRequest, sleDot1xPortControlStatus, 
				sleDot1xPortControlTimer, sleDot1xPortControlTimeStamp, sleDot1xPortControlReqResult, sleDot1xPortControlIndex, sleDot1xPortControlEnable, 
				sleDot1xPortControlMode, sleDot1xPortControlReauthEnable, sleDot1xPortControlQuietPeriod, sleDot1xPortControlReauthPeriod, sleDot1xStatsPortIndex, 
				sleDot1xStatsEapolFramesRx, sleDot1xStatsEapolFramesTx, sleDot1xStatsEapolStartFramesRx, sleDot1xStatsEapolLogoffFramesRx, sleDot1xStatsEapolRespIdFramesRx, 
				sleDot1xStatsEapolRespFramesRx, sleDot1xStatsEapolReqIdFramesTx, sleDot1xStatsEapolReqFramesTx, sleDot1xStatsInvalidEapolFramesRx, sleDot1xStatsEapLengthErrorFramesRx, 
				sleDot1xStatsLastEapolFrameVersion, sleDot1xStatsLastEapolFrameSource, sleDot1xStatsControlRequest, sleDot1xStatsControlStatus, sleDot1xStatsControlTimer, 
				sleDot1xStatsControlTimeStamp, sleDot1xStatsControlReqResult, sleDot1xStatsControlPortIndex, sleArpInspectControlRequest, sleArpInspectControlStatus, 
				sleArpInspectControlTimer, sleArpInspectControlTimeStamp, sleArpInspectControlReqResult, sleArpInspectControlValidateSrcMac, sleArpInspectControlValidateDstMac, 
				sleArpInspectControlValidateIpAddr, sleArpAclRuleAclIndex, sleArpAclRuleIndex, sleArpAclRuleAction, sleArpAclRuleType, 
				sleArpAclRuleRangeStartIP, sleArpAclRuleRangeEndIP, sleArpAclRuleIPAddress, sleArpAclRuleIPMask, sleArpAclRuleMacAddr, 
				sleArpAclRuleMacType, sleArpAclRuleControlRequest, sleArpAclRuleControlStatus, sleArpAclRuleControlTimer, sleArpAclRuleControlTimeStamp, 
				sleArpAclRuleControlReqResult, sleArpAclRuleControlAclIndex, sleArpAclRuleControlIndex, sleArpAclRuleControlAction, sleArpAclRuleControlType, 
				sleArpAclRuleControlRangeStartIP, sleArpAclRuleControlRangeEndIP, sleArpAclRuleControlIPAddress, sleArpAclRuleControlIPMask, sleArpAclRuleControlMacAddr, 
				sleArpAclRuleControlMacType }
			STATUS current
			DESCRIPTION 
				"Description."
			::= { sleSecurity 9 }

		
		-- 1.3.6.1.4.1.6296.101.7.10
		sleSecurityNotificationGroup NOTIFICATION-GROUP
			NOTIFICATIONS { sleArpAclCreated, sleArpAclDestroyed, sleArpInspectVlanChanged, sleArpInspectPortChanged, sleSecurityRadiusProfileChanged, 
				sleSecurityTacacsProfileChanged, sleSecurityDot1xActivityChanged, sleAaaProfileChanged, sleRadiusServerCreated, sleRadiusServerDestroyed, 
				sleRadiusServerProfileChanged, sleTacacsServerCreated, sleTacacsServerDestroyed, sleTacacsServerClientKeyChanged, sleAclCreated, 
				sleAclDestroyed, sleAclClassifierProfileChanged, sleAclMatchActionChanged, sleAclNomatchActionChanged, sleDot1xPortProfileChanged, 
				sleDot1xPortAuthSuccessChanged, sleDot1xStatisticsCleared, sleArpInspectValidateChanged, sleArpAclRuleCreated, sleArpAclRuleDestroyed
				 }
			STATUS current
			DESCRIPTION 
				"Description."
			::= { sleSecurity 10 }

		
	
	END

--
-- SLE-SECURITY-MIB.my
--
