--
-- SLE-DEVICE-MIB.my
-- MIB generated by MG-SOFT Visual MIB Builder Version 6.0  Build 88
-- Tuesday, March 31, 2009 at 14:28:49
--

	SLE-DEVICE-MIB DEFINITIONS ::= BEGIN
 
		IMPORTS
			sleMgmt			
				FROM DASAN-SMI			
			SleControlStatusType, SleControlRequestResultType			
				FROM SLE-TC-MIB			
			OBJECT-GROUP, NOTIFICATION-GROUP			
				FROM SNMPv2-CONF			
			TimeTicks, IpAddress, Integer32, Gauge32, OBJECT-TYPE, 
			MODULE-IDENTITY, NOTIFICATION-TYPE			
				FROM SNMPv2-SMI;
	
	
		-- 1.3.6.1.4.1.6296.101.2
		sleDevice MODULE-IDENTITY 
			LAST-UPDATED "200412100852Z"		-- December 10, 2004 at 08:52 GMT
			ORGANIZATION 
				"Organization."
			CONTACT-INFO 
				"Contact-info."
			DESCRIPTION 
				"Description."
			::= { sleMgmt 2 }

		
	
	
--
-- Node definitions
--
	
		-- 1.3.6.1.4.1.6296.101.2.1
		sleDeviceBase OBJECT IDENTIFIER ::= { sleDevice 1 }

		
		-- 1.3.6.1.4.1.6296.101.2.1.1
		sleDeviceBaseInfo OBJECT IDENTIFIER ::= { sleDeviceBase 1 }

		
		-- 1.3.6.1.4.1.6296.101.2.1.1.1
		sleDeviceEthernetPortNum OBJECT-TYPE
			SYNTAX Integer32
			MAX-ACCESS read-only
			STATUS current
			DESCRIPTION
				"The number of ethernet port."
			::= { sleDeviceBaseInfo 1 }

		
		-- 1.3.6.1.4.1.6296.101.2.1.1.2
		sleDevicePowerNum OBJECT-TYPE
			SYNTAX Integer32
			MAX-ACCESS read-only
			STATUS current
			DESCRIPTION
				"The number of power module"
			::= { sleDeviceBaseInfo 2 }

		
		-- 1.3.6.1.4.1.6296.101.2.1.1.3
		sleDeviceFanModuleNum OBJECT-TYPE
			SYNTAX Integer32
			MAX-ACCESS read-only
			STATUS current
			DESCRIPTION
				"The number of FAN module"
			::= { sleDeviceBaseInfo 3 }

		
		-- 1.3.6.1.4.1.6296.101.2.1.1.4
		sleDeviceTemperatureNum OBJECT-TYPE
			SYNTAX Integer32
			MAX-ACCESS read-only
			STATUS current
			DESCRIPTION
				"The number of temperature sensor"
			::= { sleDeviceBaseInfo 4 }

		
		-- 1.3.6.1.4.1.6296.101.2.1.1.5
		sleDeviceFanStartTemperature OBJECT-TYPE
			SYNTAX Integer32
			MAX-ACCESS read-only
			STATUS current
			DESCRIPTION
				"The temperature value which begins to turn fan."
			::= { sleDeviceBaseInfo 5 }

		
		-- 1.3.6.1.4.1.6296.101.2.1.1.6
		sleDeviceFanStopTemperature OBJECT-TYPE
			SYNTAX Integer32
			MAX-ACCESS read-only
			STATUS current
			DESCRIPTION
				"The temperature value which stops fan."
			::= { sleDeviceBaseInfo 6 }

		
		-- 1.3.6.1.4.1.6296.101.2.1.2
		sleDeviceBaseControl OBJECT IDENTIFIER ::= { sleDeviceBase 2 }

		
		-- 1.3.6.1.4.1.6296.101.2.1.2.1
		sleDeviceControlRequest OBJECT-TYPE
			SYNTAX INTEGER { setDeviceTemperatureThreshold(1) }
			MAX-ACCESS read-write
			STATUS current
			DESCRIPTION
				"set an administrative state of FAN module"
			::= { sleDeviceBaseControl 1 }

		
		-- 1.3.6.1.4.1.6296.101.2.1.2.2
		sleDeviceControlStatus OBJECT-TYPE
			SYNTAX SleControlStatusType
			MAX-ACCESS read-only
			STATUS current
			DESCRIPTION
				"Description."
			::= { sleDeviceBaseControl 2 }

		
		-- 1.3.6.1.4.1.6296.101.2.1.2.3
		sleDeviceControlTimer OBJECT-TYPE
			SYNTAX Gauge32
			MAX-ACCESS read-write
			STATUS current
			DESCRIPTION
				"Description."
			::= { sleDeviceBaseControl 3 }

		
		-- 1.3.6.1.4.1.6296.101.2.1.2.4
		sleDeviceControlTimeStamp OBJECT-TYPE
			SYNTAX TimeTicks
			MAX-ACCESS read-only
			STATUS current
			DESCRIPTION
				"Description."
			::= { sleDeviceBaseControl 4 }

		
		-- 1.3.6.1.4.1.6296.101.2.1.2.5
		sleDeviceControlReqResult OBJECT-TYPE
			SYNTAX SleControlRequestResultType
			MAX-ACCESS read-only
			STATUS current
			DESCRIPTION
				"Description."
			::= { sleDeviceBaseControl 5 }

		
		-- 1.3.6.1.4.1.6296.101.2.1.2.6
		sleDeviceControlFanStartTemperature OBJECT-TYPE
			SYNTAX Integer32
			MAX-ACCESS read-write
			STATUS current
			DESCRIPTION
				"Description."
			::= { sleDeviceBaseControl 6 }

		
		-- 1.3.6.1.4.1.6296.101.2.1.2.7
		sleDeviceControlFanStopTemperature OBJECT-TYPE
			SYNTAX Integer32
			MAX-ACCESS read-write
			STATUS current
			DESCRIPTION
				"Description."
			::= { sleDeviceBaseControl 7 }

		
		-- 1.3.6.1.4.1.6296.101.2.1.3
		sleDeviceBaseNotification OBJECT IDENTIFIER ::= { sleDeviceBase 3 }

		
		-- 1.3.6.1.4.1.6296.101.2.1.3.1
		sleDeviceTemperatureThresholdChanged NOTIFICATION-TYPE
			OBJECTS { sleDeviceFanStartTemperature, sleDeviceFanStopTemperature, sleDeviceControlRequest, sleDeviceControlTimeStamp, sleDeviceControlReqResult
				 }
			STATUS current
			DESCRIPTION 
				"Description."
			::= { sleDeviceBaseNotification 1 }

		
		-- 1.3.6.1.4.1.6296.101.2.2
		sleEthernetPort OBJECT IDENTIFIER ::= { sleDevice 2 }

		
		-- 1.3.6.1.4.1.6296.101.2.2.1
		sleEthernetPortTable OBJECT-TYPE
			SYNTAX SEQUENCE OF SleEthernetPortEntry
			MAX-ACCESS not-accessible
			STATUS current
			DESCRIPTION
				"Description."
			::= { sleEthernetPort 1 }

		
		-- 1.3.6.1.4.1.6296.101.2.2.1.1
		sleEthernetPortEntry OBJECT-TYPE
			SYNTAX SleEthernetPortEntry
			MAX-ACCESS not-accessible
			STATUS current
			DESCRIPTION
				"Description."
			INDEX { sleEthernetPortIndex }
			::= { sleEthernetPortTable 1 }

		
		SleEthernetPortEntry ::=
			SEQUENCE { 
				sleEthernetPortIndex
					INTEGER,
				sleEthernetPortPhyIndex
					Integer32,
				sleEthernetPortType
					INTEGER,
				sleEthernetPortAdminStatus
					INTEGER,
				sleEthernetPortOperStatus
					INTEGER,
				sleEthernetPortTransmissionRate
					Integer32,
				sleEthernetPortDuplexMode
					INTEGER,
				sleEthernetPortFlowControl
					INTEGER,
				sleEthernetPortNegotiationMode
					INTEGER,
				sleEthernetPortJumboFrameSize
					Integer32,
				sleEthernetPortSfpTransceiver
					INTEGER,
				sleEthernetPortSfpVendorName
					OCTET STRING,
				sleEthernetPortSfpVendorPartNumber
					OCTET STRING,
				sleEthernetPortSfpVendorRevision
					OCTET STRING,
				sleEthernetPortSfpVendorSerialNumber
					OCTET STRING,
				sleEthernetPortSfpDateCode
					OCTET STRING,
				sleEthernetPortPhysicalRemoteChassis
					OCTET STRING,
				sleEthernetPortPhysicalRemoteSlot
					Integer32,
				sleEthernetPortPhysicalRemotePort
					Integer32,
				sleEthernetPortPhysicalLinkDiscoveryMode
					INTEGER
			 }

		-- 1.3.6.1.4.1.6296.101.2.2.1.1.1
		sleEthernetPortIndex OBJECT-TYPE
			SYNTAX INTEGER (1..255)
			MAX-ACCESS read-only
			STATUS current
			DESCRIPTION
				"Description."
			::= { sleEthernetPortEntry 1 }

		
		-- 1.3.6.1.4.1.6296.101.2.2.1.1.2
		sleEthernetPortPhyIndex OBJECT-TYPE
			SYNTAX Integer32
			MAX-ACCESS read-only
			STATUS current
			DESCRIPTION
				"Description."
			::= { sleEthernetPortEntry 2 }

		
		-- 1.3.6.1.4.1.6296.101.2.2.1.1.3
		sleEthernetPortType OBJECT-TYPE
			SYNTAX INTEGER
				{
				unknown(0),
				electrical(1),
				optical(2)
				}
			MAX-ACCESS read-only
			STATUS current
			DESCRIPTION
				"Description. The type of port.
				It is not planed to made a automatic switchover between optical and electrical interfaces."
			::= { sleEthernetPortEntry 3 }

		
		-- 1.3.6.1.4.1.6296.101.2.2.1.1.4
		sleEthernetPortAdminStatus OBJECT-TYPE
			SYNTAX INTEGER
				{
				up(1),
				down(2),
				notAvailable(3)
				}
			MAX-ACCESS read-only
			STATUS current
			DESCRIPTION
				"Description."
			::= { sleEthernetPortEntry 4 }

		
		-- 1.3.6.1.4.1.6296.101.2.2.1.1.5
		sleEthernetPortOperStatus OBJECT-TYPE
			SYNTAX INTEGER
				{
				up(1),
				down(2),
				notAvailable(3)
				}
			MAX-ACCESS read-only
			STATUS current
			DESCRIPTION
				"Description."
			::= { sleEthernetPortEntry 5 }

		
		-- 1.3.6.1.4.1.6296.101.2.2.1.1.6
		sleEthernetPortTransmissionRate OBJECT-TYPE
			SYNTAX Integer32 (10 | 100 | 1000 | 10000)
			MAX-ACCESS read-only
			STATUS current
			DESCRIPTION
				"Description.The speed of port. Unit is Mbit/s.
				This configurations are only useful for electrical interfaces.
				Optical - interfaces will always support 1000 MBIT/s"
			::= { sleEthernetPortEntry 6 }

		
		-- 1.3.6.1.4.1.6296.101.2.2.1.1.7
		sleEthernetPortDuplexMode OBJECT-TYPE
			SYNTAX INTEGER
				{
				full(1),
				half(2),
				notAvailable(3)
				}
			MAX-ACCESS read-only
			STATUS current
			DESCRIPTION
				"Description.The duplex status of port."
			::= { sleEthernetPortEntry 7 }

		
		-- 1.3.6.1.4.1.6296.101.2.2.1.1.8
		sleEthernetPortFlowControl OBJECT-TYPE
			SYNTAX INTEGER
				{
				disabled(1),
				enabledSymetrical(2),
				enabledAsymetrical(3),
				enabledBoth(4),
				notAvailable(5)
				}
			MAX-ACCESS read-only
			STATUS current
			DESCRIPTION
				"Description.The flow-control mode of port."
			::= { sleEthernetPortEntry 8 }

		
		-- 1.3.6.1.4.1.6296.101.2.2.1.1.9
		sleEthernetPortNegotiationMode OBJECT-TYPE
			SYNTAX INTEGER
				{
				auto(1),
				force(2),
				notAvailable(3)
				}
			MAX-ACCESS read-only
			STATUS current
			DESCRIPTION
				"Description. The Auto Negotiation mode of port. "
			::= { sleEthernetPortEntry 9 }

		
		-- 1.3.6.1.4.1.6296.101.2.2.1.1.10
		sleEthernetPortJumboFrameSize OBJECT-TYPE
			SYNTAX Integer32 (0 | 1518..9000)
			MAX-ACCESS read-only
			STATUS current
			DESCRIPTION
				"Description. The jumbo frame's size of port.
				If the value is zero, it means that it is not set up."
			::= { sleEthernetPortEntry 10 }

		
		-- 1.3.6.1.4.1.6296.101.2.2.1.1.11
		sleEthernetPortSfpTransceiver OBJECT-TYPE
			SYNTAX INTEGER
				{
				unknown(0),
				electrical(1),
				electricalCoaxial(2),
				opticalLongHaul(3),
				opticalShortHaul(4)
				}
			MAX-ACCESS read-only
			STATUS current
			DESCRIPTION
				"Description."
			::= { sleEthernetPortEntry 11 }

		
		-- 1.3.6.1.4.1.6296.101.2.2.1.1.12
		sleEthernetPortSfpVendorName OBJECT-TYPE
			SYNTAX OCTET STRING
			MAX-ACCESS read-only
			STATUS current
			DESCRIPTION
				"Description."
			::= { sleEthernetPortEntry 12 }

		
		-- 1.3.6.1.4.1.6296.101.2.2.1.1.13
		sleEthernetPortSfpVendorPartNumber OBJECT-TYPE
			SYNTAX OCTET STRING
			MAX-ACCESS read-only
			STATUS current
			DESCRIPTION
				"Description."
			::= { sleEthernetPortEntry 13 }

		
		-- 1.3.6.1.4.1.6296.101.2.2.1.1.14
		sleEthernetPortSfpVendorRevision OBJECT-TYPE
			SYNTAX OCTET STRING
			MAX-ACCESS read-only
			STATUS current
			DESCRIPTION
				"Description."
			::= { sleEthernetPortEntry 14 }

		
		-- 1.3.6.1.4.1.6296.101.2.2.1.1.15
		sleEthernetPortSfpVendorSerialNumber OBJECT-TYPE
			SYNTAX OCTET STRING
			MAX-ACCESS read-only
			STATUS current
			DESCRIPTION
				"Description."
			::= { sleEthernetPortEntry 15 }

		
		-- 1.3.6.1.4.1.6296.101.2.2.1.1.16
		sleEthernetPortSfpDateCode OBJECT-TYPE
			SYNTAX OCTET STRING
			MAX-ACCESS read-only
			STATUS current
			DESCRIPTION
				"Description."
			::= { sleEthernetPortEntry 16 }

		
		-- 1.3.6.1.4.1.6296.101.2.2.1.1.17
		sleEthernetPortPhysicalRemoteChassis OBJECT-TYPE
			SYNTAX OCTET STRING
			MAX-ACCESS read-only
			STATUS current
			DESCRIPTION
				"Description."
			::= { sleEthernetPortEntry 17 }

		
		-- 1.3.6.1.4.1.6296.101.2.2.1.1.18
		sleEthernetPortPhysicalRemoteSlot OBJECT-TYPE
			SYNTAX Integer32
			MAX-ACCESS read-only
			STATUS current
			DESCRIPTION
				"Description."
			::= { sleEthernetPortEntry 18 }

		
		-- 1.3.6.1.4.1.6296.101.2.2.1.1.19
		sleEthernetPortPhysicalRemotePort OBJECT-TYPE
			SYNTAX Integer32
			MAX-ACCESS read-only
			STATUS current
			DESCRIPTION
				"Description."
			::= { sleEthernetPortEntry 19 }

		
		-- 1.3.6.1.4.1.6296.101.2.2.1.1.20
		sleEthernetPortPhysicalLinkDiscoveryMode OBJECT-TYPE
			SYNTAX INTEGER
				{
				none(1),
				manual(2),
				automatic(3)
				}
			MAX-ACCESS read-only
			STATUS current
			DESCRIPTION
				"Description."
			::= { sleEthernetPortEntry 20 }

		
		-- 1.3.6.1.4.1.6296.101.2.2.2
		sleEthernetPortControl OBJECT IDENTIFIER ::= { sleEthernetPort 2 }

		
		-- 1.3.6.1.4.1.6296.101.2.2.2.1
		sleEthernetPortControlRequest OBJECT-TYPE
			SYNTAX INTEGER { setEthernetPortProfile(1) }
			MAX-ACCESS read-write
			STATUS current
			DESCRIPTION
				"Description."
			::= { sleEthernetPortControl 1 }

		
		-- 1.3.6.1.4.1.6296.101.2.2.2.2
		sleEthernetPortControlStatus OBJECT-TYPE
			SYNTAX SleControlStatusType
			MAX-ACCESS read-only
			STATUS current
			DESCRIPTION
				"Description."
			::= { sleEthernetPortControl 2 }

		
		-- 1.3.6.1.4.1.6296.101.2.2.2.3
		sleEthernetPortControlTimer OBJECT-TYPE
			SYNTAX Gauge32
			MAX-ACCESS read-write
			STATUS current
			DESCRIPTION
				"Description."
			::= { sleEthernetPortControl 3 }

		
		-- 1.3.6.1.4.1.6296.101.2.2.2.4
		sleEthernetPortControlTimeStamp OBJECT-TYPE
			SYNTAX TimeTicks
			MAX-ACCESS read-only
			STATUS current
			DESCRIPTION
				"Description."
			::= { sleEthernetPortControl 4 }

		
		-- 1.3.6.1.4.1.6296.101.2.2.2.5
		sleEthernetPortControlReqResult OBJECT-TYPE
			SYNTAX SleControlRequestResultType
			MAX-ACCESS read-only
			STATUS current
			DESCRIPTION
				"Description."
			::= { sleEthernetPortControl 5 }

		
		-- 1.3.6.1.4.1.6296.101.2.2.2.6
		sleEthernetPortControlIndex OBJECT-TYPE
			SYNTAX Integer32
			MAX-ACCESS read-write
			STATUS current
			DESCRIPTION
				"Description."
			::= { sleEthernetPortControl 6 }

		
		-- 1.3.6.1.4.1.6296.101.2.2.2.7
		sleEthernetPortControlType OBJECT-TYPE
			SYNTAX INTEGER
				{
				unknown(0),
				electrical(1),
				optical(2)
				}
			MAX-ACCESS read-write
			STATUS current
			DESCRIPTION
				"Description."
			::= { sleEthernetPortControl 7 }

		
		-- 1.3.6.1.4.1.6296.101.2.2.2.8
		sleEthernetPortControlAdminStatus OBJECT-TYPE
			SYNTAX INTEGER
				{
				up(1),
				down(2),
				notAvailable(3)
				}
			MAX-ACCESS read-write
			STATUS current
			DESCRIPTION
				"Description."
			::= { sleEthernetPortControl 8 }

		
		-- 1.3.6.1.4.1.6296.101.2.2.2.9
		sleEthernetPortControlTransmissionRate OBJECT-TYPE
			SYNTAX Integer32 (10 | 100 | 1000 | 10000)
			MAX-ACCESS read-write
			STATUS current
			DESCRIPTION
				"Description.The speed of port. Unit is Mbit/s.
				This configurations are only useful for electrical interfaces.
				Optical - interfaces will always support 1000 MBIT/s"
			::= { sleEthernetPortControl 9 }

		
		-- 1.3.6.1.4.1.6296.101.2.2.2.10
		sleEthernetPortControlDuplexMode OBJECT-TYPE
			SYNTAX INTEGER
				{
				full(1),
				half(2),
				notAvailable(3)
				}
			MAX-ACCESS read-write
			STATUS current
			DESCRIPTION
				"Description."
			::= { sleEthernetPortControl 10 }

		
		-- 1.3.6.1.4.1.6296.101.2.2.2.11
		sleEthernetPortControlFlowControl OBJECT-TYPE
			SYNTAX INTEGER
				{
				disabled(1),
				enabledSymetrical(2),
				enabledAsymetrical(3),
				enabledBoth(4),
				notAvailable(5)
				}
			MAX-ACCESS read-write
			STATUS current
			DESCRIPTION
				"Description."
			::= { sleEthernetPortControl 11 }

		
		-- 1.3.6.1.4.1.6296.101.2.2.2.12
		sleEthernetPortControlNegotiationMode OBJECT-TYPE
			SYNTAX INTEGER
				{
				auto(1),
				force(2),
				notAvailable(3)
				}
			MAX-ACCESS read-write
			STATUS current
			DESCRIPTION
				"Description."
			::= { sleEthernetPortControl 12 }

		
		-- 1.3.6.1.4.1.6296.101.2.2.2.13
		sleEthernetPortControlJumboFrameSize OBJECT-TYPE
			SYNTAX Integer32 (0 | 1518..9000)
			MAX-ACCESS read-write
			STATUS current
			DESCRIPTION
				"Description. If the value is zero, it means erasing the set-up value.
				"
			::= { sleEthernetPortControl 13 }

		
		-- 1.3.6.1.4.1.6296.101.2.2.2.14
		sleEthernetPortControlPhysicalRemoteChassis OBJECT-TYPE
			SYNTAX OCTET STRING
			MAX-ACCESS read-write
			STATUS current
			DESCRIPTION
				"Description."
			::= { sleEthernetPortControl 14 }

		
		-- 1.3.6.1.4.1.6296.101.2.2.2.15
		sleEthernetPortControlPhysicalRemoteSlot OBJECT-TYPE
			SYNTAX Integer32
			MAX-ACCESS read-write
			STATUS current
			DESCRIPTION
				"Description."
			::= { sleEthernetPortControl 15 }

		
		-- 1.3.6.1.4.1.6296.101.2.2.2.16
		sleEthernetPortControlPhysicalRemotePort OBJECT-TYPE
			SYNTAX Integer32
			MAX-ACCESS read-write
			STATUS current
			DESCRIPTION
				"Description."
			::= { sleEthernetPortControl 16 }

		
		-- 1.3.6.1.4.1.6296.101.2.2.2.17
		sleEthernetPortControlPhysicalLinkDiscoveryMode OBJECT-TYPE
			SYNTAX INTEGER
				{
				none(1),
				manual(2),
				automatic(3)
				}
			MAX-ACCESS read-write
			STATUS current
			DESCRIPTION
				"Description."
			::= { sleEthernetPortControl 17 }

		
		-- 1.3.6.1.4.1.6296.101.2.2.3
		sleEthernetPortNotification OBJECT IDENTIFIER ::= { sleEthernetPort 3 }

		
		-- 1.3.6.1.4.1.6296.101.2.2.3.1
		sleEthernetPortChanged NOTIFICATION-TYPE
			OBJECTS { sleEthernetPortType, sleEthernetPortAdminStatus, sleEthernetPortTransmissionRate, sleEthernetPortDuplexMode, sleEthernetPortFlowControl, 
				sleEthernetPortNegotiationMode, sleEthernetPortJumboFrameSize, sleEthernetPortSfpVendorName, sleEthernetPortSfpVendorPartNumber, sleEthernetPortSfpVendorRevision, 
				sleEthernetPortSfpVendorSerialNumber, sleEthernetPortSfpDateCode, sleEthernetPortPhysicalRemoteChassis, sleEthernetPortPhysicalRemoteSlot, sleEthernetPortPhysicalRemotePort, 
				sleEthernetPortPhysicalLinkDiscoveryMode, sleEthernetPortControlRequest, sleEthernetPortControlTimeStamp, sleEthernetPortControlReqResult }
			STATUS current
			DESCRIPTION 
				"Description."
			::= { sleEthernetPortNotification 1 }

		
		-- 1.3.6.1.4.1.6296.101.2.3
		slePower OBJECT IDENTIFIER ::= { sleDevice 3 }

		
		-- 1.3.6.1.4.1.6296.101.2.3.1
		slePowerTable OBJECT-TYPE
			SYNTAX SEQUENCE OF SlePowerEntry
			MAX-ACCESS not-accessible
			STATUS current
			DESCRIPTION
				"Description."
			::= { slePower 1 }

		
		-- 1.3.6.1.4.1.6296.101.2.3.1.1
		slePowerEntry OBJECT-TYPE
			SYNTAX SlePowerEntry
			MAX-ACCESS not-accessible
			STATUS current
			DESCRIPTION
				"Description."
			INDEX { slePowerIndex }
			::= { slePowerTable 1 }

		
		SlePowerEntry ::=
			SEQUENCE { 
				slePowerIndex
					INTEGER,
				slePowerPhyIndex
					Integer32,
				slePowerState
					INTEGER
			 }

		-- 1.3.6.1.4.1.6296.101.2.3.1.1.1
		slePowerIndex OBJECT-TYPE
			SYNTAX INTEGER (1..255)
			MAX-ACCESS read-only
			STATUS current
			DESCRIPTION
				"A unique value, greater than zero, for each module. It is recommended that values are assigned contiguously starting from 1. The value for each interface sub-layer must remain constant at least from one re-initialization of the entity's network management system to the next re-initialization."
			::= { slePowerEntry 1 }

		
		-- 1.3.6.1.4.1.6296.101.2.3.1.1.2
		slePowerPhyIndex OBJECT-TYPE
			SYNTAX Integer32
			MAX-ACCESS read-only
			STATUS current
			DESCRIPTION
				"entPhysicalIndex of Power Modules (0: Internal, -1: uninstalled)"
			::= { slePowerEntry 2 }

		
		-- 1.3.6.1.4.1.6296.101.2.3.1.1.3
		slePowerState OBJECT-TYPE
			SYNTAX INTEGER
				{
				failure(0),
				ok(1)
				}
			MAX-ACCESS read-only
			STATUS current
			DESCRIPTION
				"Power status information."
			::= { slePowerEntry 3 }

		
		-- 1.3.6.1.4.1.6296.101.2.4
		sleFanModule OBJECT IDENTIFIER ::= { sleDevice 4 }

		
		-- 1.3.6.1.4.1.6296.101.2.4.1
		sleFanModuleTable OBJECT-TYPE
			SYNTAX SEQUENCE OF SleFanModuleEntry
			MAX-ACCESS not-accessible
			STATUS current
			DESCRIPTION
				"Description."
			::= { sleFanModule 1 }

		
		-- 1.3.6.1.4.1.6296.101.2.4.1.1
		sleFanModuleEntry OBJECT-TYPE
			SYNTAX SleFanModuleEntry
			MAX-ACCESS not-accessible
			STATUS current
			DESCRIPTION
				"Description."
			INDEX { sleFanModuleIndex }
			::= { sleFanModuleTable 1 }

		
		SleFanModuleEntry ::=
			SEQUENCE { 
				sleFanModuleIndex
					INTEGER,
				sleFanModulePhyIndex
					Integer32,
				sleFanModuleUnitNum
					Integer32,
				sleFanModuleAdminState
					INTEGER
			 }

		-- 1.3.6.1.4.1.6296.101.2.4.1.1.1
		sleFanModuleIndex OBJECT-TYPE
			SYNTAX INTEGER (1..255)
			MAX-ACCESS read-only
			STATUS current
			DESCRIPTION
				"A unique value, greater than zero, for each module. It is recommended that values are assigned contiguously starting from 1."
			::= { sleFanModuleEntry 1 }

		
		-- 1.3.6.1.4.1.6296.101.2.4.1.1.2
		sleFanModulePhyIndex OBJECT-TYPE
			SYNTAX Integer32
			MAX-ACCESS read-only
			STATUS current
			DESCRIPTION
				"entPhysicalIndex of FAN Modules. (0: Internal, -1: uninstalled)"
			::= { sleFanModuleEntry 2 }

		
		-- 1.3.6.1.4.1.6296.101.2.4.1.1.3
		sleFanModuleUnitNum OBJECT-TYPE
			SYNTAX Integer32
			MAX-ACCESS read-only
			STATUS current
			DESCRIPTION
				"The number of unit in FAN module"
			::= { sleFanModuleEntry 3 }

		
		-- 1.3.6.1.4.1.6296.101.2.4.1.1.4
		sleFanModuleAdminState OBJECT-TYPE
			SYNTAX INTEGER
				{
				off(0),
				on(1)
				}
			MAX-ACCESS read-only
			STATUS current
			DESCRIPTION
				"An administrative state of FAN module"
			::= { sleFanModuleEntry 4 }

		
		-- 1.3.6.1.4.1.6296.101.2.4.2
		sleFanModuleControl OBJECT IDENTIFIER ::= { sleFanModule 2 }

		
		-- 1.3.6.1.4.1.6296.101.2.4.2.1
		sleFanModuleControlRequest OBJECT-TYPE
			SYNTAX INTEGER { setFanAdminState(1) }
			MAX-ACCESS read-write
			STATUS current
			DESCRIPTION
				"set an administrative state of FAN module"
			::= { sleFanModuleControl 1 }

		
		-- 1.3.6.1.4.1.6296.101.2.4.2.2
		sleFanModuleControlStatus OBJECT-TYPE
			SYNTAX SleControlStatusType
			MAX-ACCESS read-only
			STATUS current
			DESCRIPTION
				"Description."
			::= { sleFanModuleControl 2 }

		
		-- 1.3.6.1.4.1.6296.101.2.4.2.3
		sleFanModuleControlTimer OBJECT-TYPE
			SYNTAX Gauge32
			MAX-ACCESS read-write
			STATUS current
			DESCRIPTION
				"Description."
			::= { sleFanModuleControl 3 }

		
		-- 1.3.6.1.4.1.6296.101.2.4.2.4
		sleFanModuleControlTimeStamp OBJECT-TYPE
			SYNTAX TimeTicks
			MAX-ACCESS read-only
			STATUS current
			DESCRIPTION
				"Description."
			::= { sleFanModuleControl 4 }

		
		-- 1.3.6.1.4.1.6296.101.2.4.2.5
		sleFanModuleControlReqResult OBJECT-TYPE
			SYNTAX SleControlRequestResultType
			MAX-ACCESS read-only
			STATUS current
			DESCRIPTION
				"Description."
			::= { sleFanModuleControl 5 }

		
		-- 1.3.6.1.4.1.6296.101.2.4.2.6
		sleFanModuleControlIndex OBJECT-TYPE
			SYNTAX Integer32
			MAX-ACCESS read-write
			STATUS current
			DESCRIPTION
				"Description."
			::= { sleFanModuleControl 6 }

		
		-- 1.3.6.1.4.1.6296.101.2.4.2.7
		sleFanModuleControlAdminState OBJECT-TYPE
			SYNTAX INTEGER
				{
				off(0),
				on(1)
				}
			MAX-ACCESS read-write
			STATUS current
			DESCRIPTION
				"An administrative state of FAN module"
			::= { sleFanModuleControl 7 }

		
		-- 1.3.6.1.4.1.6296.101.2.4.3
		sleFanModuleNotification OBJECT IDENTIFIER ::= { sleFanModule 3 }

		
		-- 1.3.6.1.4.1.6296.101.2.4.3.1
		sleFanAdminStateChanged NOTIFICATION-TYPE
			OBJECTS { sleFanModuleAdminState, sleFanModuleControlRequest, sleFanModuleControlTimeStamp, sleFanModuleControlReqResult }
			STATUS current
			DESCRIPTION 
				"Description."
			::= { sleFanModuleNotification 1 }

		
		-- 1.3.6.1.4.1.6296.101.2.5
		sleFanUnit OBJECT IDENTIFIER ::= { sleDevice 5 }

		
		-- 1.3.6.1.4.1.6296.101.2.5.1
		sleFanUnitTable OBJECT-TYPE
			SYNTAX SEQUENCE OF SleFanUnitEntry
			MAX-ACCESS not-accessible
			STATUS current
			DESCRIPTION
				"Description."
			::= { sleFanUnit 1 }

		
		-- 1.3.6.1.4.1.6296.101.2.5.1.1
		sleFanUnitEntry OBJECT-TYPE
			SYNTAX SleFanUnitEntry
			MAX-ACCESS not-accessible
			STATUS current
			DESCRIPTION
				"Description."
			INDEX { sleFanModuleIndex, sleFanUnitIndex }
			::= { sleFanUnitTable 1 }

		
		SleFanUnitEntry ::=
			SEQUENCE { 
				sleFanUnitIndex
					INTEGER,
				sleFanUnitOperState
					INTEGER
			 }

		-- 1.3.6.1.4.1.6296.101.2.5.1.1.1
		sleFanUnitIndex OBJECT-TYPE
			SYNTAX INTEGER (1..255)
			MAX-ACCESS read-only
			STATUS current
			DESCRIPTION
				"A unique number in FAN module"
			::= { sleFanUnitEntry 1 }

		
		-- 1.3.6.1.4.1.6296.101.2.5.1.1.2
		sleFanUnitOperState OBJECT-TYPE
			SYNTAX INTEGER
				{
				failure(0),
				ok(1)
				}
			MAX-ACCESS read-only
			STATUS current
			DESCRIPTION
				"An operational state of FAN unit"
			::= { sleFanUnitEntry 2 }

		
		-- 1.3.6.1.4.1.6296.101.2.6
		sleTemperature OBJECT IDENTIFIER ::= { sleDevice 6 }

		
		-- 1.3.6.1.4.1.6296.101.2.6.1
		sleTemperatureTable OBJECT-TYPE
			SYNTAX SEQUENCE OF SleTemperatureEntry
			MAX-ACCESS not-accessible
			STATUS current
			DESCRIPTION
				"Description."
			::= { sleTemperature 1 }

		
		-- 1.3.6.1.4.1.6296.101.2.6.1.1
		sleTemperatureEntry OBJECT-TYPE
			SYNTAX SleTemperatureEntry
			MAX-ACCESS not-accessible
			STATUS current
			DESCRIPTION
				"Description."
			INDEX { sleTemperatureIndex }
			::= { sleTemperatureTable 1 }

		
		SleTemperatureEntry ::=
			SEQUENCE { 
				sleTemperatureIndex
					INTEGER,
				sleTemperatureState
					INTEGER,
				sleTemperatureValue
					Integer32
			 }

		-- 1.3.6.1.4.1.6296.101.2.6.1.1.1
		sleTemperatureIndex OBJECT-TYPE
			SYNTAX INTEGER (1..255)
			MAX-ACCESS read-only
			STATUS current
			DESCRIPTION
				"A unique value, greater than zero, for each module. It is recommended that values are assigned contiguously starting from 1."
			::= { sleTemperatureEntry 1 }

		
		-- 1.3.6.1.4.1.6296.101.2.6.1.1.2
		sleTemperatureState OBJECT-TYPE
			SYNTAX INTEGER
				{
				failure(0),
				ok(1),
				others(2)
				}
			MAX-ACCESS read-only
			STATUS current
			DESCRIPTION
				"Temperature status information"
			::= { sleTemperatureEntry 2 }

		
		-- 1.3.6.1.4.1.6296.101.2.6.1.1.3
		sleTemperatureValue OBJECT-TYPE
			SYNTAX Integer32
			MAX-ACCESS read-only
			STATUS current
			DESCRIPTION
				"The value of temperature sensor. (unit: C)"
			::= { sleTemperatureEntry 3 }

		
		-- 1.3.6.1.4.1.6296.101.2.7
		sleBattery OBJECT IDENTIFIER ::= { sleDevice 7 }

		
		-- 1.3.6.1.4.1.6296.101.2.7.1
		sleBatteryTable OBJECT-TYPE
			SYNTAX SEQUENCE OF SleBatteryEntry
			MAX-ACCESS not-accessible
			STATUS current
			DESCRIPTION
				"Description."
			::= { sleBattery 1 }

		
		-- 1.3.6.1.4.1.6296.101.2.7.1.1
		sleBatteryEntry OBJECT-TYPE
			SYNTAX SleBatteryEntry
			MAX-ACCESS not-accessible
			STATUS current
			DESCRIPTION
				"Description."
			INDEX { sleBatteryIndex }
			::= { sleBatteryTable 1 }

		
		SleBatteryEntry ::=
			SEQUENCE { 
				sleBatteryIndex
					INTEGER,
				sleOperationPowerType
					INTEGER,
				sleOperationPowerInfo
					OCTET STRING,
				slePSUACPowerState
					INTEGER,
				slePSUTemperture
					Integer32,
				slePSUTempThreshold
					Integer32,
				slePSUOutVoltage
					OCTET STRING,
				slePSUOverTemp
					INTEGER,
				slePSUFirmwareVer
					Integer32,
				sleRBUEquipState
					INTEGER,
				sleRBUModeStaus
					OCTET STRING,
				sleRBUTemperature1
					Integer32,
				sleRBUTemperature2
					Integer32,
				sleRBUTempLowThreshold
					Integer32,
				sleRBUOutVoltage
					OCTET STRING,
				sleRBUChargeCurrent
					Integer32,
				sleRBURemainCapacity
					Integer32,
				sleRBUOverTemp
					INTEGER,
				sleBatteryLow
					INTEGER,
				sleRBUTempHighThreshold
					Integer32,
				sleRBUBTStatus
					INTEGER,
				sleRBUBTThreshold
					Integer32,
				sleRBURechargeVoltage
					Integer32,
				sleBatteryCellStatus
					INTEGER,
				sleBPSUACHardwareVer
					Integer32
			 }

		-- 1.3.6.1.4.1.6296.101.2.7.1.1.1
		sleBatteryIndex OBJECT-TYPE
			SYNTAX INTEGER (1..256)
			MAX-ACCESS read-only
			STATUS current
			DESCRIPTION
				"The index of battery charger."
			::= { sleBatteryEntry 1 }

		
		-- 1.3.6.1.4.1.6296.101.2.7.1.1.2
		sleOperationPowerType OBJECT-TYPE
			SYNTAX INTEGER
				{
				ac(0),
				rbu(1)
				}
			MAX-ACCESS read-only
			STATUS current
			DESCRIPTION
				"Power Type."
			::= { sleBatteryEntry 2 }

		
		-- 1.3.6.1.4.1.6296.101.2.7.1.1.3
		sleOperationPowerInfo OBJECT-TYPE
			SYNTAX OCTET STRING
			MAX-ACCESS read-only
			STATUS current
			DESCRIPTION
				"Operation Power Info."
			::= { sleBatteryEntry 3 }

		
		-- 1.3.6.1.4.1.6296.101.2.7.1.1.4
		slePSUACPowerState OBJECT-TYPE
			SYNTAX INTEGER
				{
				ok(0),
				fault(1)
				}
			MAX-ACCESS read-only
			STATUS current
			DESCRIPTION
				"Power State."
			::= { sleBatteryEntry 4 }

		
		-- 1.3.6.1.4.1.6296.101.2.7.1.1.5
		slePSUTemperture OBJECT-TYPE
			SYNTAX Integer32
			MAX-ACCESS read-only
			STATUS current
			DESCRIPTION
				"Temperture."
			::= { sleBatteryEntry 5 }

		
		-- 1.3.6.1.4.1.6296.101.2.7.1.1.6
		slePSUTempThreshold OBJECT-TYPE
			SYNTAX Integer32
			MAX-ACCESS read-only
			STATUS current
			DESCRIPTION
				"Temperture Threshold."
			::= { sleBatteryEntry 6 }

		
		-- 1.3.6.1.4.1.6296.101.2.7.1.1.7
		slePSUOutVoltage OBJECT-TYPE
			SYNTAX OCTET STRING
			MAX-ACCESS read-only
			STATUS current
			DESCRIPTION
				"Voltage."
			::= { sleBatteryEntry 7 }

		
		-- 1.3.6.1.4.1.6296.101.2.7.1.1.8
		slePSUOverTemp OBJECT-TYPE
			SYNTAX INTEGER
				{
				normal(0),
				over(1)
				}
			MAX-ACCESS read-only
			STATUS current
			DESCRIPTION
				"Description."
			::= { sleBatteryEntry 8 }

		
		-- 1.3.6.1.4.1.6296.101.2.7.1.1.9
		slePSUFirmwareVer OBJECT-TYPE
			SYNTAX Integer32
			MAX-ACCESS read-only
			STATUS current
			DESCRIPTION
				"The firmware version of battery charger for communication to system."
			::= { sleBatteryEntry 9 }

		
		-- 1.3.6.1.4.1.6296.101.2.7.1.1.10
		sleRBUEquipState OBJECT-TYPE
			SYNTAX INTEGER
				{
				euipped(0),
				empty(1)
				}
			MAX-ACCESS read-only
			STATUS current
			DESCRIPTION
				"Equipment State."
			::= { sleBatteryEntry 10 }

		
		-- 1.3.6.1.4.1.6296.101.2.7.1.1.11
		sleRBUModeStaus OBJECT-TYPE
			SYNTAX OCTET STRING
			MAX-ACCESS read-only
			STATUS current
			DESCRIPTION
				"Description."
			::= { sleBatteryEntry 11 }

		
		-- 1.3.6.1.4.1.6296.101.2.7.1.1.12
		sleRBUTemperature1 OBJECT-TYPE
			SYNTAX Integer32
			MAX-ACCESS read-only
			STATUS current
			DESCRIPTION
				"Description."
			::= { sleBatteryEntry 12 }

		
		-- 1.3.6.1.4.1.6296.101.2.7.1.1.13
		sleRBUTemperature2 OBJECT-TYPE
			SYNTAX Integer32
			MAX-ACCESS read-only
			STATUS current
			DESCRIPTION
				"."
			::= { sleBatteryEntry 13 }

		
		-- 1.3.6.1.4.1.6296.101.2.7.1.1.14
		sleRBUTempLowThreshold OBJECT-TYPE
			SYNTAX Integer32
			MAX-ACCESS read-only
			STATUS current
			DESCRIPTION
				"RBU Low Temperature Threshold."
			::= { sleBatteryEntry 14 }

		
		-- 1.3.6.1.4.1.6296.101.2.7.1.1.15
		sleRBUOutVoltage OBJECT-TYPE
			SYNTAX OCTET STRING
			MAX-ACCESS read-only
			STATUS current
			DESCRIPTION
				"RBU Out Voltage."
			::= { sleBatteryEntry 15 }

		
		-- 1.3.6.1.4.1.6296.101.2.7.1.1.16
		sleRBUChargeCurrent OBJECT-TYPE
			SYNTAX Integer32
			MAX-ACCESS read-only
			STATUS current
			DESCRIPTION
				"Current Charge."
			::= { sleBatteryEntry 16 }

		
		-- 1.3.6.1.4.1.6296.101.2.7.1.1.17
		sleRBURemainCapacity OBJECT-TYPE
			SYNTAX Integer32
			MAX-ACCESS read-only
			STATUS current
			DESCRIPTION
				"Remain Capacity."
			::= { sleBatteryEntry 17 }

		
		-- 1.3.6.1.4.1.6296.101.2.7.1.1.18
		sleRBUOverTemp OBJECT-TYPE
			SYNTAX INTEGER
				{
				normal(0),
				over(1),
				under(2)
				}
			MAX-ACCESS read-only
			STATUS current
			DESCRIPTION
				"The  state of Temperature over."
			::= { sleBatteryEntry 18 }

		
		-- 1.3.6.1.4.1.6296.101.2.7.1.1.19
		sleBatteryLow OBJECT-TYPE
			SYNTAX INTEGER
				{
				normal(0),
				low(1),
				notAvailable(2)
				}
			MAX-ACCESS read-only
			STATUS current
			DESCRIPTION
				"Battery state."
			::= { sleBatteryEntry 19 }

		
		-- 1.3.6.1.4.1.6296.101.2.7.1.1.20
		sleRBUTempHighThreshold OBJECT-TYPE
			SYNTAX Integer32
			MAX-ACCESS read-only
			STATUS current
			DESCRIPTION
				"RBU High Temperature Threshold."
			::= { sleBatteryEntry 20 }

		
		-- 1.3.6.1.4.1.6296.101.2.7.1.1.21
		sleRBUBTStatus OBJECT-TYPE
			SYNTAX INTEGER
				{
				enable(1),
				disable(2)
				}
			MAX-ACCESS read-only
			STATUS current
			DESCRIPTION
				"Description."
			::= { sleBatteryEntry 21 }

		
		-- 1.3.6.1.4.1.6296.101.2.7.1.1.22
		sleRBUBTThreshold OBJECT-TYPE
			SYNTAX Integer32
			MAX-ACCESS read-only
			STATUS current
			DESCRIPTION
				"Description."
			::= { sleBatteryEntry 22 }

		
		-- 1.3.6.1.4.1.6296.101.2.7.1.1.23
		sleRBURechargeVoltage OBJECT-TYPE
			SYNTAX Integer32
			MAX-ACCESS read-only
			STATUS current
			DESCRIPTION
				"Description."
			::= { sleBatteryEntry 23 }

		
		-- 1.3.6.1.4.1.6296.101.2.7.1.1.24
		sleBatteryCellStatus OBJECT-TYPE
			SYNTAX INTEGER
				{
				ok(1),
				failure(2)
				}
			MAX-ACCESS read-only
			STATUS current
			DESCRIPTION
				"Description."
			::= { sleBatteryEntry 24 }

		
		-- 1.3.6.1.4.1.6296.101.2.7.1.1.25
		sleBPSUACHardwareVer OBJECT-TYPE
			SYNTAX Integer32
			MAX-ACCESS read-only
			STATUS current
			DESCRIPTION
				"Description."
			::= { sleBatteryEntry 25 }

		
		-- 1.3.6.1.4.1.6296.101.2.7.2
		sleBatteryControl OBJECT IDENTIFIER ::= { sleBattery 2 }

		
		-- 1.3.6.1.4.1.6296.101.2.7.2.1
		sleBatteryControlRequest OBJECT-TYPE
			SYNTAX INTEGER
				{
				setBatteryForceCharge(1),
				setBatteryChargingStart(2),
				setBatteryForceChargeNonStop(3),
				setBatteryBootingTimeStatus(4),
				setBatteryBootingTime(5),
				setBatteryRechargeVoltage(6),
				setPsuAcTemperature(7),
				setBatteryTemperature(8)
				}
			MAX-ACCESS read-write
			STATUS current
			DESCRIPTION
				"Description."
			::= { sleBatteryControl 1 }

		
		-- 1.3.6.1.4.1.6296.101.2.7.2.2
		sleBatteryControlStatus OBJECT-TYPE
			SYNTAX Integer32
			MAX-ACCESS read-write
			STATUS current
			DESCRIPTION
				"Description."
			::= { sleBatteryControl 2 }

		
		-- 1.3.6.1.4.1.6296.101.2.7.2.3
		sleBatteryControlTimer OBJECT-TYPE
			SYNTAX Integer32
			MAX-ACCESS read-write
			STATUS current
			DESCRIPTION
				"Description."
			::= { sleBatteryControl 3 }

		
		-- 1.3.6.1.4.1.6296.101.2.7.2.4
		sleBatteryControlTimeStamp OBJECT-TYPE
			SYNTAX Integer32
			MAX-ACCESS read-write
			STATUS current
			DESCRIPTION
				"Description."
			::= { sleBatteryControl 4 }

		
		-- 1.3.6.1.4.1.6296.101.2.7.2.5
		sleBatteryControlReqResult OBJECT-TYPE
			SYNTAX Integer32
			MAX-ACCESS read-write
			STATUS current
			DESCRIPTION
				"Description."
			::= { sleBatteryControl 5 }

		
		-- 1.3.6.1.4.1.6296.101.2.7.2.6
		sleBatteryControlRBUBTStatus OBJECT-TYPE
			SYNTAX INTEGER
				{
				enable(1),
				disable(2)
				}
			MAX-ACCESS read-write
			STATUS current
			DESCRIPTION
				"Description."
			::= { sleBatteryControl 6 }

		
		-- 1.3.6.1.4.1.6296.101.2.7.2.7
		sleBatteryControlRBUBTThreshold OBJECT-TYPE
			SYNTAX Integer32
			MAX-ACCESS read-write
			STATUS current
			DESCRIPTION
				"Description."
			::= { sleBatteryControl 7 }

		
		-- 1.3.6.1.4.1.6296.101.2.7.2.8
		sleBatteryControlRBURechargeVoltage OBJECT-TYPE
			SYNTAX Integer32
			MAX-ACCESS read-write
			STATUS current
			DESCRIPTION
				"Description."
			::= { sleBatteryControl 8 }

		
		-- 1.3.6.1.4.1.6296.101.2.7.2.9
		sleBatteryControlTemperThresh1 OBJECT-TYPE
			SYNTAX Integer32
			MAX-ACCESS read-write
			STATUS current
			DESCRIPTION
				"Description."
			::= { sleBatteryControl 9 }

		
		-- 1.3.6.1.4.1.6296.101.2.7.2.10
		sleBatteryControlTemperThresh2 OBJECT-TYPE
			SYNTAX Integer32
			MAX-ACCESS read-write
			STATUS current
			DESCRIPTION
				"Description."
			::= { sleBatteryControl 10 }

		
		-- 1.3.6.1.4.1.6296.101.2.7.3
		sleBatteryNotification OBJECT IDENTIFIER ::= { sleBattery 3 }

		
		-- 1.3.6.1.4.1.6296.101.2.7.3.1
		sleBatteryForceChargeChanged NOTIFICATION-TYPE
			OBJECTS { sleBatteryControlRequest, sleBatteryControlTimeStamp, sleBatteryControlReqResult }
			STATUS current
			DESCRIPTION 
				"Description."
			::= { sleBatteryNotification 1 }

		
		-- 1.3.6.1.4.1.6296.101.2.7.3.2
		sleBatteryChargingStartChanged NOTIFICATION-TYPE
			OBJECTS { sleBatteryControlRequest, sleBatteryControlTimeStamp, sleBatteryControlReqResult }
			STATUS current
			DESCRIPTION 
				"Description."
			::= { sleBatteryNotification 2 }

		
		-- 1.3.6.1.4.1.6296.101.2.7.3.3
		sleBatteryForceChargeNonStopChanged NOTIFICATION-TYPE
			OBJECTS { sleBatteryControlRequest, sleBatteryControlTimeStamp, sleBatteryControlReqResult }
			STATUS current
			DESCRIPTION 
				"Description."
			::= { sleBatteryNotification 3 }

		
		-- 1.3.6.1.4.1.6296.101.2.7.3.4
		sleBatteryRBUBTStatusChanged NOTIFICATION-TYPE
			OBJECTS { sleBatteryControlRequest, sleBatteryControlTimeStamp, sleBatteryControlReqResult, sleRBUBTStatus }
			STATUS current
			DESCRIPTION 
				"Description."
			::= { sleBatteryNotification 4 }

		
		-- 1.3.6.1.4.1.6296.101.2.7.3.5
		sleBatteryRBUBTThresholdChanged NOTIFICATION-TYPE
			OBJECTS { sleBatteryControlRequest, sleBatteryControlTimeStamp, sleBatteryControlReqResult, sleRBUBTThreshold }
			STATUS current
			DESCRIPTION 
				"Description."
			::= { sleBatteryNotification 5 }

		
		-- 1.3.6.1.4.1.6296.101.2.7.3.6
		sleBatteryRBURechargeVoltageChanged NOTIFICATION-TYPE
			OBJECTS { sleBatteryControlRequest, sleBatteryControlTimeStamp, sleBatteryControlReqResult, sleRBURechargeVoltage }
			STATUS current
			DESCRIPTION 
				"Description."
			::= { sleBatteryNotification 6 }

		
		-- 1.3.6.1.4.1.6296.101.2.7.3.7
		sleBatteryPsuAcTemperThreshChanged NOTIFICATION-TYPE
			OBJECTS { sleBatteryControlRequest, sleBatteryControlTimeStamp, sleBatteryControlReqResult, slePSUTempThreshold }
			STATUS current
			DESCRIPTION 
				"Description."
			::= { sleBatteryNotification 7 }

		
		-- 1.3.6.1.4.1.6296.101.2.7.3.8
		sleBatteryRBUTemperThreshChanged NOTIFICATION-TYPE
			OBJECTS { sleBatteryControlRequest, sleBatteryControlTimeStamp, sleBatteryControlReqResult, sleRBUTempLowThreshold, sleRBUTempHighThreshold
				 }
			STATUS current
			DESCRIPTION 
				"Description."
			::= { sleBatteryNotification 8 }

		
		-- 1.3.6.1.4.1.6296.101.2.7.4
		sleBatteryBackupTable OBJECT-TYPE
			SYNTAX SEQUENCE OF SleBatteryBackupEntry
			MAX-ACCESS not-accessible
			STATUS current
			DESCRIPTION
				"Description."
			::= { sleBattery 4 }

		
		-- 1.3.6.1.4.1.6296.101.2.7.4.1
		sleBatteryBackupEntry OBJECT-TYPE
			SYNTAX SleBatteryBackupEntry
			MAX-ACCESS not-accessible
			STATUS current
			DESCRIPTION
				"Description."
			INDEX { sleBatteryBackupFile }
			::= { sleBatteryBackupTable 1 }

		
		SleBatteryBackupEntry ::=
			SEQUENCE { 
				sleBatteryBackupFile
					OCTET STRING
			 }

		-- 1.3.6.1.4.1.6296.101.2.7.4.1.1
		sleBatteryBackupFile OBJECT-TYPE
			SYNTAX OCTET STRING (SIZE (1..64))
			MAX-ACCESS read-only
			STATUS current
			DESCRIPTION
				"Description."
			::= { sleBatteryBackupEntry 1 }

		
		-- 1.3.6.1.4.1.6296.101.2.7.5
		sleBatteryBackupControl OBJECT IDENTIFIER ::= { sleBattery 5 }

		
		-- 1.3.6.1.4.1.6296.101.2.7.5.1
		sleBatteryBackupControlRequest OBJECT-TYPE
			SYNTAX INTEGER
				{
				setBatteryBackupProfile(1),
				setBatteryUpgrade(2),
				clearBatteryBackupTable(3)
				}
			MAX-ACCESS read-write
			STATUS current
			DESCRIPTION
				"Description."
			::= { sleBatteryBackupControl 1 }

		
		-- 1.3.6.1.4.1.6296.101.2.7.5.2
		sleBatteryBackupControlStatus OBJECT-TYPE
			SYNTAX SleControlStatusType
			MAX-ACCESS read-only
			STATUS current
			DESCRIPTION
				"Description."
			::= { sleBatteryBackupControl 2 }

		
		-- 1.3.6.1.4.1.6296.101.2.7.5.3
		sleBatteryBackupControlTimer OBJECT-TYPE
			SYNTAX Gauge32
			MAX-ACCESS read-write
			STATUS current
			DESCRIPTION
				"Description."
			::= { sleBatteryBackupControl 3 }

		
		-- 1.3.6.1.4.1.6296.101.2.7.5.4
		sleBatteryBackupControlTimeStamp OBJECT-TYPE
			SYNTAX TimeTicks
			MAX-ACCESS read-only
			STATUS current
			DESCRIPTION
				"Description."
			::= { sleBatteryBackupControl 4 }

		
		-- 1.3.6.1.4.1.6296.101.2.7.5.5
		sleBatteryBackupControlReqResult OBJECT-TYPE
			SYNTAX SleControlRequestResultType
			MAX-ACCESS read-only
			STATUS current
			DESCRIPTION
				"Description."
			::= { sleBatteryBackupControl 5 }

		
		-- 1.3.6.1.4.1.6296.101.2.7.5.6
		sleBatteryBackupControlServerIP OBJECT-TYPE
			SYNTAX IpAddress
			MAX-ACCESS read-write
			STATUS current
			DESCRIPTION
				"Description."
			::= { sleBatteryBackupControl 6 }

		
		-- 1.3.6.1.4.1.6296.101.2.7.5.7
		sleBatteryBackupControlUserID OBJECT-TYPE
			SYNTAX OCTET STRING (SIZE (1..64))
			MAX-ACCESS read-write
			STATUS current
			DESCRIPTION
				"Description."
			::= { sleBatteryBackupControl 7 }

		
		-- 1.3.6.1.4.1.6296.101.2.7.5.8
		sleBatteryBackupControlPassword OBJECT-TYPE
			SYNTAX OCTET STRING (SIZE (1..64))
			MAX-ACCESS read-write
			STATUS current
			DESCRIPTION
				"Description."
			::= { sleBatteryBackupControl 8 }

		
		-- 1.3.6.1.4.1.6296.101.2.7.5.9
		sleBatteryBackupControlFlag OBJECT-TYPE
			SYNTAX INTEGER
				{
				download(1),
				upload(2)
				}
			MAX-ACCESS read-write
			STATUS current
			DESCRIPTION
				"Description."
			::= { sleBatteryBackupControl 9 }

		
		-- 1.3.6.1.4.1.6296.101.2.7.5.10
		sleBatteryBackupControlLocalFile OBJECT-TYPE
			SYNTAX OCTET STRING (SIZE (1..64))
			MAX-ACCESS read-write
			STATUS current
			DESCRIPTION
				"Description."
			::= { sleBatteryBackupControl 10 }

		
		-- 1.3.6.1.4.1.6296.101.2.7.5.11
		sleBatteryBackupControlRemoteFile OBJECT-TYPE
			SYNTAX OCTET STRING (SIZE (1..64))
			MAX-ACCESS read-write
			STATUS current
			DESCRIPTION
				"Description."
			::= { sleBatteryBackupControl 11 }

		
		-- 1.3.6.1.4.1.6296.101.2.7.6
		sleBatterBackupNotification OBJECT IDENTIFIER ::= { sleBattery 6 }

		
		-- 1.3.6.1.4.1.6296.101.2.7.6.1
		sleBatteryBackupProfileChanged NOTIFICATION-TYPE
			OBJECTS { sleBatteryBackupControlRequest, sleBatteryBackupControlTimeStamp, sleBatteryBackupControlReqResult, sleBatteryBackupControlServerIP, sleBatteryBackupControlUserID, 
				sleBatteryBackupControlPassword, sleBatteryBackupControlFlag, sleBatteryBackupControlLocalFile, sleBatteryBackupControlRemoteFile }
			STATUS current
			DESCRIPTION 
				"Description."
			::= { sleBatterBackupNotification 1 }

		
		-- 1.3.6.1.4.1.6296.101.2.7.6.2
		sleBatteryBackupUpgraded NOTIFICATION-TYPE
			OBJECTS { sleBatteryBackupControlRequest, sleBatteryBackupControlTimeStamp, sleBatteryBackupControlReqResult, sleBatteryBackupControlLocalFile }
			STATUS current
			DESCRIPTION 
				"Description."
			::= { sleBatterBackupNotification 2 }

		
		-- 1.3.6.1.4.1.6296.101.2.7.6.3
		sleBatteryBackupTableCleared NOTIFICATION-TYPE
			OBJECTS { sleBatteryBackupControlRequest, sleBatteryBackupControlTimeStamp, sleBatteryBackupControlReqResult, sleBatteryBackupControlLocalFile }
			STATUS current
			DESCRIPTION 
				"Description."
			::= { sleBatterBackupNotification 3 }

		
		-- 1.3.6.1.4.1.6296.101.2.8
		sleDoor OBJECT IDENTIFIER ::= { sleDevice 8 }

		
		-- 1.3.6.1.4.1.6296.101.2.8.1
		sleDoorInfo OBJECT IDENTIFIER ::= { sleDoor 1 }

		
		-- 1.3.6.1.4.1.6296.101.2.8.1.1
		sleDoorStatus OBJECT-TYPE
			SYNTAX INTEGER
				{
				close(0),
				open(1)
				}
			MAX-ACCESS read-only
			STATUS current
			DESCRIPTION
				"Description."
			::= { sleDoorInfo 1 }

		
		-- 1.3.6.1.4.1.6296.101.2.9
		sleCpu OBJECT IDENTIFIER ::= { sleDevice 9 }

		
		-- 1.3.6.1.4.1.6296.101.2.9.1
		sleCpuInfo OBJECT IDENTIFIER ::= { sleCpu 1 }

		
		-- 1.3.6.1.4.1.6296.101.2.9.1.1
		sleCpuProcessor OBJECT-TYPE
			SYNTAX OCTET STRING
			MAX-ACCESS read-only
			STATUS current
			DESCRIPTION
				"Description."
			::= { sleCpuInfo 1 }

		
		-- 1.3.6.1.4.1.6296.101.2.9.1.2
		sleCpuModel OBJECT-TYPE
			SYNTAX OCTET STRING
			MAX-ACCESS read-only
			STATUS current
			DESCRIPTION
				"Description."
			::= { sleCpuInfo 2 }

		
		-- 1.3.6.1.4.1.6296.101.2.9.1.3
		sleCpuRevision OBJECT-TYPE
			SYNTAX OCTET STRING
			MAX-ACCESS read-only
			STATUS current
			DESCRIPTION
				"Description."
			::= { sleCpuInfo 3 }

		
		-- 1.3.6.1.4.1.6296.101.2.9.1.4
		sleCpuBogomips OBJECT-TYPE
			SYNTAX OCTET STRING
			MAX-ACCESS read-only
			STATUS current
			DESCRIPTION
				"Description."
			::= { sleCpuInfo 4 }

		
		-- 1.3.6.1.4.1.6296.101.2.9.1.5
		sleCpuManufacturer OBJECT-TYPE
			SYNTAX OCTET STRING
			MAX-ACCESS read-only
			STATUS current
			DESCRIPTION
				"Description."
			::= { sleCpuInfo 5 }

		
		-- 1.3.6.1.4.1.6296.101.2.9.1.6
		sleCpuClock OBJECT-TYPE
			SYNTAX Integer32
			MAX-ACCESS read-only
			STATUS current
			DESCRIPTION
				"Description."
			::= { sleCpuInfo 6 }

		
		-- 1.3.6.1.4.1.6296.101.2.9.1.7
		sleCpuBusClock OBJECT-TYPE
			SYNTAX Integer32
			MAX-ACCESS read-only
			STATUS current
			DESCRIPTION
				"Description."
			::= { sleCpuInfo 7 }

		
		-- 1.3.6.1.4.1.6296.101.2.10
		sleClockModule OBJECT IDENTIFIER ::= { sleDevice 10 }

		
		-- 1.3.6.1.4.1.6296.101.2.10.1
		sleClockModuleTable OBJECT-TYPE
			SYNTAX SEQUENCE OF SleClockModuleEntry
			MAX-ACCESS not-accessible
			STATUS current
			DESCRIPTION
				"Description."
			::= { sleClockModule 1 }

		
		-- 1.3.6.1.4.1.6296.101.2.10.1.1
		sleClockModuleEntry OBJECT-TYPE
			SYNTAX SleClockModuleEntry
			MAX-ACCESS not-accessible
			STATUS current
			DESCRIPTION
				"Description."
			INDEX { sleClockModuleIndex }
			::= { sleClockModuleTable 1 }

		
		SleClockModuleEntry ::=
			SEQUENCE { 
				sleClockModuleIndex
					INTEGER,
				sleClockModuleBoardId
					INTEGER,
				sleClockModuleInstallStatus
					INTEGER,
				sleClockModuleInitStatus
					INTEGER
			 }

		-- 1.3.6.1.4.1.6296.101.2.10.1.1.1
		sleClockModuleIndex OBJECT-TYPE
			SYNTAX INTEGER
			MAX-ACCESS read-only
			STATUS current
			DESCRIPTION
				"A unique value, greater than zero, for each module. It is recommended that values are assigned contiguously starting from 1."
			::= { sleClockModuleEntry 1 }

		
		-- 1.3.6.1.4.1.6296.101.2.10.1.1.2
		sleClockModuleBoardId OBJECT-TYPE
			SYNTAX INTEGER
				{
				sfuA(1),
				sfuB(2)
				}
			MAX-ACCESS read-only
			STATUS current
			DESCRIPTION
				"Indication of the board identifier."
			::= { sleClockModuleEntry 2 }

		
		-- 1.3.6.1.4.1.6296.101.2.10.1.1.3
		sleClockModuleInstallStatus OBJECT-TYPE
			SYNTAX INTEGER
				{
				removed(0),
				installed(1)
				}
			MAX-ACCESS read-only
			STATUS current
			DESCRIPTION
				"The install status of clock module."
			::= { sleClockModuleEntry 3 }

		
		-- 1.3.6.1.4.1.6296.101.2.10.1.1.4
		sleClockModuleInitStatus OBJECT-TYPE
			SYNTAX INTEGER
				{
				failure(0),
				ok(1)
				}
			MAX-ACCESS read-only
			STATUS current
			DESCRIPTION
				"The initialization status of clock module."
			::= { sleClockModuleEntry 4 }

		
		-- 1.3.6.1.4.1.6296.101.2.11
		sleDeviceGroup OBJECT-GROUP
			OBJECTS { sleDeviceEthernetPortNum, sleDevicePowerNum, sleDeviceFanModuleNum, sleDeviceTemperatureNum, sleDeviceFanStartTemperature, 
				sleDeviceFanStopTemperature, sleDeviceControlRequest, sleDeviceControlStatus, sleDeviceControlTimer, sleDeviceControlTimeStamp, 
				sleDeviceControlReqResult, sleDeviceControlFanStartTemperature, sleDeviceControlFanStopTemperature, sleEthernetPortIndex, sleEthernetPortPhyIndex, 
				sleEthernetPortType, sleEthernetPortAdminStatus, sleEthernetPortOperStatus, sleEthernetPortTransmissionRate, sleEthernetPortDuplexMode, 
				sleEthernetPortFlowControl, sleEthernetPortNegotiationMode, sleEthernetPortJumboFrameSize, sleEthernetPortSfpTransceiver, sleEthernetPortSfpVendorName, 
				sleEthernetPortSfpVendorPartNumber, sleEthernetPortSfpVendorRevision, sleEthernetPortSfpVendorSerialNumber, sleEthernetPortSfpDateCode, sleEthernetPortPhysicalRemoteChassis, 
				sleEthernetPortPhysicalRemoteSlot, sleEthernetPortPhysicalRemotePort, sleEthernetPortPhysicalLinkDiscoveryMode, sleEthernetPortControlRequest, sleEthernetPortControlStatus, 
				sleEthernetPortControlTimer, sleEthernetPortControlTimeStamp, sleEthernetPortControlReqResult, sleEthernetPortControlIndex, sleEthernetPortControlType, 
				sleEthernetPortControlAdminStatus, sleEthernetPortControlTransmissionRate, sleEthernetPortControlDuplexMode, sleEthernetPortControlFlowControl, sleEthernetPortControlJumboFrameSize, 
				sleEthernetPortControlPhysicalRemoteChassis, sleEthernetPortControlPhysicalRemoteSlot, sleEthernetPortControlPhysicalRemotePort, sleEthernetPortControlPhysicalLinkDiscoveryMode, slePowerIndex, 
				slePowerPhyIndex, slePowerState, sleFanModuleIndex, sleFanModulePhyIndex, sleFanModuleUnitNum, 
				sleFanModuleAdminState, sleFanModuleControlRequest, sleFanModuleControlStatus, sleFanModuleControlTimer, sleFanModuleControlTimeStamp, 
				sleFanModuleControlReqResult, sleFanModuleControlIndex, sleFanModuleControlAdminState, sleFanUnitIndex, sleFanUnitOperState, 
				sleTemperatureIndex, sleTemperatureState, sleTemperatureValue, sleBatteryIndex, sleDoorStatus, 
				sleOperationPowerType, sleOperationPowerInfo, slePSUACPowerState, slePSUTemperture, slePSUOutVoltage, 
				slePSUOverTemp, slePSUFirmwareVer, sleRBUEquipState, sleRBUModeStaus, sleBatteryBackupFile, 
				sleBatteryBackupControlRequest, sleBatteryBackupControlStatus, sleBatteryBackupControlTimer, sleBatteryBackupControlTimeStamp, sleBatteryBackupControlReqResult, 
				sleBatteryBackupControlServerIP, sleBatteryBackupControlUserID, sleBatteryBackupControlPassword, sleBatteryBackupControlFlag, sleBatteryBackupControlLocalFile, 
				sleBatteryBackupControlRemoteFile, sleCpuProcessor, sleCpuModel, sleCpuRevision, sleCpuBogomips, 
				sleCpuManufacturer, sleCpuClock, sleCpuBusClock, sleRBUTemperature1, slePSUTempThreshold, 
				sleRBUTemperature2, sleRBUOutVoltage, sleRBUChargeCurrent, sleRBURemainCapacity, sleRBUOverTemp, 
				sleBatteryLow, sleRBUBTStatus, sleRBUBTThreshold, sleRBURechargeVoltage, sleBatteryCellStatus, 
				sleBPSUACHardwareVer, sleBatteryControlRequest, sleBatteryControlStatus, sleBatteryControlTimer, sleBatteryControlTimeStamp, 
				sleBatteryControlReqResult, sleBatteryControlRBUBTStatus, sleBatteryControlRBUBTThreshold, sleBatteryControlRBURechargeVoltage, sleBatteryControlTemperThresh1, 
				sleBatteryControlTemperThresh2, sleRBUTempHighThreshold, sleRBUTempLowThreshold, sleEthernetPortControlNegotiationMode }
			STATUS current
			DESCRIPTION 
				"Description."
			::= { sleDevice 11 }

		
		-- 1.3.6.1.4.1.6296.101.2.12
		sleDeviceNotificationGroup NOTIFICATION-GROUP
			NOTIFICATIONS { sleDeviceTemperatureThresholdChanged, sleEthernetPortChanged, sleFanAdminStateChanged, sleBatteryBackupProfileChanged, sleBatteryBackupUpgraded, 
				sleBatteryBackupTableCleared, sleBatteryForceChargeChanged, sleBatteryChargingStartChanged, sleBatteryForceChargeNonStopChanged, sleBatteryRBUBTStatusChanged, 
				sleBatteryRBUBTThresholdChanged, sleBatteryRBURechargeVoltageChanged, sleBatteryPsuAcTemperThreshChanged, sleBatteryRBUTemperThreshChanged }
			STATUS current
			DESCRIPTION 
				"Description."
			::= { sleDevice 12 }

		
	
	END

--
-- SLE-DEVICE-MIB.my
--
