CSI-BBIPX-MIB 
-- ******************************************************
--Control Solutions, Inc., SNMP  MIB
--Prefix for private enterprises:  1.3.6.1.4.1	
--Control Solutions, Inc. private enterprize number:  3815
--
-- The following MIB is the definition of the SNMP based implementation
-- of Babel Buster X2, Babel Buster SP, and i.CanDoIt BAS-700 ReMOTE I/O.
-- This MIB provides access to general purpose data registers
-- per BBX2 core implementation.
--
--
-- ************************************************************

DEFINITIONS ::= BEGIN

IMPORTS  
	MODULE-IDENTITY, OBJECT-TYPE, Integer32, NOTIFICATION-TYPE 
		FROM SNMPv2-SMI
	MODULE-COMPLIANCE, OBJECT-GROUP, NOTIFICATION-GROUP
		FROM SNMPv2-CONF
 	bbipx 
		FROM Control-Solutions-MIB-Registrations;


bbipxModule MODULE-IDENTITY
	LAST-UPDATED "200507050000Z"
	ORGANIZATION "Control Solutions, Inc."
	CONTACT-INFO
		"Jim Hogenson
		Control Solutions, Inc.
		980 E. Berwood Ave, Suite 100
		PO Box 10789
		St. Paul, MN 55110
		jimhogenson@csimn.com
		Voice: 651-426-4410
		Fax: 651-426-4418"
	DESCRIPTION
		"The following MIB is the definition of SNMP access to
		Babel Buster IP/X core based on Control Solutions Babel Buster
		Ethernet processor."
	REVISION "200812020000Z"
	DESCRIPTION
		"Initial draft."
	::= { bbipxV1 1 }


          -- textual conventions

          DisplayString ::=
              OCTET STRING
          -- This data type is used to model textual information taken
          -- from the NVT ASCII character set.  By convention, objects
          -- with this syntax are declared as having
          --
          --      SIZE (0..255)

-- Major object categories for Babel Buster 10/100

dataRegs	OBJECT IDENTIFIER ::= { bbipxmSnmp 1 }  	-- 3815.1.3.1.1

-- ******************************************************
--
-- INTEGER DATA REGISTER TABLE (first int is 1.3.6.1.4.1.3815.1.3.1.1.1.2.1)
-- 
-- ******************************************************

dataRegTable OBJECT-TYPE
	SYNTAX	SEQUENCE OF DataRegEntry
	MAX-ACCESS	not-accessible
	STATUS	current
	DESCRIPTION
		"Integer data register table."
	::= { dataRegs 1 }

dataRegEntry OBJECT-TYPE
	SYNTAX	dataRegEntry
	MAX-ACCESS	not-accessible
	STATUS	current
	DESCRIPTION
		"Integer data register table entry."
	INDEX	{ dataRegIndex }
	::= { dataRegTable 1 }

DataRegEntry ::= SEQUENCE {
	dataRegIndex		INTEGER,
	dataRegRegister		Integer32,
	dataRegName			DisplayString
	}

dataRegIndex OBJECT-TYPE
	SYNTAX	INTEGER (1..65536) 
	MAX-ACCESS	not-accessible
	STATUS	current
	DESCRIPTION
		"Register number, index into integer data register table."
	::= { dataRegEntry 1 }

dataRegRegister OBJECT-TYPE
	SYNTAX	Integer32
	MAX-ACCESS	read-write
	STATUS	current
	DESCRIPTION
		"Register's data value."
	::= { dataRegEntry 2 }

dataRegName OBJECT-TYPE
	SYNTAX	DisplayString (SIZE(0..40))
	MAX-ACCESS	read-only
	STATUS	current
	DESCRIPTION
		"Register's name."
	::= { dataRegEntry 3 }

-- ******************************************************
--
-- SIMPLE I/O FOR SNMP NOTIFICATIONS
-- 
-- ******************************************************

bbipxTrapPrefix	OBJECT IDENTIFIER ::= { bbipx 2 }
bbipxTraps		OBJECT IDENTIFIER ::= { bbipxTrapPrefix 0 }

eventStateChange	NOTIFICATION-TYPE
	OBJECTS {
		changeRegValue,
		changeRegName
	}
	STATUS	 	current
	DESCRIPTION
		"This trap is sent when a register changes value
		if notifications are enabled for the object that changed."
	::= { bbipxTraps 1 }

-- ******************************************************
--
-- SIMPLE I/O FOR SNMP COMPLIANCE
-- 
-- ******************************************************

bbipxConformance	OBJECT IDENTIFIER ::= { bbipx 3 }

bbipxGroups		OBJECT IDENTIFIER ::= { bbipxConformance 1 }
bbipxCompliances 	OBJECT IDENTIFIER ::= { bbipxConformance 2 }

bbipxCompliance MODULE-COMPLIANCE
	STATUS 	current
	DESCRIPTION
		"The compliance statement for SNMPv2 entities which
		implement the agent supported by the Babel Buster X2 core."
	MODULE
	MANDATORY-GROUPS
		{ bbipxDataRegIntGroup }
	::= { bbipxCompliances 1 }

bbipxDataRegIntGroup	OBJECT-GROUP
	OBJECTS {
		dataIntRegister,
		dataIntName
	}
	STATUS 	current
	DESCRIPTION
		"Group of objects that define integer data registers."
	::= { bbipxGroups 1 }

bbipxNotificationGroup	NOTIFICATION-GROUP
	NOTIFICATIONS { 
		eventStateChange 
	}
	STATUS current
	DESCRIPTION
		"Group of objects that define notifications."
	::= { bbipxGroups 2 }

END
