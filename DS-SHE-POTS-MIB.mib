--
-- she-pots-mib.mib
-- MIB generated by MG-SOFT Visual MIB Builder Version 6.0  Build 88
-- Monday, March 03, 2008 at 16:16:34
--

	DS-SHE-POTS-MIB DEFINITIONS ::= BEGIN
 
		IMPORTS
			she			
				FROM AN-MIB
			dsShe
				FROM DASAN-SMI							
			ifIndex			
				FROM IF-MIB			
			sheAlarmTimeAndDate, sheAlarmReportingSource, sheAlarmReportingSourceType, sheAlarmSeverity, SheAlarmSevProfileIndex			
				FROM DS-SHE-ALARMING-MIB			
			SheControlStatusType			
				FROM DS-SHE-TC-MIB			
			OBJECT-GROUP, MODULE-COMPLIANCE, NOTIFICATION-GROUP			
				FROM SNMPv2-CONF			
			TimeTicks, Unsigned32, Gauge32, OBJECT-TYPE, MODULE-IDENTITY, 
			NOTIFICATION-TYPE			
				FROM SNMPv2-SMI			
			DisplayString			
				FROM SNMPv2-TC;
	
	
		shePotsMib MODULE-IDENTITY 
			LAST-UPDATED "200801311120Z"		-- January 31, 2008 at 11:20 GMT
			ORGANIZATION 
				"Nokia Siemens Networks"
			CONTACT-INFO 
				"Yang Xu
				Com CD/FN RDC BJ
				yang.xu@siemens.com
				+0086 58671204
				
				
				Gerd Barchmann
				COO BBA DSLAM RD HW1
				gerd.barchmann@nsn.com"
			DESCRIPTION 
				"This MIB contains all needed informations about shePots module and
				all supported features."
			REVISION "200605151632Z"		-- May 15, 2006 at 16:32 GMT
			DESCRIPTION 
				"new she pots mib"
			REVISION "200608221003Z"		-- August 22, 2006 at 10:03 GMT
			DESCRIPTION 
				"Merge done to SHE R2.5 by Gerd Barchmann."
			REVISION "200705081528Z"		-- May 08, 2007 at 15:28 GMT
			DESCRIPTION 
				"Merge current R2.0M maintenance release to SHE R2.5.2.
				This version is not backward compatible to SHE R2.5.1."
			REVISION "200709121105Z"		-- September 12, 2007 at 11:05 GMT
			DESCRIPTION 
				"Merge APS38 release of R2.0M version.
				Add highfeedcoinbox(3) into ShePotsPptpProfilePortPotsTypeType.
				Add new leaf shePotsPptpProfileCid and shePotsPptpProfileControlCid. Define new type ShePotsPptpProfileCidType for it.
				shePotsAnalogIfProfileCid and shePotsAnalogIfProfileControlCid are removed
				Add ipHostProtection(38) into ShePotsControlRequestResultType.
				Add 3ElementCapacitanceTest(52) Must:shePotsConfigControlIfIndexBitMask	into shePotsConfigControlRequest description.
				Add 3ElementCapacitanceTest(52) into ShePotsControlRequestType.
				Add shePotsAnalogIfProfileHookoffMin and shePotsAnalogIfProfileControlHookoffMin.
				Add fault(19) into ShePotsConfigPortStatusType.
				Add one new entry shePotsPptpProfilePortPotsLineType into shePotsPptpProfileTable.
				Add ShePotsPptpProfilePortPotsLineTypeType.
				Add new PortStatus item: threeElementCapacitancetest.
				Add new items in ReqResultType (38~43).
				Modify shePotsAnalogIfProfileControlMeteringPulseInterval (20~65530. DEFVAL 20).
				Add testringstart and threeElementCapacitanceTest into shePotsConfigLastTest."
			REVISION "200710231140Z"		-- October 23, 2007 at 11:40 GMT
			DESCRIPTION 
				"Add SIP support for R2.6S and R2.8."
			REVISION "200801311110Z"		-- January 31, 2008 at 11:10 GMT
			DESCRIPTION 
				"Small descriptional correction.
				Add register information for SIP user."
			::= { dsShe 38 }

		
	
--
-- Type definitions
--
	
		ShePotsPptpProfilePortPotsTypeType ::= INTEGER
			{
			commonTelephone(1),
			coinbox(2),
			highfeedcoinbox(3)
			}

		ShePotsControlRequestType ::= INTEGER
			{
			noRequest(1),
			createPotsPptpProfile(10),
			deletePotsPptpProfile(11),
			modifyPotsPptpProfile(12),
			createPotsAnalogIfProfile(20),
			modifyPotsAnalogIfProfile(21),
			deletePotsAnalogIfProfile(22),
			modifyPotsConfig(30),
			testRing(31),
			testToneDial(32),
			testToneRingback(33),
			testToneBusy(34),
			testToneStop(35),
			receiverOffHook(40),
			onOffHookSelfTest(41),
			telephoneNumTest(42),
			resistanceTest(45),
			loopResistanceCurrentTest(46),
			dcFeedVoltage(47),
			dcFeedCurrent(48),
			openCircuitVoltage(49),
			acVoltageTest(50),
			batteryVoltageTest(51),
			threeElementCapacitanceTest(52),
			modifyPotsSipUserData(53)
			}

		ShePotsControlRequestResultType ::= INTEGER
			{
			noRequest(1),
			failed(2),
			voipNotInitialized(3),
			memoryAllocFailure(4),
			defProfilesCreationFailure(5),
			exceedMaxProfileNum(6),
			exceedMaxVgwNum(7),
			exceedMaxSlotNum(8),
			invalidParameter(9),
			vgwMemberListNotEmpty(10),
			profileIsInUse(11),
			duplicatedIndex(12),
			duplicatedPort(13),
			duplicatedName(14),
			tooLongName(15),
			profileEntryNotFound(16),
			cannotDeleteDefProfile(17),
			cannotModifyDefProfileName(18),
			tableIsEmpty(19),
			tableEntryNotFound(20),
			memberBelongsToOtherVgw(21),
			testOnGoing(22),
			porNotInTestStatus(23),
			maxLessThanMin(24),
			duplicatedIpAddress(25),
			duplicatedSlotIpHost(26),
			ipHostGatewayFailed(27),
			adminNotInTestStatus(28),
			dhcpNotSupported(29),
			comExecStarted(30),
			paramFaulty(31),
			requestBusy(32),
			setDataFailed(34),
			aswTimeout(35),
			commandFailed(36),
			commandSucceeded(37),
			ipHostProtection(38),
			hlminSmallthanHkmin(39),
			exceedMaxHighfeedPortNum(40),
			highfeedPortIdInvalid(41),
			highfeedPortsNumInvalid(42),
			portNotInDisableStatus(43)
			}

		ShePotsAnalogIfProfileCidType ::= INTEGER
			{
			dtmf(0),
			nonRpas(1),
			rpas(2),
			ntt(3)
			}

		ShePotsAnalogIfProfileMeteringPulseFreqType ::= INTEGER
			{
			freq12kHz(0),
			freq16kHz(1)
			}

		ShePotsConfigPortStatusType ::= INTEGER
			{
			down(0),
			busy(1),
			idle(2),
			testing(3),
			testRing(4),
			testToneDial(5),
			testToneRingback(6),
			testToneBusy(7),
			testToneStop(8),
			receiverOffHook(9),
			onOffHookSelfTest(10),
			telephoneNumTest(11),
			resistanceTest(12),
			loopResistanceCurrentTest(13),
			dcFeedVoltage(14),
			dcFeedCurrent(15),
			openCircuitVoltage(16),
			acVoltageTest(17),
			batteryVoltageTest(18),
			fault(19),
			threeElementCapacitanceTest(20)
			}

		ShePotsConfigPotsPortPriorityLevelType ::= INTEGER
			{
			level1(1),
			level2(2),
			level3(3)
			}

		ShePotsConfigLastTestType ::= INTEGER
			{
			noTest(0),
			testRing(1),
			testToneDial(2),
			testToneRingback(3),
			testToneBusy(4),
			testToneStop(5),
			receiverOffHook(6),
			onOffHookSelfTest(7),
			telephoneNumTest(8),
			resistanceTest(9),
			loopResistanceCurrentTest(10),
			dcFeedVoltage(11),
			dcFeedCurrent(12),
			openCircuitVoltage(13),
			acVoltageTest(14),
			batteryVoltageTest(15),
			threeElementCapacitanceTest(16)
			}

--      ShePotsPptpProfileCidTypeObjects group
		ShePotsPptpProfileCidType ::= INTEGER
			{
			dtmf(0),
			fSKBellcore(1),
			fSKETSIRPAS(2),
			nTT(3),
			fSKETSIDTAS(4),
			fSKETSILRDTAS(5)
			}

-- ShePotsPptpProfilePortPotsLineTypeObjects group
		ShePotsPptpProfilePortPotsLineTypeType ::= INTEGER
			{
			longline(1),
			mediumline(2),
			shortline(3)
			}

		ShePotsSipUserDataConfigType ::= INTEGER
			{
			enable(1),
			disable(0)
			}

		ShePotsSipUserDataRegisterStatusType ::= INTEGER
			{
			unregistered(0),
			registered(1)
			}

	
	
--
-- Node definitions
--
	
		shePotsPptpObjects OBJECT IDENTIFIER ::= { shePotsMib 1 }

		
		shePotsPptpProfileTable OBJECT-TYPE
			SYNTAX SEQUENCE OF ShePotsPptpProfileEntry
			MAX-ACCESS not-accessible
			STATUS current
			DESCRIPTION
				"This table contains attributes for each potsPptpProfile."
			::= { shePotsPptpObjects 1 }

		
		shePotsPptpProfileEntry OBJECT-TYPE
			SYNTAX ShePotsPptpProfileEntry
			MAX-ACCESS not-accessible
			STATUS current
			DESCRIPTION
				"An entry represents a set of profile configurations
				in shePotsPptpProfileTable.A default profile will always exist. 
				This profile's name will be set to `DEFVAL' and its parameters 
				will be set to vendor specific values.
				"
			INDEX { shePotsPptpProfileIndex }
			::= { shePotsPptpProfileTable 1 }

		
		ShePotsPptpProfileEntry ::=
			SEQUENCE { 
				shePotsPptpProfileIndex
					Unsigned32,
				shePotsPptpProfileName
					DisplayString,
				shePotsPptpProfilePortIGain
					INTEGER,
				shePotsPptpProfilePortOGain
					INTEGER,
				shePotsPptpProfilePortFaxlvl
					Unsigned32,
				shePotsPptpProfilePortPotsType
					ShePotsPptpProfilePortPotsTypeType,
				shePotsPptpProfileCid
					ShePotsPptpProfileCidType,
				shePotsPptpProfilePortPotsLineType
					ShePotsPptpProfilePortPotsLineTypeType
			 }

		shePotsPptpProfileIndex OBJECT-TYPE
			SYNTAX Unsigned32
			MAX-ACCESS read-only
			STATUS current
			DESCRIPTION
				"Table index."
			::= { shePotsPptpProfileEntry 1 }

		
		shePotsPptpProfileName OBJECT-TYPE
			SYNTAX DisplayString (SIZE (1..31))
			MAX-ACCESS read-only
			STATUS current
			DESCRIPTION
				"A describable name that uniquely identifies a profile 
				entry of this table.The profile name is user specified.
				A default profile will always exist. This profile's name 
				will be set to `DEFVAL'."
			::= { shePotsPptpProfileEntry 2 }

		
		shePotsPptpProfilePortIGain OBJECT-TYPE
			SYNTAX INTEGER (-140..60)
			UNITS "0.1 dB"
			MAX-ACCESS read-only
			STATUS current
			DESCRIPTION
				"ITUT: Gain control, or usage of signal level adaptation and 
				noise level reduction is used to adapt the level of the signal. 
				However, it is necessary, for example for modem calls, to turn 
				off this function.
				Input volume of AGLU port. Unit:0.1db
				[value range] value =<-140 ~ 60> (default : 0)
				"
			DEFVAL { 0 }
			::= { shePotsPptpProfileEntry 3 }

		
		shePotsPptpProfilePortOGain OBJECT-TYPE
			SYNTAX INTEGER (-140..60)
			UNITS "0.1 dB"
			MAX-ACCESS read-only
			STATUS current
			DESCRIPTION
				"Output volume of AGLU port. Unit:0.1db
				[value range]value =<-140 ~ 60> (default : 0)
				"
			DEFVAL { 0 }
			::= { shePotsPptpProfileEntry 4 }

		
		shePotsPptpProfilePortFaxlvl OBJECT-TYPE
			SYNTAX Unsigned32 (0..15)
			UNITS "dBm"
			MAX-ACCESS read-only
			STATUS current
			DESCRIPTION
				"Fax volume of AGLU port is used to set the transmit level in T.38 
				fax relay mode.The level is expressed in 1dBm steps, within the
				range of 0.. 15. The default value is 10 , which corresponds to a
				transmit level of 10dBm.  
				[value range]NUM = Volume value : level 1 ~ level 15 
				(step:1dBm, Default: 10, Disable:0)
				"
			DEFVAL { 10 }
			::= { shePotsPptpProfileEntry 5 }

		
		shePotsPptpProfilePortPotsType OBJECT-TYPE
			SYNTAX ShePotsPptpProfilePortPotsTypeType
			MAX-ACCESS read-only
			STATUS current
			DESCRIPTION
				"Pots type [value index]
				
				commonTelephone(1),  
				coinbox(2)
				highfeedcoinbox(3)	"
			DEFVAL { commonTelephone }
			::= { shePotsPptpProfileEntry 6 }

		
		shePotsPptpProfileCid OBJECT-TYPE
			SYNTAX ShePotsPptpProfileCidType
			MAX-ACCESS read-only
			STATUS current
			DESCRIPTION
				"Use of Caller ID and can be set to the following four value. 		
				
				dtmf(0),
				fSKBellcore(1),   -- Bellcore      (default)                    
				fSKETSIRPAS(2),  -- ETSI specification RPAS type
				nTT(3)              
				fSKETSIDTAS(4),  -- ETSI specification DTAS type  
				fSKETSILRDTAS(5) -- ETSI specification LRDTAS type   
				
				Supported with R2.0M APS >= 38."
			DEFVAL { fSKBellcore }
			::= { shePotsPptpProfileEntry 7 }

		
		shePotsPptpProfilePortPotsLineType OBJECT-TYPE
			SYNTAX ShePotsPptpProfilePortPotsLineTypeType
			MAX-ACCESS read-only
			STATUS current
			DESCRIPTION
				" The three line types are defined by the resistance of pots line
				longline(1),
				mediumline(2),
				shortline(3)
				
				Supported with R2.0M APS >= 38."
			DEFVAL { longline }
			::= { shePotsPptpProfileEntry 8 }

		
		shePotsPptpProfileControl OBJECT IDENTIFIER ::= { shePotsPptpObjects 2 }

		
		shePotsPptpProfileControlRequest OBJECT-TYPE
			SYNTAX ShePotsControlRequestType
			MAX-ACCESS read-write
			STATUS current
			DESCRIPTION
				"The request of a user command.
				createPotsPptpProfile	(10),
					Must: shePotsPptpProfileControlName 				
				        Optional: shePotsPptpProfileControlPortIGain 		
				        	  shePotsPptpProfileControlPortOGain         
				        	  shePotsPptpProfileControlPortFaxlvl
				        	  shePotsPptpProfileControlPortPotsType
				        	  shePotsPptpProfileControlCid
				        	  shePotsPptpProfileControlPortPotsLineType        
				         			  
				deletePotsPptpProfile 	(11),
				 	Must: shePotsPptpProfileControlIndex
				 
				modifyPotsPptpProfile	(12),
				        Must: shePotsPptpProfileControlIndex 				
				       	Optional:shePotsPptpProfileControlName 
				       		 shePotsPptpProfileControlPortIGain 		
				       		 shePotsPptpProfileControlPortOGain         
				       		 shePotsPptpProfileControlPortFaxlvl
				       		 shePotsPptpProfileControlPortPotsType 			  
				       		 shePotsPptpProfileControlCid
				       		 shePotsPptpProfileControlPortPotsLineType        
				"
			::= { shePotsPptpProfileControl 1 }

		
		shePotsPptpProfileControlIndex OBJECT-TYPE
			SYNTAX Unsigned32
			MAX-ACCESS read-write
			STATUS current
			DESCRIPTION
				"shePotsPptpProfileIndex - each index uniquely identifies 
				one potsPptpProfile entry."
			::= { shePotsPptpProfileControl 2 }

		
		shePotsPptpProfileControlName OBJECT-TYPE
			SYNTAX DisplayString (SIZE (1..31))
			MAX-ACCESS read-write
			STATUS current
			DESCRIPTION
				"A describable name that uniquely identifies a profile entry of 
				this table.The profile name is user specified. A default profile 
				will always exist. This profile's name will be set to `DEFVAL'."
			::= { shePotsPptpProfileControl 3 }

		
		shePotsPptpProfileControlPortIGain OBJECT-TYPE
			SYNTAX INTEGER (-140..60)
			UNITS "0.1 dB"
			MAX-ACCESS read-write
			STATUS current
			DESCRIPTION
				"Input volume of AGLU port. 
				[value range]value =<-140 ~ 60> (default : 0)
				"
			::= { shePotsPptpProfileControl 4 }

		
		shePotsPptpProfileControlPortOGain OBJECT-TYPE
			SYNTAX INTEGER (-140..60)
			UNITS "0.1 dB"
			MAX-ACCESS read-write
			STATUS current
			DESCRIPTION
				"Output volume of AGLU port. 
				[value range]
				value =<-140 ~ 60> (default : 0)
				"
			::= { shePotsPptpProfileControl 5 }

		
		shePotsPptpProfileControlPortFaxlvl OBJECT-TYPE
			SYNTAX Unsigned32 (0..15)
			UNITS "dBm"
			MAX-ACCESS read-write
			STATUS current
			DESCRIPTION
				"Fax volume of AGLU port.          
				[value range]NUM = Volume value : level 1 ~ level 15 
				(step:1dBm, Default: 10, Disable:0)
				"
			::= { shePotsPptpProfileControl 6 }

		
		shePotsPptpProfileControlPortPotsType OBJECT-TYPE
			SYNTAX ShePotsPptpProfilePortPotsTypeType
			MAX-ACCESS read-write
			STATUS current
			DESCRIPTION
				" Pots type [value index]
				commonTelephone(1), 
				coinbox(2) 		
				highfeedcoinbox(3)"
			::= { shePotsPptpProfileControl 7 }

		
		shePotsPptpProfileControlStatus OBJECT-TYPE
			SYNTAX SheControlStatusType
			MAX-ACCESS read-only
			STATUS current
			DESCRIPTION
				"The status of a user command."
			::= { shePotsPptpProfileControl 8 }

		
		shePotsPptpProfileControlTimer OBJECT-TYPE
			SYNTAX Gauge32
			MAX-ACCESS read-only
			STATUS current
			DESCRIPTION
				"The maximum wait time for the manager for a 
				long running user command."
			::= { shePotsPptpProfileControl 9 }

		
		shePotsPptpProfileControlTimeStamp OBJECT-TYPE
			SYNTAX TimeTicks
			MAX-ACCESS read-only
			STATUS current
			DESCRIPTION
				"The time stamp of the last command (end of command)."
			::= { shePotsPptpProfileControl 10 }

		
		shePotsPptpProfileControlReqResult OBJECT-TYPE
			SYNTAX ShePotsControlRequestResultType
			MAX-ACCESS read-only
			STATUS current
			DESCRIPTION
				"The result of the last user command."
			::= { shePotsPptpProfileControl 11 }

		
		shePotsPptpProfileControlCid OBJECT-TYPE
			SYNTAX ShePotsPptpProfileCidType
			MAX-ACCESS read-write
			STATUS current
			DESCRIPTION
				"Use of Caller ID and can be set to the following four value. 		
				
				dtmf(0),
				fSKBellcore(1),   -- Bellcore      (default)                    
				fSKETSIRPAS(2),  -- ETSI specification RPAS type
				nTT(3)              
				fSKETSIDTAS(4),  -- ETSI specification DTAS type  
				fSKETSILRDTAS(5) -- ETSI specification LRDTAS type   
				
				Supported with R2.0M APS >= 38."
			::= { shePotsPptpProfileControl 12 }

		
		shePotsPptpProfileControlPortPotsLineType OBJECT-TYPE
			SYNTAX ShePotsPptpProfilePortPotsLineTypeType
			MAX-ACCESS read-write
			STATUS current
			DESCRIPTION
				" The three line types are defined by the resistance of pots line.
				longline(1),
				mediumline(2),
				shortline(3)
				
				Supported with R2.0M APS >= 38."
			::= { shePotsPptpProfileControl 13 }

		
		shePotsAnalogIfObjects OBJECT IDENTIFIER ::= { shePotsMib 2 }

		
		shePotsAnalogIfProfileTable OBJECT-TYPE
			SYNTAX SEQUENCE OF ShePotsAnalogIfProfileEntry
			MAX-ACCESS not-accessible
			STATUS current
			DESCRIPTION
				"This table contains attributes for each PotsAnalogIfProfile."
			::= { shePotsAnalogIfObjects 1 }

		
		shePotsAnalogIfProfileEntry OBJECT-TYPE
			SYNTAX ShePotsAnalogIfProfileEntry
			MAX-ACCESS not-accessible
			STATUS current
			DESCRIPTION
				"An entry represents a set of profile configurations
				in shePotsAnalogIfProfileTable.A default profile will always exist. 
				This profile's name will be set to `DEFVAL' and its parameters 
				will be set to vendor specific values.
				"
			INDEX { shePotsAnalogIfProfileIndex }
			::= { shePotsAnalogIfProfileTable 1 }

		
		ShePotsAnalogIfProfileEntry ::=
			SEQUENCE { 
				shePotsAnalogIfProfileIndex
					Unsigned32,
				shePotsAnalogIfProfileName
					DisplayString,
				shePotsAnalogIfProfileCid
					ShePotsAnalogIfProfileCidType,
				shePotsAnalogIfProfileHookflashMin
					Unsigned32,
				shePotsAnalogIfProfileHookflashMax
					Unsigned32,
				shePotsAnalogIfProfilePulseBreakMin
					Unsigned32,
				shePotsAnalogIfProfilePulseBreakMax
					Unsigned32,
				shePotsAnalogIfProfilePulseMakeMin
					Unsigned32,
				shePotsAnalogIfProfilePulseMakeMax
					Unsigned32,
				shePotsAnalogIfProfilePulseInterdigitMin
					Unsigned32,
				shePotsAnalogIfProfileMeteringPulseFreq
					ShePotsAnalogIfProfileMeteringPulseFreqType,
				shePotsAnalogIfProfileMeteringPulseInterval
					Unsigned32,
				shePotsAnalogIfProfileHookoffMin
					Unsigned32
			 }

		shePotsAnalogIfProfileIndex OBJECT-TYPE
			SYNTAX Unsigned32
			MAX-ACCESS read-only
			STATUS current
			DESCRIPTION
				"Table index. Each index uniquely identifies one PotsAnalogIfProfile."
			::= { shePotsAnalogIfProfileEntry 1 }

		
		shePotsAnalogIfProfileName OBJECT-TYPE
			SYNTAX DisplayString (SIZE (1..31))
			MAX-ACCESS read-only
			STATUS current
			DESCRIPTION
				"A describable name that uniquely identifies a profile entry 
				of this table.The profile name is user specified. A default profile 
				will always exist. This profile's name will be set to `DEFVAL'."
			::= { shePotsAnalogIfProfileEntry 2 }

		
		shePotsAnalogIfProfileCid OBJECT-TYPE
			SYNTAX ShePotsAnalogIfProfileCidType
			MAX-ACCESS read-only
			STATUS current
			DESCRIPTION
				"Use of Caller ID and can be set to the following four value. 		
				dtmf	(0),
				nonRpas(1),
				rpas	(2), 
				ntt	(3)
				
				non-RPAS: CLIP type include Bellcore, ETSI except timing RP-AS.
				RPAS: CLIP type of ETSI timing RP-AS.
				DTMF: CLIP type of DTMF.
				NTT: CLIP type conform to NTT specification.
				
				This Object is discarded.
				"
			DEFVAL { nonRpas }
			::= { shePotsAnalogIfProfileEntry 3 }

		
		shePotsAnalogIfProfileHookflashMin OBJECT-TYPE
			SYNTAX Unsigned32 (10..2000)
			UNITS "msec"
			MAX-ACCESS read-only
			STATUS current
			DESCRIPTION
				"recognize Hook-flash
				[value range]
				value = <10..2000> = Time in msec
				default(250)
				"
			DEFVAL { 250 }
			::= { shePotsAnalogIfProfileEntry 4 }

		
		shePotsAnalogIfProfileHookflashMax OBJECT-TYPE
			SYNTAX Unsigned32 (10..2000)
			UNITS "msec"
			MAX-ACCESS read-only
			STATUS current
			DESCRIPTION
				"Maximum hook flash threshold time to recognize Hook-flash
				[value range]  value = <10..2000> = Time in msec
				default(1300)"
			DEFVAL { 1300 }
			::= { shePotsAnalogIfProfileEntry 5 }

		
		shePotsAnalogIfProfilePulseBreakMin OBJECT-TYPE
			SYNTAX Unsigned32 (10..1000)
			MAX-ACCESS read-only
			STATUS current
			DESCRIPTION
				"PulseBreakMin for slot[AGLU]
				[value index]	NUM = value : 10~1000 
				Default: 33)"
			DEFVAL { 33 }
			::= { shePotsAnalogIfProfileEntry 6 }

		
		shePotsAnalogIfProfilePulseBreakMax OBJECT-TYPE
			SYNTAX Unsigned32 (10..1000)
			MAX-ACCESS read-only
			STATUS current
			DESCRIPTION
				"PulseBreakMax for slot[AGLU]
				[value index]NUM = value : 10~1000 
				(Default: 100)
				"
			DEFVAL { 100 }
			::= { shePotsAnalogIfProfileEntry 7 }

		
		shePotsAnalogIfProfilePulseMakeMin OBJECT-TYPE
			SYNTAX Unsigned32 (10..1000)
			MAX-ACCESS read-only
			STATUS current
			DESCRIPTION
				"PulseMakeMin for slot[AGLU]
				[value index]NUM = value : 10~1000 
				(Default: 17)
				"
			DEFVAL { 17 }
			::= { shePotsAnalogIfProfileEntry 8 }

		
		shePotsAnalogIfProfilePulseMakeMax OBJECT-TYPE
			SYNTAX Unsigned32 (10..1000)
			MAX-ACCESS read-only
			STATUS current
			DESCRIPTION
				"PulseMakeMax for slot[AGLU]
				[value index] NUM = value : 10~1000 
				(Default: 75) 
				"
			DEFVAL { 75 }
			::= { shePotsAnalogIfProfileEntry 9 }

		
		shePotsAnalogIfProfilePulseInterdigitMin OBJECT-TYPE
			SYNTAX Unsigned32 (10..1000)
			MAX-ACCESS read-only
			STATUS current
			DESCRIPTION
				"PulseInterdigitMin for slot[AGLU]
				[value index]NUM = value : 10~1000 
				(Default: 250)
				"
			DEFVAL { 250 }
			::= { shePotsAnalogIfProfileEntry 10 }

		
		shePotsAnalogIfProfileMeteringPulseFreq OBJECT-TYPE
			SYNTAX ShePotsAnalogIfProfileMeteringPulseFreqType
			MAX-ACCESS read-only
			STATUS current
			DESCRIPTION
				"The pulse frequency for metering.
				0 - freq12kHz
				1 - freq16kHz
				"
			DEFVAL { freq12kHz }
			::= { shePotsAnalogIfProfileEntry 11 }

		
		shePotsAnalogIfProfileMeteringPulseInterval OBJECT-TYPE
			SYNTAX Unsigned32 (20..65530)
			MAX-ACCESS read-only
			STATUS current
			DESCRIPTION
				"The pulse interval for metering.
				"
			DEFVAL { 20 }
			::= { shePotsAnalogIfProfileEntry 12 }

		
		shePotsAnalogIfProfileHookoffMin OBJECT-TYPE
			SYNTAX Unsigned32 (10..2000)
			UNITS "msec"
			MAX-ACCESS read-only
			STATUS current
			DESCRIPTION
				"Hook off min is the mininal time to regnonize and report  hook-off event. 
				It means that hook-off event will not be reported until the hook holding time
				exceeds this timer. Another senario to use this timer is when user push hook
				switch for a time a little bit more than hook-flash max but less than hook of 
				min, hiX will report hook-on, then report hook-off with a time interval
				equal hook of min. This keep the time interval not less than hook of min
				between hook-on and hook-off.
				[value range]
				value = <10..2000> = Time in msec
				default(80)
				hook flash min > hook off min
				
				Supported with R2.0M APS >= 38.
				"
			::= { shePotsAnalogIfProfileEntry 13 }

		
		shePotsAnalogIfProfileControl OBJECT IDENTIFIER ::= { shePotsAnalogIfObjects 2 }

		
		shePotsAnalogIfProfileControlRequest OBJECT-TYPE
			SYNTAX ShePotsControlRequestType
			MAX-ACCESS read-write
			STATUS current
			DESCRIPTION
				"The request of a user command.
				createPotsAnalogIfProfile  	(20),
					Must: shePotsAnalogIfProfileControlName			
					Optional:	shePotsAnalogIfProfileControlCid				       	           
				         		shePotsAnalogIfProfileControlHookflashMin 			        	
				         		shePotsAnalogIfProfileControlHookflashMax   		            
				         		shePotsAnalogIfProfileControlPulseBreakMin 		  
				     			shePotsAnalogIfProfileControlPulseBreakMax 		   
				     			shePotsAnalogIfProfileControlPulseMakeMin 			
				     			shePotsAnalogIfProfileControlPulseMakeMax  		
				     			shePotsAnalogIfProfileControlPulseInterdigitMin
				     			shePotsAnalogIfProfileControlMeteringPulseFreq
				     			shePotsAnalogIfProfileControlMeteringPulseInterval
				     			shePotsAnalogIfProfileControlHookoffMin
				
				     	  	
				modifyPotsAnalogIfProfile  	(21),
				        Must: shePotsAnalogIfProfileControlIndex
				        Optional:  shePotsAnalogIfProfileControlName 				
				         	       shePotsAnalogIfProfileControlCid				       	           
				         	       shePotsAnalogIfProfileControlHookflashMin 			        	
				         	       shePotsAnalogIfProfileControlHookflashMax   		            
				         	       shePotsAnalogIfProfileControlPulseBreakMin 		  
				     		       shePotsAnalogIfProfileControlPulseBreakMax 		   
				     		       shePotsAnalogIfProfileControlPulseMakeMin 			
				     		       shePotsAnalogIfProfileControlPulseMakeMax  		
				     		       shePotsAnalogIfProfileControlPulseInterdigitMin 
				     		       shePotsAnalogIfProfileControlMeteringPulseFreq
				     		       shePotsAnalogIfProfileControlMeteringPulseInterval
				     		       shePotsAnalogIfProfileControlHookoffMin
				     
				deletePotsAnalogIfProfile  	(22),
				      Must: shePotsAnalogIfProfileControlIndex			"
			::= { shePotsAnalogIfProfileControl 1 }

		
		shePotsAnalogIfProfileControlIndex OBJECT-TYPE
			SYNTAX Unsigned32
			MAX-ACCESS read-write
			STATUS current
			DESCRIPTION
				"sheVoipPotsAnalogIfProfileIndex"
			::= { shePotsAnalogIfProfileControl 2 }

		
		shePotsAnalogIfProfileControlName OBJECT-TYPE
			SYNTAX DisplayString (SIZE (1..31))
			MAX-ACCESS read-write
			STATUS current
			DESCRIPTION
				"A describable name that uniquely identifies 
				a profile entry of this table.The profile name 
				is user specified.A default profile will always exist. 
				This profile's name will be set to `DEFVAL'."
			::= { shePotsAnalogIfProfileControl 3 }

		
		shePotsAnalogIfProfileControlCid OBJECT-TYPE
			SYNTAX ShePotsAnalogIfProfileCidType
			MAX-ACCESS read-write
			STATUS current
			DESCRIPTION
				"Use of Caller ID and can be set to the following four value. 		
				dtmf	(0),
				non-rpas(1),
				rpas	(2), 
				ntt	(3)
				
				non-RPAS: CLIP type include Bellcore, ETSI except timing RP-AS.
				RPAS: CLIP type of ETSI timing RP-AS.
				DTMF: CLIP type of DTMF.
				NTT: CLIP type conform to NTT specification.
				
				This Object is discarded."
			::= { shePotsAnalogIfProfileControl 4 }

		
		shePotsAnalogIfProfileControlHookflashMin OBJECT-TYPE
			SYNTAX Unsigned32 (10..2000)
			UNITS "msec"
			MAX-ACCESS read-write
			STATUS current
			DESCRIPTION
				"recognize Hook-flash
				[value range]
				value = <10..2000> = Time in msec
				default(250)
				"
			::= { shePotsAnalogIfProfileControl 5 }

		
		shePotsAnalogIfProfileControlHookflashMax OBJECT-TYPE
			SYNTAX Unsigned32 (10..2000)
			UNITS "msec"
			MAX-ACCESS read-write
			STATUS current
			DESCRIPTION
				"Maximum hook flash threshold time to recognize Hook-flash
				[value range]  value = <10..2000> = Time in msec
				default(1300)
				 		"
			::= { shePotsAnalogIfProfileControl 6 }

		
		shePotsAnalogIfProfileControlPulseBreakMin OBJECT-TYPE
			SYNTAX Unsigned32 (10..1000)
			MAX-ACCESS read-write
			STATUS current
			DESCRIPTION
				"PulseBreakMin for slot[AGLU]
				[value index]	NUM = value : 10~1000 
				Default: 33)
				 		"
			::= { shePotsAnalogIfProfileControl 7 }

		
		shePotsAnalogIfProfileControlPulseBreakMax OBJECT-TYPE
			SYNTAX Unsigned32 (10..1000)
			MAX-ACCESS read-write
			STATUS current
			DESCRIPTION
				"PulseBreakMax for slot[AGLU]
				[value index]NUM = value : 10~1000 
				(Default: 100)
				"
			::= { shePotsAnalogIfProfileControl 8 }

		
		shePotsAnalogIfProfileControlPulseMakeMin OBJECT-TYPE
			SYNTAX Unsigned32 (10..1000)
			MAX-ACCESS read-write
			STATUS current
			DESCRIPTION
				"PulseMakeMin for slot[AGLU]
				[value index]NUM = value : 10~1000 
				(Default: 17)
				"
			::= { shePotsAnalogIfProfileControl 9 }

		
		shePotsAnalogIfProfileControlPulseMakeMax OBJECT-TYPE
			SYNTAX Unsigned32 (10..1000)
			MAX-ACCESS read-write
			STATUS current
			DESCRIPTION
				"PulseMakeMax for slot[AGLU]
				[value index] NUM = value : 10~1000 
				(Default: 75) 
				"
			::= { shePotsAnalogIfProfileControl 10 }

		
		shePotsAnalogIfProfileControlPulseInterdigitMin OBJECT-TYPE
			SYNTAX Unsigned32 (10..1000)
			MAX-ACCESS read-write
			STATUS current
			DESCRIPTION
				"PulseInterdigitMin for slot[AGLU]
				[value index]NUM = value : 10~1000 
				(Default: 250)
				"
			::= { shePotsAnalogIfProfileControl 11 }

		
		shePotsAnalogIfProfileControlMeteringPulseFreq OBJECT-TYPE
			SYNTAX ShePotsAnalogIfProfileMeteringPulseFreqType
			MAX-ACCESS read-write
			STATUS current
			DESCRIPTION
				"The pulse frequency for metering,used by amet package.
				0 - freq12kHz
				1 - freq16kHz
				"
			::= { shePotsAnalogIfProfileControl 12 }

		
		shePotsAnalogIfProfileControlMeteringPulseInterval OBJECT-TYPE
			SYNTAX Unsigned32 (20..65530)
			MAX-ACCESS read-write
			STATUS current
			DESCRIPTION
				"The pulse interval for metering.
				"
			::= { shePotsAnalogIfProfileControl 13 }

		
		shePotsAnalogIfProfileControlStatus OBJECT-TYPE
			SYNTAX SheControlStatusType
			MAX-ACCESS read-only
			STATUS current
			DESCRIPTION
				"The status of a user command."
			::= { shePotsAnalogIfProfileControl 14 }

		
		shePotsAnalogIfProfileControlTimer OBJECT-TYPE
			SYNTAX Gauge32
			MAX-ACCESS read-only
			STATUS current
			DESCRIPTION
				"The maximum wait time for the manager for a 
				long running user command."
			::= { shePotsAnalogIfProfileControl 15 }

		
		shePotsAnalogIfProfileControlTimeStamp OBJECT-TYPE
			SYNTAX TimeTicks
			MAX-ACCESS read-only
			STATUS current
			DESCRIPTION
				"The time stamp of the last command (end of command)."
			::= { shePotsAnalogIfProfileControl 16 }

		
		shePotsAnalogIfProfileControlReqResult OBJECT-TYPE
			SYNTAX ShePotsControlRequestResultType
			MAX-ACCESS read-only
			STATUS current
			DESCRIPTION
				"The result of the last user command."
			::= { shePotsAnalogIfProfileControl 17 }

		
		shePotsAnalogIfProfileControlHookoffMin OBJECT-TYPE
			SYNTAX Unsigned32 (10..2000)
			UNITS "msec"
			MAX-ACCESS read-write
			STATUS current
			DESCRIPTION
				"The Hook off min is the mininal time to regnonize and report  hook-off event. 
				It means that hook-off event will not be reported until the hook holding time
				 exceeds this timer. Another senario to use this timer is when user push hook
				 switch for a time a little bit more than hook-flash max but less than hook of 
				min, hiX will report hook-on, then report hook-off with a time interval
				 equal hook of min. This keep the time interval not less than hook of min
				 between hook-on and hook-off. 
				[value range]
				value = <10..2000> = Time in msec
				default(200)				 
				 
				Supported with R2.0M APS >= 38."
			::= { shePotsAnalogIfProfileControl 18 }

		
		shePotsConfigObjects OBJECT IDENTIFIER ::= { shePotsMib 3 }

		
		shePotsConfigTable OBJECT-TYPE
			SYNTAX SEQUENCE OF ShePotsConfigEntry
			MAX-ACCESS not-accessible
			STATUS current
			DESCRIPTION
				"The table contains all physical POTS interfaces 
				of the NE. The entries are automatically created/deleted by the NE."
			::= { shePotsConfigObjects 1 }

		
		shePotsConfigEntry OBJECT-TYPE
			SYNTAX ShePotsConfigEntry
			MAX-ACCESS not-accessible
			STATUS current
			DESCRIPTION
				"An entry in shePotsConfigTable."
			INDEX { ifIndex }
			::= { shePotsConfigTable 1 }

		
		ShePotsConfigEntry ::=
			SEQUENCE { 
				shePotsConfigPortStatus
					ShePotsConfigPortStatusType,
				shePotsConfigPotsPortPriorityLevel
					ShePotsConfigPotsPortPriorityLevelType,
				shePotsConfigPptpProfileIndex
					Unsigned32,
				shePotsConfigAnalogIfProfileIndex
					Unsigned32,
				shePotsConfigLastTest
					ShePotsConfigLastTestType,
				shePotsConfigILTFResult1
					Unsigned32,
				shePotsConfigILTFResult2
					Unsigned32,
				shePotsConfigILTFResult3
					Unsigned32,
				shePotsConfigAlarmSeverityIndex
					SheAlarmSevProfileIndex
			 }

		shePotsConfigPortStatus OBJECT-TYPE
			SYNTAX ShePotsConfigPortStatusType
			MAX-ACCESS read-only
			STATUS current
			DESCRIPTION
				"Port Status works as operStatus, standing for current operational 
				state of the interface. Its value is related with ifAdminStatus:
				down		(0),
				busy		(1),    
				idle		(2),
				testing		(3),
				testRing	(4),         
				testToneDial		(5),
				testToneRingback	(6),
				testToneBusy            (7),
				testToneStop		(8),
				receiverOffHook		(9),       			
				onOffHookSelfTest       (10),			
				telephoneNumTest	(11),			
				resistanceTest		(12),
				loopResistanceCurrentTest	(13),
				dcFeedVoltage			(14),	 
				dcFeedCurrent			(15), 
				openCircuitVoltage		(16),
				acVoltageTest			(17),
				batteryVoltageTest		(18),
				fault				(19),
				threeElementCapacitanceTest        (20)
				
				
				IfAdminStatus shows the desired state of the interface. If ifAdminStatus is down(2) then
				shePotsConfigPortStatus should be idle(2). If ifAdminStatus is changed to up(1) then 
				shePotsConfigPortStatus should remain in the idle(2) state till hookoff or ring event 
				trigger the state turning into up. Only when ifAdminStatus is set to testing can this 
				attribute be testing(3).The testing(3) state indicates that no operational packets can 
				be passed. A specific test starts only when the port is in testing state.
				"
			DEFVAL { down }
			::= { shePotsConfigEntry 1 }

		
		shePotsConfigPotsPortPriorityLevel OBJECT-TYPE
			SYNTAX ShePotsConfigPotsPortPriorityLevelType
			MAX-ACCESS read-only
			STATUS current
			DESCRIPTION
				"level1(1):Pot in level 1,any time it can call out. 
				level2(2):Pot in level 2,only calling resource under sheVoipCallPriorityProfileLevel1% 
				on AGLU slot, then can call out. 
				level3(3):Pot in level 3,only calling resource under sheVoipCallPriorityProfileLevel2% 
				on AGLU slot, then can call out. 
				"
			DEFVAL { level3 }
			::= { shePotsConfigEntry 2 }

		
		shePotsConfigPptpProfileIndex OBJECT-TYPE
			SYNTAX Unsigned32
			MAX-ACCESS read-only
			STATUS current
			DESCRIPTION
				"Equals to shePotsPptpProfileIndex. (default : 1)"
			DEFVAL { 1 }
			::= { shePotsConfigEntry 3 }

		
		shePotsConfigAnalogIfProfileIndex OBJECT-TYPE
			SYNTAX Unsigned32
			MAX-ACCESS read-only
			STATUS current
			DESCRIPTION
				"Equals to sheVoipPotsAnalogIfProfileIndex."
			DEFVAL { 1 }
			::= { shePotsConfigEntry 4 }

		
		shePotsConfigLastTest OBJECT-TYPE
			SYNTAX ShePotsConfigLastTestType
			MAX-ACCESS read-only
			STATUS current
			DESCRIPTION
				"Line test that has done.
				noTest             (0),
				testRing           (1),
				testToneDial       (2),
				testToneRingback   (3),
				testToneBusy       (4),
				testToneStop       (5),
				receiverOffHook    (6),
				onOffHookSelfTest  (7),
				telephoneNumTest   (8),
				resistanceTest     (9),
				loopResistanceCurrentTest (10),
				dcFeedVoltage      (11),
				dcFeedCurrent      (12),
				openCircuitVoltage (13),
				acVoltageTest      (14),
				batteryVoltageTest (15),
				threeElementCapacitanceTest (16)"
			::= { shePotsConfigEntry 5 }

		
		shePotsConfigILTFResult1 OBJECT-TYPE
			SYNTAX Unsigned32
			MAX-ACCESS read-only
			STATUS current
			DESCRIPTION
				"This attribute is only used to save Integrated Line Test Function result.
				testRing: Ring Pass
				resistanceTest: Tip_gnd   value rang: 200000000 ~ -20000000 /100 
				0 impedance not measured
				> 200000000 open
				< -200000000 short
				
				dcFeedVoltage: Voltage 
				dcFeedCurrent: Current
				openCircuitVoltage:  tip_voltage ;
				loopResistance: Loop resistance test value;
				receiverOffHook:Receiver_offhook on(0), off(1);  
				onOffHookSelfTest: unknown(0)
					           abort  (1)
					           hwfault (2)
					           passed  (3)
				acVoltageTest: Tip-lead voltage *100
				batteryVoltageTest: battery voltage
				threeElementCapacitanceTest : Cctg	// Tip-to-Ground capacitance (nFarads) "
			DEFVAL { 1 }
			::= { shePotsConfigEntry 6 }

		
		shePotsConfigILTFResult2 OBJECT-TYPE
			SYNTAX Unsigned32
			MAX-ACCESS read-only
			STATUS current
			DESCRIPTION
				"This attribute is only used to save Integrated Line Test Function result. 
				testRing: Ring Interception  0:failed, 1:succeeded.
				resistanceTest: Ring_gnd value rang: 200000000 ~ -20000000 /100
				  0 impedance not measured
				  > 200000000 open
				  < -200000000 short
				dcFeedVoltage:
				dcFeedCurrent: 
				openCircuitVoltage:  Ring_voltage ;
				loopResistanceCurrentTest:  Loop current test value
				receiverOffHook:  
				onOffHookSelftest:
				acVoltageTest: Ring-lead voltage * 100
				threeElementCapacitanceTest :  Ccrg // Ring-to-Ground capacitance (nFarads)"
			DEFVAL { 1 }
			::= { shePotsConfigEntry 7 }

		
		shePotsConfigILTFResult3 OBJECT-TYPE
			SYNTAX Unsigned32
			MAX-ACCESS read-only
			STATUS current
			DESCRIPTION
				"This attribute is only used to save Integrated Line Test Function result. 
				testRing: Ring Voltage
				resistanceTest: Tip_ring   value rang: 200000000 ~ -20000000 /100
				  0 impedance not measured
				  > 200000000 open
				  < -200000000 short
				dcFeedVoltage: 
				dcFeedCurrent: 
				openCircuitVoltage:  Tip_ring_voltage  ;
				loopResistance:
				receiverOffHook:  
				onOffHookSelftest:
				acVoltageTest: Differential voltage *100
				threeElementCapacitanceTest :  Cctr   // Tip-to-Ring capacitance (nFarads) "
			DEFVAL { 1 }
			::= { shePotsConfigEntry 8 }

		
		shePotsConfigAlarmSeverityIndex OBJECT-TYPE
			SYNTAX SheAlarmSevProfileIndex
			MAX-ACCESS read-only
			STATUS current
			DESCRIPTION
				"Equals to sheAlarmSevProfileIndex in sheAlarmSeverityProfileTable, sheAlarmingMib."
			DEFVAL { 1 }
			::= { shePotsConfigEntry 9 }

		
		shePotsConfigControl OBJECT IDENTIFIER ::= { shePotsConfigObjects 2 }

		
		shePotsConfigControlRequest OBJECT-TYPE
			SYNTAX ShePotsControlRequestType
			MAX-ACCESS read-write
			STATUS current
			DESCRIPTION
				"The request of a user command.
				modifyPotsConfig    (30)
				  Must:  shePotsConfigControlIfIndexBitMask
				  	  shePotsConfigControlPotsPortPriorityLevel
				  	  shePotsConfigControlPptpProfileIndex
					  shePotsConfigControlAnalogIfProfileIndex
					  shePotsConfigControlAlarmSeverityIndex
				
				testRing		(31),
				  Must:  shePotsConfigControlIfIndexBitMask
				
				testToneDial		(32),
				  Must:  shePotsConfigControlIfIndexBitMask
				
				testToneRingback			(33)
				  Must:  shePotsConfigControlIfIndexBitMask
				
				testToneBusy        (34),
				  Must:  shePotsConfigControlIfIndexBitMask
				
				testToneStop       (35)
				  Must:  shePotsConfigControlIfIndexBitMask
				
				The following are long-running commands that are only used to start the tests.
				Traps are sent out with the testing results when tests are finished.
				testRing			(31)
				  Must:  shePotsConfigControlIfIndexBitMask
				
				receiverOffHook		(40)
				  Must:  shePotsConfigControlIfIndexBitMask
				
				onOffHookSelfTest		(41)
				  Must:  shePotsConfigControlIfIndexBitMask	 
				
				telephoneNumTest		(42)  
				  Must:  shePotsConfigControlIfIndexBitMask
				
				resistanceTest	(45) 
				  Must:  shePotsConfigControlIfIndexBitMask
				
				loopResistanceCurrentTest		(46) 
				  Must:  shePotsConfigControlIfIndexBitMask
				
				dcFeedVoltage		(47)  
				  Must:  shePotsConfigControlIfIndexBitMask
				
				dcFeedCurrent   (48)
				  Must:  shePotsConfigControlIfIndexBitMask
				
				openCircuitVoltage  (49)
				  Must:  shePotsConfigControlIfIndexBitMask
				
				acVoltageTest				(50),
				  Must:  shePotsConfigControlIfIndexBitMask
				
				batteryVoltageTest			(51)
				  Must:  shePotsConfigControlIfIndexBitMask
				
				Supported with R2.0M APS >= 38:
				threeElementCapacitanceTest (52)     
				   Must:shePotsConfigControlIfIndexBitMask
				"
			::= { shePotsConfigControl 1 }

		
		shePotsConfigControlIfIndexBitMask OBJECT-TYPE
			SYNTAX OCTET STRING (SIZE (256))
			MAX-ACCESS read-write
			STATUS current
			DESCRIPTION
				"IfIndex list, represented by 256 bytes. Each bit stands for an ifIndex that marks
				a port."
			::= { shePotsConfigControl 2 }

		
		shePotsConfigControlPotsPortPriorityLevel OBJECT-TYPE
			SYNTAX ShePotsConfigPotsPortPriorityLevelType
			MAX-ACCESS read-write
			STATUS current
			DESCRIPTION
				"level1(1), 
				level2(2), 
				level3(3) 
				 (default : 3) 
				 "
			::= { shePotsConfigControl 3 }

		
		shePotsConfigControlPptpProfileIndex OBJECT-TYPE
			SYNTAX Unsigned32
			MAX-ACCESS read-write
			STATUS current
			DESCRIPTION
				"Equals to shePotsPptpProfileIndex.
				"
			::= { shePotsConfigControl 4 }

		
		shePotsConfigControlAnalogIfProfileIndex OBJECT-TYPE
			SYNTAX Unsigned32
			MAX-ACCESS read-write
			STATUS current
			DESCRIPTION
				"Equals to shePotsAnalogIfProfileIndex.
				"
			::= { shePotsConfigControl 5 }

		
		shePotsConfigControlStatus OBJECT-TYPE
			SYNTAX SheControlStatusType
			MAX-ACCESS read-only
			STATUS current
			DESCRIPTION
				"The status of a user command."
			::= { shePotsConfigControl 6 }

		
		shePotsConfigControlTimer OBJECT-TYPE
			SYNTAX Gauge32
			MAX-ACCESS read-only
			STATUS current
			DESCRIPTION
				"The maximum wait time for the manager for a 
				long running user command."
			::= { shePotsConfigControl 7 }

		
		shePotsConfigControlTimeStamp OBJECT-TYPE
			SYNTAX TimeTicks
			MAX-ACCESS read-only
			STATUS current
			DESCRIPTION
				"The time stamp of the last command (end of command)."
			::= { shePotsConfigControl 8 }

		
		shePotsConfigControlReqResult OBJECT-TYPE
			SYNTAX ShePotsControlRequestResultType
			MAX-ACCESS read-only
			STATUS current
			DESCRIPTION
				"The result of the last user command."
			::= { shePotsConfigControl 9 }

		
		shePotsConfigControlAlarmSeverityIndex OBJECT-TYPE
			SYNTAX SheAlarmSevProfileIndex
			MAX-ACCESS read-write
			STATUS current
			DESCRIPTION
				"Equals to sheAlarmSevProfileIndex in sheAlarmSeverityProfileTable, sheAlarmingMib."
			::= { shePotsConfigControl 10 }

		
		shePotsNotifications OBJECT IDENTIFIER ::= { shePotsMib 4 }

		
		shePotsPptpEvents OBJECT IDENTIFIER ::= { shePotsNotifications 1 }

		
		shePotsPptpProfileCreatedTrap NOTIFICATION-TYPE
			OBJECTS { shePotsPptpProfileIndex, shePotsPptpProfileName, shePotsPptpProfilePortIGain, shePotsPptpProfilePortOGain, shePotsPptpProfilePortFaxlvl, 
				shePotsPptpProfilePortPotsType, shePotsPptpProfileControlTimeStamp, shePotsPptpProfileCid, shePotsPptpProfilePortPotsLineType }
			STATUS current
			DESCRIPTION 
				"Indicates that PotsPptpProfile is created successfully."
			::= { shePotsPptpEvents 1 }

		
		shePotsPptpProfileDeletedTrap NOTIFICATION-TYPE
			OBJECTS { shePotsPptpProfileIndex, shePotsPptpProfileName, shePotsPptpProfileControlTimeStamp }
			STATUS current
			DESCRIPTION 
				"Indicates that PotsPptpProfile is deleted successfully."
			::= { shePotsPptpEvents 2 }

		
		shePotsPptpProfileModifiedTrap NOTIFICATION-TYPE
			OBJECTS { shePotsPptpProfileIndex, shePotsPptpProfileName, shePotsPptpProfilePortIGain, shePotsPptpProfilePortOGain, shePotsPptpProfilePortFaxlvl, 
				shePotsPptpProfilePortPotsType, shePotsPptpProfileControlTimeStamp, shePotsPptpProfileCid, shePotsPptpProfilePortPotsLineType }
			STATUS current
			DESCRIPTION 
				"Indicates that PotsPptpProfile is modified successfully."
			::= { shePotsPptpEvents 3 }

		
		shePotsAnalogIfEvents OBJECT IDENTIFIER ::= { shePotsNotifications 2 }

		
		shePotsAnalogIfProfileCreatedTrap NOTIFICATION-TYPE
			OBJECTS { shePotsAnalogIfProfileIndex, shePotsAnalogIfProfileName, shePotsAnalogIfProfileCid, shePotsAnalogIfProfileHookflashMin, shePotsAnalogIfProfileHookflashMax, 
				shePotsAnalogIfProfilePulseBreakMin, shePotsAnalogIfProfilePulseBreakMax, shePotsAnalogIfProfilePulseMakeMin, shePotsAnalogIfProfilePulseMakeMax, shePotsAnalogIfProfilePulseInterdigitMin, 
				shePotsAnalogIfProfileMeteringPulseFreq, shePotsAnalogIfProfileMeteringPulseInterval, shePotsAnalogIfProfileControlTimeStamp, shePotsAnalogIfProfileHookoffMin }
			STATUS current
			DESCRIPTION 
				"Indicates that AnalogIfProfile entry is created successfully."
			::= { shePotsAnalogIfEvents 1 }

		
		shePotsAnalogIfProfileDeletedTrap NOTIFICATION-TYPE
			OBJECTS { shePotsAnalogIfProfileIndex, shePotsAnalogIfProfileName, shePotsAnalogIfProfileControlTimeStamp }
			STATUS current
			DESCRIPTION 
				"Indicates that AnalogIfProfile entry is deleted successfully."
			::= { shePotsAnalogIfEvents 2 }

		
		shePotsAnalogIfProfileModifiedTrap NOTIFICATION-TYPE
			OBJECTS { shePotsAnalogIfProfileIndex, shePotsAnalogIfProfileName, shePotsAnalogIfProfileCid, shePotsAnalogIfProfileHookflashMin, shePotsAnalogIfProfileHookflashMax, 
				shePotsAnalogIfProfilePulseBreakMin, shePotsAnalogIfProfilePulseBreakMax, shePotsAnalogIfProfilePulseMakeMin, shePotsAnalogIfProfilePulseMakeMax, shePotsAnalogIfProfilePulseInterdigitMin, 
				shePotsAnalogIfProfileMeteringPulseFreq, shePotsAnalogIfProfileMeteringPulseInterval, shePotsAnalogIfProfileControlTimeStamp, shePotsAnalogIfProfileHookoffMin }
			STATUS current
			DESCRIPTION 
				"Indicates that AnalogIfProfile entry is modified successfully."
			::= { shePotsAnalogIfEvents 3 }

		
		shePotsConfigEvents OBJECT IDENTIFIER ::= { shePotsNotifications 3 }

		
		shePotsConfigModifiedTrap NOTIFICATION-TYPE
			OBJECTS { ifIndex, shePotsConfigPotsPortPriorityLevel, shePotsConfigPptpProfileIndex, shePotsConfigAnalogIfProfileIndex, shePotsConfigAlarmSeverityIndex, 
				shePotsConfigControlIfIndexBitMask, shePotsConfigControlTimeStamp }
			STATUS current
			DESCRIPTION 
				"Indicates that PotsConfig entry is modified successfully."
			::= { shePotsConfigEvents 1 }

		
		shePotsConfigTestFinishedTrap NOTIFICATION-TYPE
			OBJECTS { ifIndex, shePotsConfigPortStatus, shePotsConfigLastTest, shePotsConfigILTFResult1, shePotsConfigILTFResult2, 
				shePotsConfigILTFResult3, shePotsConfigControlReqResult, shePotsConfigControlTimeStamp }
			STATUS current
			DESCRIPTION 
				"Trap is sent out when line test is finished."
			::= { shePotsConfigEvents 2 }

		
		shePotsConfigPortStatusChangedTrap NOTIFICATION-TYPE
			OBJECTS { ifIndex, shePotsConfigPortStatus, shePotsConfigControlTimeStamp }
			STATUS current
			DESCRIPTION 
				"This trap is sent out only when port status is changed between two of these three
				status - up, down and testing."
			::= { shePotsConfigEvents 3 }

		
		shePotsAlarms OBJECT IDENTIFIER ::= { shePotsNotifications 4 }

		
		shePortsThermFltDetectAlarm NOTIFICATION-TYPE
			OBJECTS { sheAlarmTimeAndDate, sheAlarmReportingSource, sheAlarmReportingSourceType, sheAlarmSeverity }
			STATUS current
			DESCRIPTION 
				"Alarm raised when thermal fault is detected."
			::= { shePotsAlarms 1 }

		
		shePortsDCFltDetectAlarm NOTIFICATION-TYPE
			OBJECTS { sheAlarmTimeAndDate, sheAlarmReportingSource, sheAlarmReportingSourceType, sheAlarmSeverity }
			STATUS current
			DESCRIPTION 
				"Alarm raised when dc fault is detected."
			::= { shePotsAlarms 2 }

		
		shePortsACFltDetectAlarm NOTIFICATION-TYPE
			OBJECTS { sheAlarmTimeAndDate, sheAlarmReportingSource, sheAlarmReportingSourceType, sheAlarmSeverity }
			STATUS current
			DESCRIPTION 
				"Alarm raised when ac fault is detected."
			::= { shePotsAlarms 3 }

		
		shePortsGkeyDetectAlarm NOTIFICATION-TYPE
			OBJECTS { sheAlarmTimeAndDate, sheAlarmReportingSource, sheAlarmReportingSourceType, sheAlarmSeverity }
			STATUS current
			DESCRIPTION 
				"Alarm raised when ground key is detected."
			::= { shePotsAlarms 4 }

		
-- added by cn2zj090 on 2007-07-12 for sip feature    
-- shePotsSipUserDataConfig Modify trap
		shePotsSipUserDataEvents OBJECT IDENTIFIER ::= { shePotsNotifications 5 }

		
		shePotsSipUserDataConfigModifiedTrap NOTIFICATION-TYPE
			OBJECTS { ifIndex, shePotsSipUserDataConfigUserName, shePotsSipUserDataConfigPassword, shePotsSipUserDataConfigDmIndex, shePotsSipUserDataConfigCallingLineIdPresentation, 
				shePotsSipUserDataConfigCallCompletiontoBusySubscriber, shePotsSipUserDataConfigCallWaiting, shePotsSipUserDataConfigOutgoingCallBarring, shePotsSipUserDataConfigThreePartyConference, shePotsSipUserDataConfigCallHold, 
				shePotsSipUserDataConfigDialTimeOut, shePotsSipUserDataConfigBusyTimeOut, shePotsSipUserDataConfigHowlerTimeOut, shePotsSipUserDataConfigRegisterStatus, shePotsSipUserDataConfigControlIfIndexBitMask, 
				shePotsSipUserDataConfigControlTimeStamp }
			STATUS current
			DESCRIPTION 
				"Indicates that SipUserDataConfig entry is modified successfully."
			::= { shePotsSipUserDataEvents 1 }

		
-- added by cn2zj090 on 2007-07-12
		shePotsSipUserDataObjects OBJECT IDENTIFIER ::= { shePotsMib 5 }

		
-- shePotsSipUserDataConfigTable 				
		shePotsSipUserDataConfigTable OBJECT-TYPE
			SYNTAX SEQUENCE OF ShePotsSipUserDataConfigEntry
			MAX-ACCESS not-accessible
			STATUS current
			DESCRIPTION
				"This table contains attributes for each pots sip user data profile."
			::= { shePotsSipUserDataObjects 1 }

		
		shePotsSipUserDataConfigEntry OBJECT-TYPE
			SYNTAX ShePotsSipUserDataConfigEntry
			MAX-ACCESS not-accessible
			STATUS current
			DESCRIPTION
				"An entry represents a set of profile configurations
				in shePotsSipUserDataConfigTable.A default profile will always exist. 
				This profile's name will be set to `DEFVAL' and its parameters 
				will be set to vendor specific values.
				"
			INDEX { ifIndex }
			::= { shePotsSipUserDataConfigTable 1 }

		
		ShePotsSipUserDataConfigEntry ::=
			SEQUENCE { 
				shePotsSipUserDataConfigUserName
					DisplayString,
				shePotsSipUserDataConfigPassword
					DisplayString,
				shePotsSipUserDataConfigDmIndex
					Unsigned32,
				shePotsSipUserDataConfigCallingLineIdPresentation
					ShePotsSipUserDataConfigType,
				shePotsSipUserDataConfigCallCompletiontoBusySubscriber
					ShePotsSipUserDataConfigType,
				shePotsSipUserDataConfigCallWaiting
					ShePotsSipUserDataConfigType,
				shePotsSipUserDataConfigOutgoingCallBarring
					ShePotsSipUserDataConfigType,
				shePotsSipUserDataConfigThreePartyConference
					ShePotsSipUserDataConfigType,
				shePotsSipUserDataConfigCallHold
					ShePotsSipUserDataConfigType,
				shePotsSipUserDataConfigDialTimeOut
					Unsigned32,
				shePotsSipUserDataConfigBusyTimeOut
					Unsigned32,
				shePotsSipUserDataConfigHowlerTimeOut
					Unsigned32,
				shePotsSipUserDataConfigRegisterStatus
					ShePotsSipUserDataRegisterStatusType
			 }

		shePotsSipUserDataConfigUserName OBJECT-TYPE
			SYNTAX DisplayString
			MAX-ACCESS read-only
			STATUS current
			DESCRIPTION
				"The assigned subscribers phonenumber.
				Example: +49891234567"
			::= { shePotsSipUserDataConfigEntry 1 }

		
		shePotsSipUserDataConfigPassword OBJECT-TYPE
			SYNTAX DisplayString
			MAX-ACCESS read-only
			STATUS current
			DESCRIPTION
				"password. "
			::= { shePotsSipUserDataConfigEntry 2 }

		
		shePotsSipUserDataConfigDmIndex OBJECT-TYPE
			SYNTAX Unsigned32
			MAX-ACCESS read-only
			STATUS current
			DESCRIPTION
				"sheVoipDigitMapProfileIndex in sheVoipDigitMapProfileTable."
			::= { shePotsSipUserDataConfigEntry 3 }

		
		shePotsSipUserDataConfigCallingLineIdPresentation OBJECT-TYPE
			SYNTAX ShePotsSipUserDataConfigType
			MAX-ACCESS read-only
			STATUS current
			DESCRIPTION
				"Calling Line Identification Presentation.
				[value range] value =<0 ~ 1> (default : 0)"
			DEFVAL { 0 }
			::= { shePotsSipUserDataConfigEntry 4 }

		
		shePotsSipUserDataConfigCallCompletiontoBusySubscriber OBJECT-TYPE
			SYNTAX ShePotsSipUserDataConfigType
			MAX-ACCESS read-only
			STATUS current
			DESCRIPTION
				"Call Completion on Busy Subscriber.
				[value range] value =<0 ~ 1> (default : 0)"
			DEFVAL { 0 }
			::= { shePotsSipUserDataConfigEntry 5 }

		
		shePotsSipUserDataConfigCallWaiting OBJECT-TYPE
			SYNTAX ShePotsSipUserDataConfigType
			MAX-ACCESS read-only
			STATUS current
			DESCRIPTION
				"Call Waiting.[value range] value =<0 ~ 1> (default : 0)"
			DEFVAL { 0 }
			::= { shePotsSipUserDataConfigEntry 6 }

		
		shePotsSipUserDataConfigOutgoingCallBarring OBJECT-TYPE
			SYNTAX ShePotsSipUserDataConfigType
			MAX-ACCESS read-only
			STATUS current
			DESCRIPTION
				"Outgoing Call Barring.[value range] value =<0 ~ 1> (default : 0)"
			DEFVAL { 0 }
			::= { shePotsSipUserDataConfigEntry 7 }

		
		shePotsSipUserDataConfigThreePartyConference OBJECT-TYPE
			SYNTAX ShePotsSipUserDataConfigType
			MAX-ACCESS read-only
			STATUS current
			DESCRIPTION
				"Three Party Conference.[value range] value =<0 ~ 1> (default : 0)"
			DEFVAL { 0 }
			::= { shePotsSipUserDataConfigEntry 8 }

		
		shePotsSipUserDataConfigCallHold OBJECT-TYPE
			SYNTAX ShePotsSipUserDataConfigType
			MAX-ACCESS read-only
			STATUS current
			DESCRIPTION
				"Call Hold / Enquiry. Call Hold/Release, Toggle, Consultation.
				[value range] value =<0 ~ 1> (default : 0)"
			DEFVAL { 0 }
			::= { shePotsSipUserDataConfigEntry 9 }

		
		shePotsSipUserDataConfigDialTimeOut OBJECT-TYPE
			SYNTAX Unsigned32 (0..60)
			MAX-ACCESS read-only
			STATUS current
			DESCRIPTION
				"dial_tone timer: defined the length of the dial_tone length when no digit receive.
				(default : 10)"
			DEFVAL { 10 }
			::= { shePotsSipUserDataConfigEntry 10 }

		
		shePotsSipUserDataConfigBusyTimeOut OBJECT-TYPE
			SYNTAX Unsigned32 (0..60)
			MAX-ACCESS read-only
			STATUS current
			DESCRIPTION
				"busy_tone timer:defined the length of the busy_tone.
				(default : 10)"
			DEFVAL { 10 }
			::= { shePotsSipUserDataConfigEntry 11 }

		
		shePotsSipUserDataConfigHowlerTimeOut OBJECT-TYPE
			SYNTAX Unsigned32 (0..60)
			MAX-ACCESS read-only
			STATUS current
			DESCRIPTION
				"howler timer:defined the length of the howler.
				(default : 10)"
			DEFVAL { 10 }
			::= { shePotsSipUserDataConfigEntry 12 }

		
		shePotsSipUserDataConfigRegisterStatus OBJECT-TYPE
			SYNTAX ShePotsSipUserDataRegisterStatusType
			MAX-ACCESS read-only
			STATUS current
			DESCRIPTION
				"register status (default : 0)"
			DEFVAL { 0 }
			::= { shePotsSipUserDataConfigEntry 13 }

		
--  shePotsSipUserDataConfigControl group
		shePotsSipUserDataConfigControl OBJECT IDENTIFIER ::= { shePotsSipUserDataObjects 2 }

		
		shePotsSipUserDataConfigControlRequest OBJECT-TYPE
			SYNTAX ShePotsControlRequestType
			MAX-ACCESS read-write
			STATUS current
			DESCRIPTION
				"The request of a user command.
				modifyPotsSipUserData    (53)
				   Must:	shePotsSipUserConfigControlIfIndexBitMask   
				   Optional:
				            shePotsSipUserDataConfigControlUserName	
				            shePotsSipUserDataConfigControlPassword 
				            shePotsSipUserDataConfigControlDmIndex
				            shePotsSipUserDataConfigControlCallingLineIdPresentation
				            shePotsSipUserDataConfigControlCallCompletiontoBusySubscriber 
				            shePotsSipUserDataConfigControlCallWaiting
				            shePotsSipUserDataConfigControlOutgoingCallBarring
				            shePotsSipUserDataConfigControlThreePartyConference
				            shePotsSipUserDataConfigControlCallHold
				            shePotsSipUserDataConfigControlDialTimeOut
				            shePotsSipUserDataConfigControlBusyTimeOut
				            shePotsSipUserDataConfigControlHowlerTimeOut		   
				          "
			::= { shePotsSipUserDataConfigControl 1 }

		
		shePotsSipUserDataConfigControlStatus OBJECT-TYPE
			SYNTAX SheControlStatusType
			MAX-ACCESS read-only
			STATUS current
			DESCRIPTION
				"The status of a user command."
			::= { shePotsSipUserDataConfigControl 2 }

		
		shePotsSipUserDataConfigControlTimer OBJECT-TYPE
			SYNTAX Gauge32
			MAX-ACCESS read-only
			STATUS current
			DESCRIPTION
				"The maximum wait time for the manager for a 
				long running user command."
			::= { shePotsSipUserDataConfigControl 3 }

		
		shePotsSipUserDataConfigControlTimeStamp OBJECT-TYPE
			SYNTAX TimeTicks
			MAX-ACCESS read-only
			STATUS current
			DESCRIPTION
				"The time stamp of the last command (end of command)."
			::= { shePotsSipUserDataConfigControl 4 }

		
		shePotsSipUserDataConfigControlReqResult OBJECT-TYPE
			SYNTAX ShePotsControlRequestResultType
			MAX-ACCESS read-only
			STATUS current
			DESCRIPTION
				"The result of the last user command."
			::= { shePotsSipUserDataConfigControl 5 }

		
		shePotsSipUserDataConfigControlIfIndexBitMask OBJECT-TYPE
			SYNTAX OCTET STRING (SIZE (256))
			MAX-ACCESS read-write
			STATUS current
			DESCRIPTION
				"IfIndex list, represented by 256 bytes. Each bit stands for an ifIndex that marks
				a port."
			::= { shePotsSipUserDataConfigControl 6 }

		
		shePotsSipUserDataConfigControlUserName OBJECT-TYPE
			SYNTAX DisplayString
			MAX-ACCESS read-write
			STATUS current
			DESCRIPTION
				"The assigned subscribers phonenumber."
			::= { shePotsSipUserDataConfigControl 7 }

		
		shePotsSipUserDataConfigControlPassword OBJECT-TYPE
			SYNTAX DisplayString
			MAX-ACCESS read-write
			STATUS current
			DESCRIPTION
				"password."
			::= { shePotsSipUserDataConfigControl 8 }

		
		shePotsSipUserDataConfigControlDmIndex OBJECT-TYPE
			SYNTAX Gauge32
			MAX-ACCESS read-write
			STATUS current
			DESCRIPTION
				"sheVoipDigitMapProfileIndex in sheVoipDigitMapProfileTable."
			::= { shePotsSipUserDataConfigControl 9 }

		
		shePotsSipUserDataConfigControlCallingLineIdPresentation OBJECT-TYPE
			SYNTAX ShePotsSipUserDataConfigType
			MAX-ACCESS read-write
			STATUS current
			DESCRIPTION
				"Calling Line Identification Presentation."
			::= { shePotsSipUserDataConfigControl 10 }

		
		shePotsSipUserDataConfigControlCallCompletiontoBusySubscriber OBJECT-TYPE
			SYNTAX ShePotsSipUserDataConfigType
			MAX-ACCESS read-write
			STATUS current
			DESCRIPTION
				"Call Completion on Busy Subscriber."
			::= { shePotsSipUserDataConfigControl 11 }

		
		shePotsSipUserDataConfigControlCallWaiting OBJECT-TYPE
			SYNTAX ShePotsSipUserDataConfigType
			MAX-ACCESS read-write
			STATUS current
			DESCRIPTION
				"Call Waiting."
			::= { shePotsSipUserDataConfigControl 12 }

		
		shePotsSipUserDataConfigControlOutgoingCallBarring OBJECT-TYPE
			SYNTAX ShePotsSipUserDataConfigType
			MAX-ACCESS read-write
			STATUS current
			DESCRIPTION
				"Outgoing Call Barring."
			::= { shePotsSipUserDataConfigControl 13 }

		
		shePotsSipUserDataConfigControlThreePartyConference OBJECT-TYPE
			SYNTAX ShePotsSipUserDataConfigType
			MAX-ACCESS read-write
			STATUS current
			DESCRIPTION
				" Three Party Conference."
			::= { shePotsSipUserDataConfigControl 14 }

		
		shePotsSipUserDataConfigControlCallHold OBJECT-TYPE
			SYNTAX ShePotsSipUserDataConfigType
			MAX-ACCESS read-write
			STATUS current
			DESCRIPTION
				" Call Hold / Enquiry. Call Hold/Release, Toggle, Consultation."
			::= { shePotsSipUserDataConfigControl 15 }

		
		shePotsSipUserDataConfigControlDialTimeOut OBJECT-TYPE
			SYNTAX Unsigned32 (0..60)
			MAX-ACCESS read-write
			STATUS current
			DESCRIPTION
				"dial_tone timer: defined the length of the dial_tone length when no digit receive."
			::= { shePotsSipUserDataConfigControl 16 }

		
		shePotsSipUserDataConfigControlBusyTimeOut OBJECT-TYPE
			SYNTAX Unsigned32 (0..60)
			MAX-ACCESS read-write
			STATUS current
			DESCRIPTION
				"busy_tone timer:defined the length of the busy_tone."
			::= { shePotsSipUserDataConfigControl 17 }

		
		shePotsSipUserDataConfigControlHowlerTimeOut OBJECT-TYPE
			SYNTAX Unsigned32 (0..60)
			MAX-ACCESS read-write
			STATUS current
			DESCRIPTION
				"howler timer:defined the length of the howler. "
			::= { shePotsSipUserDataConfigControl 18 }

		
		shePotsConformance OBJECT IDENTIFIER ::= { shePotsMib 100 }

		
		shePotsCompliances OBJECT IDENTIFIER ::= { shePotsConformance 1 }

		
		shePotsMibCompliance MODULE-COMPLIANCE
			STATUS current
			DESCRIPTION 
				"Description."
			MODULE -- this module
				MANDATORY-GROUPS { shePotsGroup, shePotsControlGroup, shePotsNotificationGroup }
			::= { shePotsCompliances 1 }

		
		shePotsGroups OBJECT IDENTIFIER ::= { shePotsConformance 2 }

		
		shePotsGroup OBJECT-GROUP
			OBJECTS { shePotsPptpProfileIndex, shePotsPptpProfileName, shePotsPptpProfilePortIGain, shePotsPptpProfilePortOGain, shePotsPptpProfilePortFaxlvl, 
				shePotsPptpProfilePortPotsType, shePotsAnalogIfProfileIndex, shePotsAnalogIfProfileName, shePotsAnalogIfProfileCid, shePotsAnalogIfProfileHookflashMin, 
				shePotsAnalogIfProfileHookflashMax, shePotsAnalogIfProfilePulseBreakMin, shePotsAnalogIfProfilePulseBreakMax, shePotsAnalogIfProfilePulseMakeMin, shePotsAnalogIfProfilePulseMakeMax, 
				shePotsAnalogIfProfilePulseInterdigitMin, shePotsAnalogIfProfileMeteringPulseFreq, shePotsAnalogIfProfileMeteringPulseInterval, shePotsConfigPortStatus, shePotsConfigPotsPortPriorityLevel, 
				shePotsConfigPptpProfileIndex, shePotsConfigAnalogIfProfileIndex, shePotsConfigLastTest, shePotsConfigILTFResult1, shePotsConfigILTFResult2, 
				shePotsConfigILTFResult3, shePotsSipUserDataConfigUserName, shePotsSipUserDataConfigPassword, shePotsSipUserDataConfigDmIndex, shePotsSipUserDataConfigCallingLineIdPresentation, 
				shePotsSipUserDataConfigCallCompletiontoBusySubscriber, shePotsSipUserDataConfigCallWaiting, shePotsSipUserDataConfigOutgoingCallBarring, shePotsSipUserDataConfigThreePartyConference, shePotsSipUserDataConfigCallHold, 
				shePotsSipUserDataConfigDialTimeOut, shePotsSipUserDataConfigBusyTimeOut, shePotsSipUserDataConfigHowlerTimeOut, shePotsSipUserDataConfigRegisterStatus, shePotsConfigAlarmSeverityIndex, 
				shePotsPptpProfileCid, shePotsPptpProfilePortPotsLineType, shePotsAnalogIfProfileHookoffMin }
			STATUS current
			DESCRIPTION 
				"A collection of objects providing information about
				a VDSL Line."
			::= { shePotsGroups 1 }

		
		shePotsControlGroup OBJECT-GROUP
			OBJECTS { shePotsPptpProfileControlRequest, shePotsPptpProfileControlIndex, shePotsPptpProfileControlName, shePotsPptpProfileControlPortIGain, shePotsPptpProfileControlPortOGain, 
				shePotsPptpProfileControlPortFaxlvl, shePotsPptpProfileControlPortPotsType, shePotsPptpProfileControlStatus, shePotsPptpProfileControlTimer, shePotsPptpProfileControlTimeStamp, 
				shePotsPptpProfileControlReqResult, shePotsAnalogIfProfileControlRequest, shePotsAnalogIfProfileControlIndex, shePotsAnalogIfProfileControlName, shePotsAnalogIfProfileControlCid, 
				shePotsAnalogIfProfileControlHookflashMin, shePotsAnalogIfProfileControlHookflashMax, shePotsAnalogIfProfileControlPulseBreakMin, shePotsAnalogIfProfileControlPulseBreakMax, shePotsAnalogIfProfileControlPulseMakeMin, 
				shePotsAnalogIfProfileControlPulseMakeMax, shePotsAnalogIfProfileControlPulseInterdigitMin, shePotsAnalogIfProfileControlMeteringPulseFreq, shePotsAnalogIfProfileControlMeteringPulseInterval, shePotsAnalogIfProfileControlStatus, 
				shePotsAnalogIfProfileControlTimer, shePotsAnalogIfProfileControlTimeStamp, shePotsAnalogIfProfileControlReqResult, shePotsConfigControlRequest, shePotsConfigControlIfIndexBitMask, 
				shePotsConfigControlPotsPortPriorityLevel, shePotsConfigControlPptpProfileIndex, shePotsConfigControlAnalogIfProfileIndex, shePotsConfigControlStatus, shePotsConfigControlTimer, 
				shePotsConfigControlTimeStamp, shePotsConfigControlReqResult, shePotsSipUserDataConfigControlRequest, shePotsSipUserDataConfigControlStatus, shePotsSipUserDataConfigControlTimer, 
				shePotsSipUserDataConfigControlTimeStamp, shePotsSipUserDataConfigControlReqResult, shePotsSipUserDataConfigControlIfIndexBitMask, shePotsSipUserDataConfigControlUserName, shePotsSipUserDataConfigControlPassword, 
				shePotsSipUserDataConfigControlDmIndex, shePotsSipUserDataConfigControlCallingLineIdPresentation, shePotsSipUserDataConfigControlCallCompletiontoBusySubscriber, shePotsSipUserDataConfigControlCallWaiting, shePotsSipUserDataConfigControlOutgoingCallBarring, 
				shePotsSipUserDataConfigControlThreePartyConference, shePotsSipUserDataConfigControlCallHold, shePotsSipUserDataConfigControlDialTimeOut, shePotsSipUserDataConfigControlBusyTimeOut, shePotsSipUserDataConfigControlHowlerTimeOut, 
				shePotsConfigControlAlarmSeverityIndex, shePotsPptpProfileControlCid, shePotsPptpProfileControlPortPotsLineType, shePotsAnalogIfProfileControlHookoffMin }
			STATUS current
			DESCRIPTION 
				"Description."
			::= { shePotsGroups 2 }

		
		shePotsNotificationGroup NOTIFICATION-GROUP
			NOTIFICATIONS { shePotsPptpProfileCreatedTrap, shePotsPptpProfileDeletedTrap, shePotsPptpProfileModifiedTrap, shePotsAnalogIfProfileCreatedTrap, shePotsAnalogIfProfileDeletedTrap, 
				shePotsAnalogIfProfileModifiedTrap, shePotsConfigModifiedTrap, shePotsConfigTestFinishedTrap, shePotsConfigPortStatusChangedTrap, shePortsThermFltDetectAlarm, 
				shePortsDCFltDetectAlarm, shePortsACFltDetectAlarm, shePortsGkeyDetectAlarm, shePotsSipUserDataConfigModifiedTrap }
			STATUS current
			DESCRIPTION 
				"This group supports notifications of significant 
				conditions associated with physical objects."
			::= { shePotsGroups 3 }

		
	
	END

--
-- she-pots-mib.mib
--
