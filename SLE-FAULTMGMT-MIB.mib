--
-- SLE-FAULTMGMT-MIB.my
-- MIB generated by MG-SOFT Visual MIB Builder Version 6.0  Build 88
-- Tuesday, March 31, 2009 at 20:32:18
--

	SLE-FAULTMGMT-MIB DEFINITIONS ::= BEGIN
 
		IMPORTS
			sleMgmt			
				FROM DASAN-SMI			
			SleControlStatusType, SleControlRequestResultType			
				FROM SLE-TC-MIB			
			OBJECT-GROUP, NOTIFICATION-GROUP			
				FROM SNMPv2-CONF			
			TimeTicks, IpAddress, Integer32, Unsigned32, Gauge32, 
			Counter32, BITS, OBJECT-TYPE, MODULE-IDENTITY, NOTIFICATION-TYPE			
				FROM SNMPv2-SMI			
			MacAddress, TimeStamp			
				FROM SNMPv2-TC;
	
	
		-- 1.3.6.1.4.1.6296.101.4
		sleFaultMgmt MODULE-IDENTITY 
			LAST-UPDATED "190412080000Z"		-- December 08, 1904 at 00:00 GMT
			ORGANIZATION 
				" "
			CONTACT-INFO 
				"
				"
			DESCRIPTION 
				"The MIB module representing multiple logical
				entities for the SLE alarm management. "
			REVISION "190412080000Z"		-- December 08, 1904 at 00:00 GMT
			DESCRIPTION 
				" "
			::= { sleMgmt 4 }

		
	
	
--
-- Node definitions
--
	
		-- 1.3.6.1.4.1.6296.101.4.1
		sleFaultMgmtBase OBJECT IDENTIFIER ::= { sleFaultMgmt 1 }

		
		-- 1.3.6.1.4.1.6296.101.4.1.1
		sleFaultMgmtBaseGroup OBJECT IDENTIFIER ::= { sleFaultMgmtBase 1 }

		
		-- 1.3.6.1.4.1.6296.101.4.1.1.1
		sleFaultDefaultSeverity OBJECT-TYPE
			SYNTAX INTEGER
				{
				critical(1),
				major(2),
				minor(3),
				warning(4),
				intermediate(5)
				}
			MAX-ACCESS read-only
			STATUS current
			DESCRIPTION
				" The severity of alarm. "
			::= { sleFaultMgmtBaseGroup 1 }

		
		-- 1.3.6.1.4.1.6296.101.4.1.1.2
		sleFaultCriteriaSeverity OBJECT-TYPE
			SYNTAX INTEGER
				{
				critical(1),
				major(2),
				minor(3),
				warning(4),
				intermediate(5)
				}
			MAX-ACCESS read-only
			STATUS current
			DESCRIPTION
				" The severity of alarm. "
			::= { sleFaultMgmtBaseGroup 2 }

		
		-- 1.3.6.1.4.1.6296.101.4.1.1.3
		sleFaultNotifiyActivity OBJECT-TYPE
			SYNTAX INTEGER
				{
				disabled(0),
				enabled(1)
				}
			MAX-ACCESS read-only
			STATUS current
			DESCRIPTION
				" The severity of alarm. "
			::= { sleFaultMgmtBaseGroup 3 }

		
		-- 1.3.6.1.4.1.6296.101.4.1.1.4
		sleFaultNextSeqNum OBJECT-TYPE
			SYNTAX Counter32
			MAX-ACCESS read-only
			STATUS current
			DESCRIPTION
				"Sequence number for the alarm synchronization. 
				This value has a number to be used for the next alarm trap."
			::= { sleFaultMgmtBaseGroup 4 }

		
		-- 1.3.6.1.4.1.6296.101.4.1.2
		sleFaultMgmtBaseControl OBJECT IDENTIFIER ::= { sleFaultMgmtBase 2 }

		
		-- 1.3.6.1.4.1.6296.101.4.1.2.1
		sleFaultControlRequest OBJECT-TYPE
			SYNTAX INTEGER
				{
				setAlarmDefaultSeverity(1),
				setAlarmCriteriaSeverity(2),
				setNotificationActivity(3)
				}
			MAX-ACCESS read-write
			STATUS current
			DESCRIPTION
				" This attribute identifies the control commands.
				updateAlarmList:
				   the NE updates entries of alarms in the sleAlarmListTable
				   after having changed alarm severities of alarms 
				   (due to change profile pointers in
				   managed entities or after modification of alarm severities 
				   in profiles). This command should be applied once after having 
				   finisled modifications of severties.
				modifyAlarmSeverity: 
				   modifies the severity of an alarm in specific profile.
				createAlarmSeverityProfile: 
				   creates a new profile with default severities.
				   The severities then have to be modified with command changeAlarmSeverity.
				deleteAlarmSeverityProfile: 
				   deletes a profile. Profile 1 is not allowed to be deleted.
				 
				Notifications : none "
			::= { sleFaultMgmtBaseControl 1 }

		
		-- 1.3.6.1.4.1.6296.101.4.1.2.2
		sleFaultControlStatus OBJECT-TYPE
			SYNTAX SleControlStatusType
			MAX-ACCESS read-only
			STATUS current
			DESCRIPTION
				" The status of a control request. "
			::= { sleFaultMgmtBaseControl 2 }

		
		-- 1.3.6.1.4.1.6296.101.4.1.2.3
		sleFaultControlTimer OBJECT-TYPE
			SYNTAX Unsigned32
			MAX-ACCESS read-write
			STATUS current
			DESCRIPTION
				" The maximum wait time for the manager for command ending.
				For long running commands.
				The manager reads this value from the DSLAM. "
			::= { sleFaultMgmtBaseControl 3 }

		
		-- 1.3.6.1.4.1.6296.101.4.1.2.4
		sleFaultControlTimeStamp OBJECT-TYPE
			SYNTAX TimeTicks
			MAX-ACCESS read-only
			STATUS current
			DESCRIPTION
				" The time stamp of the last command (end of command). "
			::= { sleFaultMgmtBaseControl 4 }

		
		-- 1.3.6.1.4.1.6296.101.4.1.2.5
		sleFaultControlReqResult OBJECT-TYPE
			SYNTAX SleControlRequestResultType
			MAX-ACCESS read-only
			STATUS current
			DESCRIPTION
				" The result of the last user command. "
			::= { sleFaultMgmtBaseControl 5 }

		
		-- 1.3.6.1.4.1.6296.101.4.1.2.6
		sleFaultControlDefaultSeverity OBJECT-TYPE
			SYNTAX INTEGER
				{
				critical(1),
				major(2),
				minor(3),
				warning(4),
				intermediate(5)
				}
			MAX-ACCESS read-write
			STATUS current
			DESCRIPTION
				" The severity of alarm. "
			::= { sleFaultMgmtBaseControl 6 }

		
		-- 1.3.6.1.4.1.6296.101.4.1.2.7
		sleFaultControlCriteriaSeverity OBJECT-TYPE
			SYNTAX INTEGER
				{
				critical(1),
				major(2),
				minor(3),
				warning(4),
				intermediate(5)
				}
			MAX-ACCESS read-write
			STATUS current
			DESCRIPTION
				" The severity of alarm. "
			::= { sleFaultMgmtBaseControl 7 }

		
		-- 1.3.6.1.4.1.6296.101.4.1.2.8
		sleFaultControlNotifiyActivity OBJECT-TYPE
			SYNTAX INTEGER
				{
				diabled(0),
				enabled(1)
				}
			MAX-ACCESS read-write
			STATUS current
			DESCRIPTION
				" The severity of alarm. "
			::= { sleFaultMgmtBaseControl 8 }

		
		-- 1.3.6.1.4.1.6296.101.4.1.3
		sleFaultMgmtBaseNotification OBJECT IDENTIFIER ::= { sleFaultMgmtBase 3 }

		
		-- 1.3.6.1.4.1.6296.101.4.1.3.1
		sleAlarmDefaultSeverityChanged NOTIFICATION-TYPE
			OBJECTS { sleFaultDefaultSeverity, sleFaultControlRequest, sleFaultControlTimeStamp, sleFaultControlReqResult }
			STATUS current
			DESCRIPTION 
				"Description."
			::= { sleFaultMgmtBaseNotification 1 }

		
		-- 1.3.6.1.4.1.6296.101.4.1.3.2
		sleAlarmDefaultCriteriaChanged NOTIFICATION-TYPE
			OBJECTS { sleFaultCriteriaSeverity, sleFaultControlRequest, sleFaultControlTimeStamp, sleFaultControlReqResult }
			STATUS current
			DESCRIPTION 
				"Description."
			::= { sleFaultMgmtBaseNotification 2 }

		
		-- 1.3.6.1.4.1.6296.101.4.1.3.3
		sleNotificationActivityChanged NOTIFICATION-TYPE
			OBJECTS { sleFaultControlRequest, sleFaultControlTimeStamp, sleFaultControlReqResult, sleFaultNotifiyActivity }
			STATUS current
			DESCRIPTION 
				"Description."
			::= { sleFaultMgmtBaseNotification 3 }

		
		-- 1.3.6.1.4.1.6296.101.4.2
		sleAlarmSeverity OBJECT IDENTIFIER ::= { sleFaultMgmt 2 }

		
		-- 1.3.6.1.4.1.6296.101.4.2.1
		sleAlarmSeverityTable OBJECT-TYPE
			SYNTAX SEQUENCE OF SleAlarmSeverityEntry
			MAX-ACCESS not-accessible
			STATUS current
			DESCRIPTION
				" The alarm severity table.
				The alarm severity table associates
				profile index and AlarmID pairs with severities to be
				used for alarm traps.
				(Note that this table does not apply to cleared alarms). "
			::= { sleAlarmSeverity 1 }

		
		-- 1.3.6.1.4.1.6296.101.4.2.1.1
		sleAlarmSeverityEntry OBJECT-TYPE
			SYNTAX SleAlarmSeverityEntry
			MAX-ACCESS not-accessible
			STATUS current
			DESCRIPTION
				" Entry of the alarm severity table. "
			INDEX { sleAlarmSeverityIndex }
			::= { sleAlarmSeverityTable 1 }

		
		SleAlarmSeverityEntry ::=
			SEQUENCE { 
				sleAlarmSeverityIndex
					INTEGER,
				sleAlarmSeverityValue
					INTEGER
			 }

		-- 1.3.6.1.4.1.6296.101.4.2.1.1.1
		sleAlarmSeverityIndex OBJECT-TYPE
			SYNTAX INTEGER
				{
				portDown(1),
				portUp(2),
				portRemoved(3),
				portInstalled(4),
				powerFail(5),
				powerOK(6),
				powerRemoved(7),
				powerInstalled(8),
				fanFail(9),
				fanOK(10),
				fanRemoved(11),
				fanInstalled(12),
				moduleRemoved(13),
				moduleInstalled(14),
				systemRestart(15),
				systemStart(16),
				broadcastOver(17),
				broadcastUnder(18),
				cpuOverLoad(19),
				cpuUnderLoad(20),
				memoryOverUsed(21),
				memoryUnderUsed(22),
				portOverThreshold(23),
				portUnderThreshold(24),
				temperatureHigh(25),
				temperatureLow(26),
				mfgdBlocked(27),
				mfgdReleased(28),
				ipConflict(29),
				ipUnconflict(30),
				dhcpLeaseShortage(31),
				dhcpLeaseSufficient(32),
				dhcpOccuredIllegalEntry(33),
				dhcpRemovedIllegalEntry(34),
				rmonAlarmRising(35),
				rmonAlarmNoRising(36),
				rmonAlarmFalling(37),
				rmonAlarmNoFalling(38),
				bpduGuardDisabled(39),
				rootGuardDisabled(40),
				portSecurity(41),
				userLogin(42),
				userLogout(43),
				igmpGroupJoined(51),
				igmpGroupLeaved(52),
				dhcpIpaddressBound(53),
				dhcpIpaddressFree(54),
				doorOpened(55),
				doorClosed(56),
				powerModeChangedPowerToBattery(57),
				powerModeChangedBatteryToPower(58),
				batterylowcapacity(59),
				batterynormalcapacity(60),
				batteryhighTemperature(61),
				batterynormalTemperature(62),
				authenticationFail(63),
				authenticationNofail(64),
				psuAcHighTemperature(65),
				psuAcNormalTemperature(66),
				batteryRemoved(67),
				batteryEquipped(68),
				batteryLowVoltage(69),
				batteryNormalVoltage(70),
				adminAccessLogin(71),
				adminAccessLogout(72),
				cfgdBlocked(73),
				cfgdReleased(74),
				sfgdBlocked(75),
				sfgdReleased(76),
				swWatchdogAbnormalState(77),
				swWatchdogNormalState(78),
				swWatchdogDetectError(79),
				swWatchdogClearError(80),
				ppsControlBlocked(81),
				ppsControlReleased(82),
				gotDMITempHighOverAlarm(83),
				gotDMITempHighFallAlarm(84),
				gotDMITempLowOverAlarm(85),
				gotDMITempLowFallAlarm(86),
				gotDMITempHighOverWarning(87),
				gotDMITempHighFallWarning(88),
				gotDMITempLowOverWarning(89),
				gotDMITempLowFallWarning(90),
				gotDMIVolHighOverAlarm(91),
				gotDMIVolHighFallAlarm(92),
				gotDMIVolLowOverAlarm(93),
				gotDMIVolLowFallAlarm(94),
				gotDMIVolHighOverWarning(95),
				gotDMIVolHighFallWarning(96),
				gotDMIVolLowOverWarning(97),
				gotDMIVolLowFallWarning(98),
				gotDMITxBiasHighOverAlarm(99),
				gotDMITxBiasHighFallAlarm(100),
				gotDMITxBiasLowOverAlarm(101),
				gotDMITxBiasLowFallAlarm(102),
				gotDMITxBiasHighOverWarning(103),
				gotDMITxBiasHighFallWarning(104),
				gotDMITxBiasLowOverWarning(105),
				gotDMITxBiasLowFallWarning(106),
				gotDMITxPowerHighOverAlarm(107),
				gotDMITxPowerHighFallAlarm(108),
				gotDMITxPowerLowOverAlarm(109),
				gotDMITxPowerLowFallAlarm(110),
				gotDMITxPowerHighOverWarning(111),
				gotDMITxPowerHighFallWarning(112),
				gotDMITxPowerLowOverWarning(113),
				gotDMITxPowerLowFallWarning(114),
				gotDMIRxPowerHighOverAlarm(115),
				gotDMIRxPowerHighFallAlarm(116),
				gotDMIRxPowerLowOverAlarm(117),
				gotDMIRxPowerLowFallAlarm(118),
				gotDMIRxPowerHighOverWarning(119),
				gotDMIRxPowerHighFallWarning(120),
				gotDMIRxPowerLowOverWarning(121),
				gotDMIRxPowerLowFallWarning(122),
				nosRemoteUpgradeRequest(123),
				nosRemoteUpgradeSuccess(124),
				nosRemoteUpgradeFailAbort(125),
				nosRemoteUpgradeFailHeaderError(126),
				nosRemoteUpgradeFailDownloadError(127),
				nosRemoteUpgradeFailFlashError(128),
				nosRemoteUpgradeStart(129),
				systemDyingGasp(130),
				remoteOamDyingGasp(131),
				remoteOamDyingGaspRestoration(132),
				swWatchdogInetAbnormalState(150),
				swWatchdogInetNormalState(151),
				swWatchdogInetDetectError(152),
				swWatchdogInetClearError(153),
				swWatchdogPonAbnormalState(154),
				swWatchdogPonNormalState(155),
				swWatchdogPonDetectError(156),
				swWatchdogPonClearError(157),
				advaTemperature(201),
				advaTemperatureNo(202),
				advaPSUFailure(203),
				advaPSUFailureNo(204),
				advaFanFailure(205),
				advaFanFailureNo(206),
				advaInterfaceReceiveFailure(207),
				advaInterfaceReceiveFailureNo(208),
				advaInterfaceOpticalThreshold(209),
				advaInterfaceOpticalThresholdNo(210),
				advaInterfaceTransmitFault(211),
				advaInterfaceTransmitFaultNo(212),
				advaInterfaceMisconfiguration(213),
				advaInterfaceMisconfigurationNo(214),
				advaInterfaceSFPMismatch(215),
				advaInterfaceSFPMismatchNo(216),
				advaVoltageLow(217),
				advaVoltageLowNo(218),
				advaVoltageHigh(219),
				advaVoltageHighNo(220),
				erpDomainLotp(301),
				erpDomainLotpNo(302),
				erpDomainULotp(303),
				erpDomainULotpNo(304),
				erpDomainMultipleRM(305),
				erpDomainMultipleRMNo(306),
				erpDomainRMNodeReacheablity(307),
				erpDomainRMNodeReacheablityNo(308),
				eponOnuDeregister(401),
				eponOnuRegister(402),
				eponOnuRegistrationError(403),
				eponOnuNoRegistrationError(404),
				eponBadEncryptionKey(405),
				eponNoBadEncryptionKey(406),
				eponLlidMistmatch(407),
				eponNoLlidMismatch(408),
				eponTooManyRegister(409),
				eponNoTooManyRegister(410),
				eponDyingGASP(411),
				eponNoDyingGASP(412),
				eponOnuErrFramePeriod(413),
				eponOnuNoErrFramePeriod(414),
				eponOnuErrFrame(415),
				eponOnuNoErrFrame(416),
				eponOnuErrFrameSecondSummary(417),
				eponOnuNoErrFrameSecondSummary(418),
				eponOnuLastOnuDeregister(419),
				eponOnuNoLastOnuDeregister(420),
				eponOltCableDown(421),
				eponOltRecoverCableDown(422),
				autoCLIStart(501),
				autoCLINoStart(502),
				autoCLIComplete(503),
				autoCLINoComplete(504),
				autoCLIRemoveOutputFile(505),
				autoCLINoRemoveOutputFile(506),
				autoResetSystem(507),
				autoResetNoSystem(508),
				autoResetPingReplyLoss(509),
				autoResetNoPingReplyLoss(510),
				autoResetMemoryLeakDetect(511),
				autoResetNoMemoryLeakDetect(512),
				arulePacketDropDetect(601),
				arulePacketDropRelease(602),
				autoCpeUpgradeStart(605),
				autoCpeUpgradeFail(607),
				autoCpeUpgradeSuccess(609),
				batteryUnderTemper(611),
				batteryTemperUnderToNormal(612),
				batteryCellAbnormal(613),
				batteryCellNormal(614),
				batteryCellTestChargeStarted(615),
				batteryCellTestChargeFinished(616),
				batteryAcPowerFault(617),
				batteryAcPowerOk(618),
				bME1CardNoDetect(620),
				clearBME1CardNoDetect(621),
				bME1CardAFEerror(622),
				clearBME1CardAFEerror(623),
				bME1CardIFEerror(624),
				clearBME1CardIFEerror(625),
				bME1CardFWerror(626),
				clearBME1CardFWerror(627),
				bME1CardPROVerror(628),
				clearBME1CardPROVerror(629),
				bME1CrashDetect(630),
				clearBME1CrashDetect(631),
				bME2CardNoDetect(632),
				clearBME2CardNoDetect(633),
				bME2CardAFEerror(634),
				clearBME2CardAFEerror(635),
				bME2CardIFEerror(636),
				clearBME2CardIFEerror(637),
				bME2CardFWerror(638),
				clearBME2CardFWerror(639),
				bME2CardPROVerror(640),
				clearBME2CardPROVerror(641),
				bME2CrashDetect(642),
				clearBME2CrashDetect(643),
				bME3CardNoDetect(644),
				clearBME3CardNoDetect(645),
				bME3CardAFEerror(646),
				clearBME3CardAFEerror(647),
				bME3CardIFEerror(648),
				clearBME3CardIFEerror(649),
				bME3CardFWerror(650),
				clearBME3CardFWerror(651),
				bME3CardPROVerror(652),
				clearBME3CardPROVerror(653),
				bME3CrashDetect(654),
				clearBME3CrashDetect(655),
				powerFromBattery(656),
				clearPowerFromBattery(657),
				invalidBatteryStatus(658),
				clearInvalidBatteryStatus(659),
				batteryChargeLow(660),
				clearBatteryChargeLow(661),
				batteryNotPresent(662),
				clearBatteryNotPresent(663),
				voltageLow(664),
				clearVoltageLow(665),
				tempOverThreshold(666),
				clearTempOverThreshold(667),
				tempUnderThreshold(668),
				clearTempUnderThreshold(669),
				cpuOverThreshold(670),
				clearCpuOverThreshold(671),
				trafficOverload(672),
				clearTrafficOverload(673),
				gEPONModuleNotDetect(674),
				clearGEPONModuleNotDetect(675),
				gEPONPortOperationDown(676),
				clearGEPONPortOperationDown(677),
				gEPONNoIncomingTraffic(678),
				clearGEPONNoIncomingTraffic(679),
				processCrashDetect(680),
				clearProcessCrashDetect(681),
				memoryLeakDetect(682),
				clearMemoryLeakDetect(683),
				memoryCorrupDetect(684),
				clearMemoryCorrupDetect(685),
				memoryLowDetect(686),
				clearMemoryLowDetect(687),
				dataLineerror(688),
				clearDataLineerror(689),
				addressLineerror(690),
				clearAddressLineerror(691),
				chipsetNotDetcet(692),
				clearChipsetNotDetcet(693),
				pciBuserror(694),
				clearPciBuserror(695),
				securityAdminConnect(696),
				clearSecurityAdminConnect(697),
				oNUPowerDown(698),
				clearONUPowerDown(699),
				oNUNotRegister(700),
				clearONUNotRegister(701),
				oNTOpticPre(702),
				clearONTOpticPre(703),
				switchoverInitiated(800),
				switchoverDone(801)
				}
			MAX-ACCESS read-only
			STATUS current
			DESCRIPTION
				"The following alarms is devided by the specific character, ===============.
				The division basis is that alarms is bounded or released.
				
				        001: portDown: To detect whether physical or logical interface's link status is up or down.
					002: portUp: 
					===============
					003: portRemoved: To detect whether physical interface is installed or not.
					004: portInstalled: 
					===============
					005: powerFail: To detect whether power module's operation status is good or not.
							(Without doubt, more than 1 power module should be equipped.)
					006: powerOK: 
					===============
					007: powerRemoved: To detect whether power module is installed or not, through the PLD access.
							   (Without doubt, more than 1 power module should be equipped.)
					008: powerInstalled: 
					===============
					009: fanFail: To detect whether FAN module's operation status is good or not.
					010: fanOK: 
					===============
					011: fanRemoved: To detect whether FAN module is installed or not, through the PLD access.
					012: fanInstalled: 
					===============
					013: moduleRemoved: To detect whether physical interface module is installed or not, through the S/W I2C
					014: moduleInstalled: 
					===============
					015: systemRestart: Network system is restarted by operator. This is not H/W start but S/W start.
					===============
					016: systemStart: Network system is restarted by operator or system status. This is not S/W start but H/W start.
							  (This alarm isn’t used current)
					===============
					017: broadcastOver: To detect the receipt of broadcast packet.
				  			    (This alarm isn’t used current)
					018: broadcastUnder: 
					===============
					019: cpuOverLoad: To detect whether the configured CPU load threshold is less than current CPU load usage or not.
					020: cpuUnderLoad: 
					===============
					021: memoryOverUsed: To detect whether the configured memory threshold is less than current memory usage or not.
					022: memoryUnderUsed: 
					===============
					023: portOverThreshold: To detect whether the configured physical or logical interface threshold is 
								less than delta value of current interface's InOctects or not.
					024: portUnderThreshold: 
					===============
					025: temperatureHigh: To detect whether the configured system's temperature threshold is 
							      less than current temperature or not.
					026: temperatureLow: 
					===============
					027: mfgdBlocked: To detect whether the specific MAC by MAC flood guard is blocked or not.
					028: mfgdReleased: 
					===============
					029: ipConflict: To detect whether the same IP address on different network node is configured or not.
					030: ipUnconflict: 
					===============
					031: dhcpLeaseShortage: To detect whether IP address that can be assigned to subscriber by DHCP server is 
								sufficient or not.
					032: dhcpLeaseSufficient: 
					===============
					033: dhcpOccuredIllegalEntry: To detect whether a subsceiber is using a static IP address or not.
					034: dhcpRemovedIllegalEntry: 
					===============
					035: rmonAlarmRising: To detect whether rising threshold of a specific MO in RMON alarm sampling is 
							      less than current calculated value by alarm sample type or not. But alarm generation 
							      would be issued by means of event type in RMON event.
					036: rmonAlarmNoRising: 
					===============
					037: rmonAlarmFalling: To detect whether falling threshold of a specific MO in RMON alarm sampling is 
							       less than current calculated value by alarm sample type or not. 
							       But alarm generation would be issued by means of event type in RMON event.
					038: rmonAlarmNoFalling: 
					===============
					039: bpduGuardDisabled: To detect whether edge ports is guarded about superior BPDU or not. 
								In case of insertion edge node with 0 or lower priority than priority of current root bridge node, 
								it will be disarrangement during a short time because of recognition a new inserted node 
								as root bridge. 
								So these edge ports is guarded, and then edge ports is blocked about all superior BPDU. 
								So STP reconfiguration doesn't use this edge ports.
					===============
					040: rootGuardDisabled: To detect whether edge ports is guarded about superior BPDU or not. 
								In case of insertion edge node with 0 or lower priority than priority of current root bridge node, 
								it will be disarrangement during a short time because of recognition a new inserted node 
								as root bridge. 
								So, Root guard prevents a new inserted node from being root bridge as well as 
								receiving a superior BPDU from root bridge. 
								but this node participates in STP topology reconfiguration. 
								If root bridge does not send a superior BPDU, then this node acts usually though STP state change.
					===============
					041: portSecurity: To detect whether interface is configured for security or not. 
							   This can be used to prevent MAC from flooding as well as spoofing. 
							   That is, As a result, this will obstruct an attack as like DoS attack.
					===============
					042: userLogin: 
					043: userLogout: 
					===============
					051: igmpGroupJoined: To detect whether a subscriber is joined a multicast group or not.
					052: igmpGroupLeaved: 
					===============
					053: dhcpIpaddressBound: To detect wether a dynamic IP address is assigned to a subscriber or not.
					054: dhcpIpaddressFree: 
					===============
					055: doorOpened: To detect whether outer door is opeded or not, as external alarm.
					056: doorClosed: 
					===============
					057: powerModeChangedPowerToBattery: To detect whether a system is using AC power or battery. 
									     A system is using AC power usually. 
									     If there is any power problems as like a power failure, 
									     a system is using battery instead of AC power. 
					058: powerModeChangedBatteryToPower: 
					===============
					059: batterylowcapacity: To detect whether current battery capacity is less 
								 capacity threshold according to battery usage or not. 
								 The capacity of AC power is 16 voltage and battery is 20. 
								 Capacity threshold is configured by H/W specification.
								 So operator can't change it.
					060: batterynormalcapacity: 
					===============
					061: batteryhighTemperature: To detect whether current temperature of battery is greater than temperature threshold or not. 
					062: batterynormalTemperature: 
					===============
					063: authenticationFail: To detect whether the connected user is authentic or non-authentic.
					064: authenticationNofail: 
					===============
					065: psuAcHighTemperature: To detect whether current temperature of Power Supply Unit is 
								   greater than temperature threshold or not. 
					066: psuAcNormalTemperature: 
					===============
					067: batteryRemoved: To detect whether battery is equipped at network system or not. 
							     Battery is used as redundancy power service. So operator can decide the installation of battery.
					068: batteryEquipped: 
					===============
					069: batteryLowVoltage: To detect whether battery voltage is less than 12.5 volt or not. 
								12.5 volt value is configured by H/W specification. So operator can't change it.
					070: batteryNormalVoltage: 
					===============
					071: adminAccessLogin: To detect whether a operator connects at this network system or not.
					072: adminAccessLogout: 
					===============
					073: cfgdBlocked: To detect whether it is blocked flood to CPU or not.
					074: cfgdReleased: 
					===============
					075: sfgdBlocked: To detect whether it is blocked flood to system or not.
					076: sfgdReleased: 
					===============
					077: swWatchdogAbnormalState: To detect whether a specific process acts normally or not.
					078: swWatchdogNormalState: 
					===============
					079: swWatchdogDetectError: To detect whether a specific process is detected a error related to itself or cleared.
					080: swWatchdogClearError: 
					===============
					081: ppsControlBlocked: To detect whether it is blocked by pps-control or not.
					082: ppsControlReleased: 
					===============
					083: gotDMITempHighOverAlarm: To detect whether internal temperature exceeds high alarm level or not.
					084: gotDMITempHighFallAlarm: 
					===============
					085: gotDMITempLowOverAlarm: To detect whether internal temperature is below low alarm level or not.
					086: gotDMITempLowFallAlarm: 
					===============
					087: gotDMITempHighOverWarning: To detect whether internal temperature exceeds high warning level or not.
					088: gotDMITempHighFallWarning: 
					===============
					089: gotDMITempLowOverWarning: To detect whether internal temperature is below low warning level or not.
					090: gotDMITempLowFallWarning: 
					===============
					091: gotDMIVolHighOverAlarm: To detect whether internal supply voltage exceeds high alarm level or not.
					092: gotDMIVolHighFallAlarm: 
					===============
					093: gotDMIVolLowOverAlarm: To detect whether internal supply voltage is below low alarm level or not.
					094: gotDMIVolLowFallAlarm: 
					===============
					095: gotDMIVolHighOverWarning: To detect whether internal supply voltage exceeds high warning level or not.
					096: gotDMIVolHighFallWarning: 
					===============
					097: gotDMIVolLowOverWarning: To detect whether internal supply voltage is below low warning level or not.
					098: gotDMIVolLowFallWarning: 
					===============
					099: gotDMITxBiasHighOverAlarm: To detect whether TX Bias current exceeds high alarm level or not.
					100: gotDMITxBiasHighFallAlarm: 
					===============
					101: gotDMITxBiasLowOverAlarm: To detect whether TX Bias current is below low alarm level or not.
					102: gotDMITxBiasLowFallAlarm: 
					===============
					103: gotDMITxBiasHighOverWarning: To detect whether TX Bias current exceeds high warning level or not.
					104: gotDMITxBiasHighFallWarning: 
					===============
					105: gotDMITxBiasLowOverWarning: To detect whether TX Bias current is below low warning level or not.
					106: gotDMITxBiasLowFallWarning: 
					===============
					107: gotDMITxPowerHighOverAlarm: To detect whether TX output power exceeds high alarm level or not.
					108: gotDMITxPowerHighFallAlarm: 
					===============
					109: gotDMITxPowerLowOverAlarm: To detect whether TX output power is below low alarm level or not.
					110: gotDMITxPowerLowFallAlarm: 
					===============
					111: gotDMITxPowerHighOverWarning: To detect whether TX output power exceeds high warning level or not.
					112: gotDMITxPowerHighFallWarning: 
					===============
					113: gotDMITxPowerLowOverWarning: To detect whether TX output power is below low warning level or not.
					114: gotDMITxPowerLowFallWarning: 
					===============
					115: gotDMIRxPowerHighOverAlarm: To detect whether RX output power exceeds high alarm level or not.
					116: gotDMIRxPowerHighFallAlarm: 
					===============
					117: gotDMIRxPowerLowOverAlarm: To detect whether RX output power is below low alarm level or not.
					118: gotDMIRxPowerLowFallAlarm: 
					===============
					119: gotDMIRxPowerHighOverWarning: To detect whether RX output power exceeds high warning level or not.
					120: gotDMIRxPowerHighFallWarning: 
					===============
					121: gotDMIRxPowerLowOverWarning: To detect whether RX output power is below low warning level or not.
					122: gotDMIRxPowerLowFallWarning: 
					===============
					123: nosRemoteUpgradeRequest: 
					124: nosRemoteUpgradeSuccess: 
					125: nosRemoteUpgradeFailAbort: 
					126: nosRemoteUpgradeFailHeaderError: 
					127: nosRemoteUpgradeFailDownloadError: 
					128: nosRemoteUpgradeFailFlashError: 
					129: nosRemoteUpgradeStart: 
				        ===============
				        130: systemDyingGasp
					===============
					201: advaTemperature: To detect whether current chassis temperature is less than chassis temperature threshold or not.
					202: advaTemperatureNo: 
					===============
					203: advaPSUFailure: To detect whether ADVA system's power supply unit has a failure or not.
					204: advaPSUFailureNo: 
					===============
					205: advaFanFailure: To detect whether ADVA system's FAN has a failure or not.
					206: advaFanFailureNo: 
					===============
					207: advaInterfaceReceiveFailure: To detect whether ADVA system's receipt has a failure or not.
					208: advaInterfaceReceiveFailureNo:  
					===============
					209: advaInterfaceOpticalThreshold: To detect whether Adva system's optical receive power level is 
									    less than optical threshold or not.
					210: advaInterfaceOpticalThresholdNo: 
					===============
					211: advaInterfaceTransmitFault: To detect whether ADVA system's transmission has a failure or not.
					212: advaInterfaceTransmitFaultNo: 
					===============
					213: dvaInterfaceMisconfiguration: To detect whether ADVA system's interface is configured rightly or not.
					214: advaInterfaceMisconfigurationNo: 
					===============
					215: advaInterfaceSFPMismatch: To detect whether ADVA system's SFP interface is mismatched or not.
					216: advaInterfaceSFPMismatchNo: 
					===============
					217: advaVoltageLow: To detect whether ADVA system's current voltage is less than voltage threshold or not.
					218: advaVoltageLowNo: 
					===============
					219: advaVoltageHigh: To detect whether ADVA system's current voltage is greater than voltage threshold or not.
					220: advaVoltageHighNo: 
					===============
					301: erpDomainLotp: To detect whether LOTP(Loss of Test Packet) exists a domain of ERP or not. 
							    The Loss of Test Packet defect is defined when a node does not receive 
							    any test packet at any of its ports for a period of 3 times.
					302: erpDomainLotpNo: 
					===============
					303: erpDomainULotp: To detect whether undirectional LOTP(Loss of Test Packet) exists a domain of ERP or not. 
							     The Loss of Test Packet defect is defined when a RM node of one domain does not 
							     receive any test packet at one port for a period of 3 times.
					304: erpDomainULotpNo: 
					===============
					305: erpDomainMultipleRM: To detect whether Multiple RM node is supported or not. 
								  The defect is raised when a RM node receives its own test packets 
								  with an Ack destination address field with a non-zero value.
					306: erpDomainMultipleRMNo: 
					===============
					307: erpDomainRMNodeReacheablity: To detect whether RM reachability is raised or not. 
									  The detection of multiple failures indicates that the ring is segmented and 
								          that the RM Node is unreacheable. 
									  This is only possible at normal ring nodes isolated from the RM node.
					308: erpDomainRMNodeReacheablityNo: 
					===============
					401: eponOnuDeregister: To detect whether ONU is registered into OLT or not. 
								That is, ONU that its operation is service on should be sent registration information to OLT. 
					402: eponOnuRegister: 
					===============
					403: eponOnuRegistrationError: To detect whether ONU is failed registeration process into OLT.
					404: eponOnuNoRegistrationError: 
					===============
					405: eponBadEncryptionKey: To detect wwhether the encryption key is valid or not.
								   A message between ONU and OLT is encrypted using random encryption key. 
								   There is that the encryption key is invalid as transmission failure from time to time.
					406: eponNoBadEncryptionKey: 
					===============
					407: eponLlidMistmatch: To detect whether Llid of message between ONU and OLT is valid or not. 
								On registering, ONU informs unique ID to OLT.
								And then, all communication between ONU and OLT must use the unique ID. 
								The unique ID is called Llid.
					408: eponNoLlidMismatch: 
					===============
					409: eponTooManyRegister: To detect whether the registered ONU per 1 OLT is greater than 32 or not. 
								  That is, ONU can be registered from 1 to the maximum 32 at 1 OLT.
					410: eponNoTooManyRegister: 
					===============
					411: eponDyingGASP: To detect whether a ONU is down from dying gasp or not. 
							    A ONU could be changed to down state as a number of reasons.
							    By the way, ONU that is changed to down as dying gasp would be sent dying gasp signal to OLT and 
							    then ONU's link would be changed to down.
					412: eponNoDyingGASP: 
					===============
					413: eponOnuErrFramePeriod: 
					414: eponOnuNoErrFramePeriod: 
					===============
					415: eponOnuErrFrame: 
					416: eponOnuNoErrFrame: 
					===============
					417: eponOnuErrFrameSecondSummary: 
					418: eponOnuNoErrFrameSecondSummary: 
					===============
					419: eponOnuLastOnuDeregister: To detect whether a deregistered ONU is last ONU or not. 
								       If a deregistered ONU is last ONU, the OLT would be changed to serviceable status. 
					420: eponOnuNoLastOnuDeregister: 
					===============
					421: eponOltCableDown: 
					422: eponOltRecoverCableDown: 
					===============
					501: autoCLIStart: To detect whether the scheduled auto CLI is started or not.
					502: autoCLINoStart: 
					===============
					503: autoCLIComplete: To detect whether the scheduled auto CLI is completed or not. 
					504: autoCLINoComplete: 
					===============
					505: autoCLIRemoveOutputFile: To detect whether the result file of the scheduled auto CLI is removed or not.
								      The reason that the result file is removed is that the configured file size for the result  is
								      less than the stored result file size. 
								      If so, the oldest file would be removed before everything.
					506: autoCLINoRemoveOutputFile: 
					===============
					507: autoResetSystem: To detect whether the system is restarted or not. 
							      The conditions that system is restarted is that ping loss threshold is 
							      less than current ping loss count during the configured interval and 
							      that current free memory size is less than configured free memory size.
					508: autoResetNoSystem: 
					===============
					509: autoResetPingReplyLoss: To detect whether ping reply from the designated network node is received or not.
								     Operator designates any gateway system that can communicate to detect 
								     current network environment. 
								     System sends ICMP packet to the designated gateway system periodically. 
								     If  the system doesn't receive ping reply packet within any interval, 
								     operator recognizes that the system can't communicate any more 
								     because of some problems of the system. 
					510: autoResetNoPingReplyLoss: 
					===============
					511: autoResetMemoryLeakDetect: To detect whether current free memory size is 
									less than the configured free memory size or not. 
									Periodically, free memory size is checked to confirm system availability.
					512: autoResetNoMemoryLeakDetect: 
					===============
					601: arulePacketDropDetect: To detect whether it is dropped some packet by arule or not.
					602: arulePacketDropRelease: 
					===============
					620: bME1CardNoDetect: 
					621: clearBME1CardNoDetect: 
					===============
					622: bME1CardAFEerror: 
					623: clearBME1CardAFEerror: 
					===============
					624: bME1CardIFEerror: 
					625: clearBME1CardIFEerror: 
					===============
					626: bME1CardFWerror: 
					627: clearBME1CardFWerror: 
					===============
					628: bME1CardPROVerror: 
					629: clearBME1CardPROVerror: 
					===============
					630: bME1CrashDetect: 
					631: clearBME1CrashDetect: 
					===============
					632: bME2CardNoDetect: 
					633: clearBME2CardNoDetect: 
					===============
					634: bME2CardAFEerror: 
					635: clearBME2CardAFEerror: 
					===============
					636: bME2CardIFEerror: 
					637: clearBME2CardIFEerror: 
					===============
					638: bME2CardFWerror: 
					639: clearBME2CardFWerror: 
					===============
					640: bME2CardPROVerror: 
					641: clearBME2CardPROVerror: 
					===============
					642: bME2CrashDetect: 
					643: clearBME2CrashDetect: 
					===============
					644: bME3CardNoDetect: 
					645: clearBME3CardNoDetect: 
					===============
					646: bME3CardAFEerror: 
					647: clearBME3CardAFEerror: 
					===============
					648: bME3CardIFEerror: 
					649: clearBME3CardIFEerror: 
					===============
					650: bME3CardFWerror: 
					651: clearBME3CardFWerror: 
					===============
					652: bME3CardPROVerror: 
					653: clearBME3CardPROVerror: 
					===============
					654: bME3CrashDetect: 
					655: clearBME3CrashDetect: 
					===============
					656: powerFromBattery: 
					657: clearPowerFromBattery: 
					===============
					658: invalidBatteryStatus: 
					659: clearInvalidBatteryStatus: 
					===============
					660: batteryChargeLow: 
					661: clearBatteryChargeLow: 
					===============
					662: batteryNotPresent: 
					663: clearBatteryNotPresent: 
					===============
					664: voltageLow: 
					665: clearVoltageLow: 
					===============
					666: tempOverThreshold: 
					667: clearTempOverThreshold: 
					===============
					668: tempUnderThreshold: 
					669: clearTempUnderThreshold: 
					===============
					670: cpuOverThreshold: 
					671: clearCpuOverThreshold: 
					===============
					672: trafficOverload: 
					673: clearTrafficOverload: 
					===============
					674: gEPONModuleNotDetect: 
					675: clearGEPONModuleNotDetect:
					===============
					676: gEPONPortOperationDown: 
					677: clearGEPONPortOperationDown: 
					===============
					678: gEPONNoIncomingTraffic: 
					679: clearGEPONNoIncomingTraffic: 
					===============
					680: processCrashDetect: 
					681: clearProcessCrashDetect: 
					===============
					682: memoryLeakDetect: 
					683: clearMemoryLeakDetect: 
					===============
					684: memoryCorrupDetect: 
					685: clearMemoryCorrupDetect: 
					===============
					686: memoryLowDetect: 
					687: clearMemoryLowDetect: 
					===============
					688: dataLineerror: 
					689: clearDataLineerror: 
					===============
					690: addressLineerror: 
					691: clearAddressLineerror: 
					===============
					692: chipsetNotDetcet: 
					693: clearChipsetNotDetcet: 
					===============
					694: pciBuserror: 
					695: clearPciBuserror: 
					===============
					696: securityAdminConnect: 
					697: clearSecurityAdminConnect: 
					===============
					698: oNUPowerDown: 
					699: clearONUPowerDown: 
					===============
					700: oNUNotRegister: 
					701: clearONUNotRegister: 
					===============
					702: oNTOpticPre: 
					703: clearONTOpticPre: 
					===============
					800: switchoverInitiated: 
					===============
					801: switchoverDone: 
					==============="
			::= { sleAlarmSeverityEntry 1 }

		
		-- 1.3.6.1.4.1.6296.101.4.2.1.1.2
		sleAlarmSeverityValue OBJECT-TYPE
			SYNTAX INTEGER
				{
				critical(1),
				major(2),
				minor(3),
				warning(4),
				intermediate(5)
				}
			MAX-ACCESS read-only
			STATUS current
			DESCRIPTION
				" The severity of alarm. "
			::= { sleAlarmSeverityEntry 2 }

		
		-- 1.3.6.1.4.1.6296.101.4.2.2
		sleAlarmSeverityControl OBJECT IDENTIFIER ::= { sleAlarmSeverity 2 }

		
		-- 1.3.6.1.4.1.6296.101.4.2.2.1
		sleAlarmSeverityControlRequest OBJECT-TYPE
			SYNTAX INTEGER
				{
				createAlarmSeveriity(1),
				destroyAlarmSeveriity(2),
				setAlarmSeveriity(3)
				}
			MAX-ACCESS read-write
			STATUS current
			DESCRIPTION
				" This attribute identifies the control commands.
				updateAlarmList:
				   the NE updates entries of alarms in the sleAlarmListTable
				   after having changed alarm severities of alarms 
				   (due to change profile pointers in
				   managed entities or after modification of alarm severities 
				   in profiles). This command should be applied once after having 
				   finisled modifications of severties.
				modifyAlarmSeverity: 
				   modifies the severity of an alarm in specific profile.
				createAlarmSeverityProfile: 
				   creates a new profile with default severities.
				   The severities then have to be modified with command changeAlarmSeverity.
				deleteAlarmSeverityProfile: 
				   deletes a profile. Profile 1 is not allowed to be deleted.
				 
				Notifications : none "
			::= { sleAlarmSeverityControl 1 }

		
		-- 1.3.6.1.4.1.6296.101.4.2.2.2
		sleAlarmSeverityControlStatus OBJECT-TYPE
			SYNTAX SleControlStatusType
			MAX-ACCESS read-only
			STATUS current
			DESCRIPTION
				" The status of a control request. "
			::= { sleAlarmSeverityControl 2 }

		
		-- 1.3.6.1.4.1.6296.101.4.2.2.3
		sleAlarmSeverityControlTimer OBJECT-TYPE
			SYNTAX Unsigned32
			MAX-ACCESS read-write
			STATUS current
			DESCRIPTION
				" The maximum wait time for the manager for command ending.
				For long running commands.
				The manager reads this value from the DSLAM. "
			::= { sleAlarmSeverityControl 3 }

		
		-- 1.3.6.1.4.1.6296.101.4.2.2.4
		sleAlarmSeverityControlTimeStamp OBJECT-TYPE
			SYNTAX TimeTicks
			MAX-ACCESS read-only
			STATUS current
			DESCRIPTION
				" The time stamp of the last command (end of command). "
			::= { sleAlarmSeverityControl 4 }

		
		-- 1.3.6.1.4.1.6296.101.4.2.2.5
		sleAlarmSeverityControlReqResult OBJECT-TYPE
			SYNTAX SleControlRequestResultType
			MAX-ACCESS read-only
			STATUS current
			DESCRIPTION
				" The result of the last user command. "
			::= { sleAlarmSeverityControl 5 }

		
		-- 1.3.6.1.4.1.6296.101.4.2.2.6
		sleAlarmSeverityControlIndex OBJECT-TYPE
			SYNTAX INTEGER
				{
				portDown(1),
				portUp(2),
				portRemoved(3),
				portInstalled(4),
				powerFail(5),
				powerOK(6),
				powerRemoved(7),
				powerInstalled(8),
				fanFail(9),
				fanOK(10),
				fanRemoved(11),
				fanInstalled(12),
				moduleRemoved(13),
				moduleInstalled(14),
				systemRestart(15),
				systemStart(16),
				broadcastOver(17),
				broadcastUnder(18),
				cpuOverLoad(19),
				cpuUnderLoad(20),
				memoryOverUsed(21),
				memoryUnderUsed(22),
				portOverThreshold(23),
				portUnderThreshold(24),
				temperatureHigh(25),
				temperatureLow(26),
				mfgdBlocked(27),
				mfgdReleased(28),
				ipConflict(29),
				ipUnconflict(30),
				dhcpLeaseShortage(31),
				dhcpLeaseSufficient(32),
				dhcpOccuredIllegalEntry(33),
				dhcpRemovedIllegalEntry(34),
				rmonAlarmRising(35),
				rmonAlarmNoRising(36),
				rmonAlarmFalling(37),
				rmonAlarmNoFalling(38),
				bpduGuardDisabled(39),
				rootGuardDisabled(40),
				portSecurity(41),
				userLogin(42),
				userLogout(43),
				igmpGroupJoined(51),
				igmpGroupLeaved(52),
				dhcpIpaddressBound(53),
				dhcpIpaddressFree(54),
				doorOpened(55),
				doorClosed(56),
				powerModeChangedPowerToBattery(57),
				powerModeChangedBatteryToPower(58),
				batterylowcapacity(59),
				batterynormalcapacity(60),
				batteryhighTemperature(61),
				batterynormalTemperature(62),
				authenticationFail(63),
				authenticationNoFail(64),
				psuAcHighTemperature(65),
				psuAcNormalTemperature(66),
				batteryRemoved(67),
				batteryEquipped(68),
				batteryLowVoltage(69),
				batteryNormalVoltage(70),
				adminAccessLogin(71),
				adminAccessLogout(72),
				cfgdBlocked(73),
				cfgdReleased(74),
				sfgdBlocked(75),
				sfgdReleased(76),
				swWatchdogAbnomalState(77),
				swWatchdogNomalState(78),
				swWatchdogDetectError(79),
				swWatchdogClearError(80),
				ppsControlBlocked(81),
				ppsControlReleased(82),
				gotDMITempHighOverAlarm(83),
				gotDMITempHighFallAlarm(84),
				gotDMITempLowOverAlarm(85),
				gotDMITempLowFallAlarm(86),
				gotDMITempHighOverWarning(87),
				gotDMITempHighFallWarning(88),
				gotDMITempLowOverWarning(89),
				gotDMITempLowFallWarning(90),
				gotDMIVolHighOverAlarm(91),
				gotDMIVolHighFallAlarm(92),
				gotDMIVolLowOverAlarm(93),
				gotDMIVolLowFallAlarm(94),
				gotDMIVolHighOverWarning(95),
				gotDMIVolHighFallWarning(96),
				gotDMIVolLowOverWarning(97),
				gotDMIVolLowFallWarning(98),
				gotDMITxBiasHighOverAlarm(99),
				gotDMITxBiasHighFallAlarm(100),
				gotDMITxBiasLowOverAlarm(101),
				gotDMITxBiasLowFallAlarm(102),
				gotDMITxBiasHighOverWarning(103),
				gotDMITxBiasHighFallWarning(104),
				gotDMITxBiasLowOverWarning(105),
				gotDMITxBiasLowFallWarning(106),
				gotDMITxPowerHighOverAlarm(107),
				gotDMITxPowerHighFallAlarm(108),
				gotDMITxPowerLowOverAlarm(109),
				gotDMITxPowerLowFallAlarm(110),
				gotDMITxPowerHighOverWarning(111),
				gotDMITxPowerHighFallWarning(112),
				gotDMITxPowerLowOverWarning(113),
				gotDMITxPowerLowFallWarning(114),
				gotDMIRxPowerHighOverAlarm(115),
				gotDMIRxPowerHighFallAlarm(116),
				gotDMIRxPowerLowOverAlarm(117),
				gotDMIRxPowerLowFallAlarm(118),
				gotDMIRxPowerHighOverWarning(119),
				gotDMIRxPowerHighFallWarning(120),
				gotDMIRxPowerLowOverWarning(121),
				gotDMIRxPowerLowFallWarning(122),
				nosRemoteUpgradeRequest(123),
				nosRemoteUpgradeSuccess(124),
				nosRemoteUpgradeFailAbort(125),
				nosRemoteUpgradeFailHeaderError(126),
				nosRemoteUpgradeFailDownloadError(127),
				nosRemoteUpgradeFailFlashError(128),
				nosRemoteUpgradeStart(129),
				systemDyingGasp(130),
				remoteOamDyingGasp(131),
				remoteOamDyingGaspRestoration(132),
				swWatchdogInetAbnormalState(150),
				swWatchdogInetNormalState(151),
				swWatchdogInetDetectError(152),
				swWatchdogInetClearError(153),
				swWatchdogPonAbnormalState(154),
				swWatchdogPonNormalState(155),
				swWatchdogPonDetectError(156),
				swWatchdogPonClearError(157),
				advaTemperature(201),
				advaTemperatureNo(202),
				advaPSUFailure(203),
				advaPSUFailureNo(204),
				advaFanFailure(205),
				advaFanFailureNo(206),
				advaInterfaceReceiveFailure(207),
				advaInterfaceReceiveFailureNo(208),
				advaInterfaceOpticalThreshold(209),
				advaInterfaceOpticalThresholdNo(210),
				advaInterfaceTransmitFault(211),
				advaInterfaceTransmitFaultNo(212),
				advaInterfaceMisconfiguration(213),
				advaInterfaceMisconfigurationNo(214),
				advaInterfaceSFPMismatch(215),
				advaInterfaceSFPMismatchNo(216),
				advaVoltageLow(217),
				advaVoltageLowNo(218),
				advaVoltageHigh(219),
				advaVoltageHighNo(220),
				erpDomainLotp(301),
				erpDomainLotpNo(302),
				erpDomainULotp(303),
				erpDomainULotpNo(304),
				erpDomainMultipleRM(305),
				erpDomainMultipleRMNo(306),
				erpDomainRMNodeReacheablity(307),
				erpDomainRMNodeReacheablityNo(308),
				eponOnuDeregister(401),
				eponOnuRegister(402),
				eponOnuRegistrationError(403),
				eponOnuNoRegistrationError(404),
				eponBadEncryptionKey(405),
				eponNoBadEncryptionKey(406),
				eponLlidMistmatch(407),
				eponNoLlidMismatch(408),
				eponTooManyRegister(409),
				eponNoTooManyRegister(410),
				eponDyingGASP(411),
				eponNoDyingGASP(412),
				eponOnuErrFramePeriod(413),
				eponOnuNoErrFramePeriod(414),
				eponOnuErrFrame(415),
				eponOnuNoErrFrame(416),
				eponOnuErrFrameSecondSummary(417),
				eponOnuNoErrFrameSecondSummary(418),
				eponOnuLastOnuDeregister(419),
				eponOnuNoLastOnuDeregister(420),
				eponOltCableDown(421),
				eponOltRecoverCableDown(422),
				autoCLIStart(501),
				autoCLINoStart(502),
				autoCLIComplete(503),
				autoCLINoComplete(504),
				autoCLIRemoveOutputFile(505),
				autoCLINoRemoveOutputFile(506),
				autoResetSystem(507),
				autoResetNoSystem(508),
				autoResetPingReplyLoss(509),
				autoResetNoPingReplyLoss(510),
				autoResetMemoryLeakDetect(511),
				autoResetNoMemoryLeakDetect(512),
				arulePacketDropDetect(601),
				arulePacketDropRelease(602),
				autoCpeUpgradeStart(605),
				autoCpeUpgradeFail(607),
				autoCpeUpgradeSuccess(609),
				batteryUnderTemper(611),
				batteryTemperUnderToNormal(612),
				batteryCellAbnormal(613),
				batteryCellNormal(614),
				batteryCellTestChargeStarted(615),
				batteryCellTestChargeFinished(616),
				batteryAcPowerFault(617),
				batteryAcPowerOk(618),
				bME1CardNoDetect(620),
				clearBME1CardNoDetect(621),
				bME1CardAFEerror(622),
				clearBME1CardAFEerror(623),
				bME1CardIFEerror(624),
				clearBME1CardIFEerror(625),
				bME1CardFWerror(626),
				clearBME1CardFWerror(627),
				bME1CardPROVerror(628),
				clearBME1CardPROVerror(629),
				bME1CrashDetect(630),
				clearBME1CrashDetect(631),
				bME2CardNoDetect(632),
				clearBME2CardNoDetect(633),
				bME2CardAFEerror(634),
				clearBME2CardAFEerror(635),
				bME2CardIFEerror(636),
				clearBME2CardIFEerror(637),
				bME2CardFWerror(638),
				clearBME2CardFWerror(639),
				bME2CardPROVerror(640),
				clearBME2CardPROVerror(641),
				bME2CrashDetect(642),
				clearBME2CrashDetect(643),
				bME3CardNoDetect(644),
				clearBME3CardNoDetect(645),
				bME3CardAFEerror(646),
				clearBME3CardAFEerror(647),
				bME3CardIFEerror(648),
				clearBME3CardIFEerror(649),
				bME3CardFWerror(650),
				clearBME3CardFWerror(651),
				bME3CardPROVerror(652),
				clearBME3CardPROVerror(653),
				bME3CrashDetect(654),
				clearBME3CrashDetect(655),
				powerFromBattery(656),
				clearPowerFromBattery(657),
				invalidBatteryStatus(658),
				clearInvalidBatteryStatus(659),
				batteryChargeLow(660),
				clearBatteryChargeLow(661),
				batteryNotPresent(662),
				clearBatteryNotPresent(663),
				voltageLow(664),
				clearVoltageLow(665),
				tempOverThreshold(666),
				clearTempOverThreshold(667),
				tempUnderThreshold(668),
				clearTempUnderThreshold(669),
				cpuOverThreshold(670),
				clearCpuOverThreshold(671),
				trafficOverload(672),
				clearTrafficOverload(673),
				gEPONModuleNotDetect(674),
				clearGEPONModuleNotDetect(675),
				gEPONPortOperationDown(676),
				clearGEPONPortOperationDown(677),
				gEPONNoIncomingTraffic(678),
				clearGEPONNoIncomingTraffic(679),
				processCrashDetect(680),
				clearProcessCrashDetect(681),
				memoryLeakDetect(682),
				clearMemoryLeakDetect(683),
				memoryCorrupDetect(684),
				clearMemoryCorrupDetect(685),
				memoryLowDetect(686),
				clearMemoryLowDetect(687),
				dataLineerror(688),
				clearDataLineerror(689),
				addressLineerror(690),
				clearAddressLineerror(691),
				chipsetNotDetcet(692),
				clearChipsetNotDetcet(693),
				pciBuserror(694),
				clearPciBuserror(695),
				securityAdminConnect(696),
				clearSecurityAdminConnect(697),
				oNUPowerDown(698),
				clearONUPowerDown(699),
				oNUNotRegister(700),
				clearONUNotRegister(701),
				oNTOpticPre(702),
				clearONTOpticPre(703),
				switchoverInitiated(800),
				switchoverDone(801)
				}
			MAX-ACCESS read-write
			STATUS current
			DESCRIPTION
				" A number identifying this alarm severity profile. 
				 The following alarms is devided by the specific character, ===============.
				 The division basis is that alarms is bounded or released.
				
				        001: portDown: To detect whether physical or logical interface's link status is up or down.
					002: portUp: 
					===============
					003: portRemoved: To detect whether physical interface is installed or not.
					004: portInstalled: 
					===============
					005: powerFail: To detect whether power module's operation status is good or not.
							(Without doubt, more than 1 power module should be equipped.)
					006: powerOK: 
					===============
					007: powerRemoved: To detect whether power module is installed or not, through the PLD access.
							   (Without doubt, more than 1 power module should be equipped.)
					008: powerInstalled: 
					===============
					009: fanFail: To detect whether FAN module's operation status is good or not.
					010: fanOK: 
					===============
					011: fanRemoved: To detect whether FAN module is installed or not, through the PLD access.
					012: fanInstalled: 
					===============
					013: moduleRemoved: To detect whether physical interface module is installed or not, through the S/W I2C
					014: moduleInstalled: 
					===============
					015: systemRestart: Network system is restarted by operator. This is not H/W start but S/W start.
					===============
					016: systemStart: Network system is restarted by operator or system status. This is not S/W start but H/W start.
							  (This alarm isn’t used current)
					===============
					017: broadcastOver: To detect the receipt of broadcast packet.
				  			    (This alarm isn’t used current)
					018: broadcastUnder: 
					===============
					019: cpuOverLoad: To detect whether the configured CPU load threshold is less than current CPU load usage or not.
					020: cpuUnderLoad: 
					===============
					021: memoryOverUsed: To detect whether the configured memory threshold is less than current memory usage or not.
					022: memoryUnderUsed: 
					===============
					023: portOverThreshold: To detect whether the configured physical or logical interface threshold is 
								less than delta value of current interface's InOctects or not.
					024: portUnderThreshold: 
					===============
					025: temperatureHigh: To detect whether the configured system's temperature threshold is 
							      less than current temperature or not.
					026: temperatureLow: 
					===============
					027: mfgdBlocked: To detect whether the specific MAC by MAC flood guard is blocked or not.
					028: mfgdReleased: 
					===============
					029: ipConflict: To detect whether the same IP address on different network node is configured or not.
					030: ipUnconflict: 
					===============
					031: dhcpLeaseShortage: To detect whether IP address that can be assigned to subscriber by DHCP server is 
								sufficient or not.
					032: dhcpLeaseSufficient: 
					===============
					033: dhcpOccuredIllegalEntry: To detect whether a subsceiber is using a static IP address or not.
					034: dhcpRemovedIllegalEntry: 
					===============
					035: rmonAlarmRising: To detect whether rising threshold of a specific MO in RMON alarm sampling is 
							      less than current calculated value by alarm sample type or not. But alarm generation 
							      would be issued by means of event type in RMON event.
					036: rmonAlarmNoRising: 
					===============
					037: rmonAlarmFalling: To detect whether falling threshold of a specific MO in RMON alarm sampling is 
							       less than current calculated value by alarm sample type or not. 
							       But alarm generation would be issued by means of event type in RMON event.
					038: rmonAlarmNoFalling: 
					===============
					039: bpduGuardDisabled: To detect whether edge ports is guarded about superior BPDU or not. 
								In case of insertion edge node with 0 or lower priority than priority of current root bridge node, 
								it will be disarrangement during a short time because of recognition a new inserted node 
								as root bridge. 
								So these edge ports is guarded, and then edge ports is blocked about all superior BPDU. 
								So STP reconfiguration doesn't use this edge ports.
					===============
					040: rootGuardDisabled: To detect whether edge ports is guarded about superior BPDU or not. 
								In case of insertion edge node with 0 or lower priority than priority of current root bridge node, 
								it will be disarrangement during a short time because of recognition a new inserted node 
								as root bridge. 
								So, Root guard prevents a new inserted node from being root bridge as well as 
								receiving a superior BPDU from root bridge. 
								but this node participates in STP topology reconfiguration. 
								If root bridge does not send a superior BPDU, then this node acts usually though STP state change.
					===============
					041: portSecurity: To detect whether interface is configured for security or not. 
							   This can be used to prevent MAC from flooding as well as spoofing. 
							   That is, As a result, this will obstruct an attack as like DoS attack.
					===============
					042: userLogin: 
					043: userLogout: 
					===============
					051: igmpGroupJoined: To detect whether a subscriber is joined a multicast group or not.
					052: igmpGroupLeaved: 
					===============
					053: dhcpIpaddressBound: To detect wether a dynamic IP address is assigned to a subscriber or not.
					054: dhcpIpaddressFree: 
					===============
					055: doorOpened: To detect whether outer door is opeded or not, as external alarm.
					056: doorClosed: 
					===============
					057: powerModeChangedPowerToBattery: To detect whether a system is using AC power or battery. 
									     A system is using AC power usually. 
									     If there is any power problems as like a power failure, 
									     a system is using battery instead of AC power. 
					058: powerModeChangedBatteryToPower: 
					===============
					059: batterylowcapacity: To detect whether current battery capacity is less 
								 capacity threshold according to battery usage or not. 
								 The capacity of AC power is 16 voltage and battery is 20. 
								 Capacity threshold is configured by H/W specification.
								 So operator can't change it.
					060: batterynormalcapacity: 
					===============
					061: batteryhighTemperature: To detect whether current temperature of battery is greater than temperature threshold or not. 
					062: batterynormalTemperature: 
					===============
					063: authenticationFail: To detect whether the connected user is authentic or non-authentic.
					064: authenticationNofail: 
					===============
					065: psuAcHighTemperature: To detect whether current temperature of Power Supply Unit is 
								   greater than temperature threshold or not. 
					066: psuAcNormalTemperature: 
					===============
					067: batteryRemoved: To detect whether battery is equipped at network system or not. 
							     Battery is used as redundancy power service. So operator can decide the installation of battery.
					068: batteryEquipped: 
					===============
					069: batteryLowVoltage: To detect whether battery voltage is less than 12.5 volt or not. 
								12.5 volt value is configured by H/W specification. So operator can't change it.
					070: batteryNormalVoltage: 
					===============
					071: adminAccessLogin: To detect whether a operator connects at this network system or not.
					072: adminAccessLogout: 
					===============
					073: cfgdBlocked: To detect whether it is blocked flood to CPU or not.
					074: cfgdReleased: 
					===============
					075: sfgdBlocked: To detect whether it is blocked flood to system or not.
					076: sfgdReleased: 
					===============
					077: swWatchdogAbnormalState: To detect whether a specific process acts normally or not.
					078: swWatchdogNormalState: 
					===============
					079: swWatchdogDetectError: To detect whether a specific process is detected a error related to itself or cleared.
					080: swWatchdogClearError: 
					===============
					081: ppsControlBlocked: To detect whether it is blocked by pps-control or not.
					082: ppsControlReleased: 
					===============
					083: gotDMITempHighOverAlarm: To detect whether internal temperature exceeds high alarm level or not.
					084: gotDMITempHighFallAlarm: 
					===============
					085: gotDMITempLowOverAlarm: To detect whether internal temperature is below low alarm level or not.
					086: gotDMITempLowFallAlarm: 
					===============
					087: gotDMITempHighOverWarning: To detect whether internal temperature exceeds high warning level or not.
					088: gotDMITempHighFallWarning: 
					===============
					089: gotDMITempLowOverWarning: To detect whether internal temperature is below low warning level or not.
					090: gotDMITempLowFallWarning: 
					===============
					091: gotDMIVolHighOverAlarm: To detect whether internal supply voltage exceeds high alarm level or not.
					092: gotDMIVolHighFallAlarm: 
					===============
					093: gotDMIVolLowOverAlarm: To detect whether internal supply voltage is below low alarm level or not.
					094: gotDMIVolLowFallAlarm: 
					===============
					095: gotDMIVolHighOverWarning: To detect whether internal supply voltage exceeds high warning level or not.
					096: gotDMIVolHighFallWarning: 
					===============
					097: gotDMIVolLowOverWarning: To detect whether internal supply voltage is below low warning level or not.
					098: gotDMIVolLowFallWarning: 
					===============
					099: gotDMITxBiasHighOverAlarm: To detect whether TX Bias current exceeds high alarm level or not.
					100: gotDMITxBiasHighFallAlarm: 
					===============
					101: gotDMITxBiasLowOverAlarm: To detect whether TX Bias current is below low alarm level or not.
					102: gotDMITxBiasLowFallAlarm: 
					===============
					103: gotDMITxBiasHighOverWarning: To detect whether TX Bias current exceeds high warning level or not.
					104: gotDMITxBiasHighFallWarning: 
					===============
					105: gotDMITxBiasLowOverWarning: To detect whether TX Bias current is below low warning level or not.
					106: gotDMITxBiasLowFallWarning: 
					===============
					107: gotDMITxPowerHighOverAlarm: To detect whether TX output power exceeds high alarm level or not.
					108: gotDMITxPowerHighFallAlarm: 
					===============
					109: gotDMITxPowerLowOverAlarm: To detect whether TX output power is below low alarm level or not.
					110: gotDMITxPowerLowFallAlarm: 
					===============
					111: gotDMITxPowerHighOverWarning: To detect whether TX output power exceeds high warning level or not.
					112: gotDMITxPowerHighFallWarning: 
					===============
					113: gotDMITxPowerLowOverWarning: To detect whether TX output power is below low warning level or not.
					114: gotDMITxPowerLowFallWarning: 
					===============
					115: gotDMIRxPowerHighOverAlarm: To detect whether RX output power exceeds high alarm level or not.
					116: gotDMIRxPowerHighFallAlarm: 
					===============
					117: gotDMIRxPowerLowOverAlarm: To detect whether RX output power is below low alarm level or not.
					118: gotDMIRxPowerLowFallAlarm: 
					===============
					119: gotDMIRxPowerHighOverWarning: To detect whether RX output power exceeds high warning level or not.
					120: gotDMIRxPowerHighFallWarning: 
					===============
					121: gotDMIRxPowerLowOverWarning: To detect whether RX output power is below low warning level or not.
					122: gotDMIRxPowerLowFallWarning: 
					===============
					123: nosRemoteUpgradeRequest: 
					124: nosRemoteUpgradeSuccess: 
					125: nosRemoteUpgradeFailAbort: 
					126: nosRemoteUpgradeFailHeaderError: 
					127: nosRemoteUpgradeFailDownloadError: 
					128: nosRemoteUpgradeFailFlashError: 
					129: nosRemoteUpgradeStart: 
					===============
				        130: systemDyingGasp
					===============
					201: advaTemperature: To detect whether current chassis temperature is less than chassis temperature threshold or not.
					202: advaTemperatureNo: 
					===============
					203: advaPSUFailure: To detect whether ADVA system's power supply unit has a failure or not.
					204: advaPSUFailureNo: 
					===============
					205: advaFanFailure: To detect whether ADVA system's FAN has a failure or not.
					206: advaFanFailureNo: 
					===============
					207: advaInterfaceReceiveFailure: To detect whether ADVA system's receipt has a failure or not.
					208: advaInterfaceReceiveFailureNo:  
					===============
					209: advaInterfaceOpticalThreshold: To detect whether Adva system's optical receive power level is 
									    less than optical threshold or not.
					210: advaInterfaceOpticalThresholdNo: 
					===============
					211: advaInterfaceTransmitFault: To detect whether ADVA system's transmission has a failure or not.
					212: advaInterfaceTransmitFaultNo: 
					===============
					213: dvaInterfaceMisconfiguration: To detect whether ADVA system's interface is configured rightly or not.
					214: advaInterfaceMisconfigurationNo: 
					===============
					215: advaInterfaceSFPMismatch: To detect whether ADVA system's SFP interface is mismatched or not.
					216: advaInterfaceSFPMismatchNo: 
					===============
					217: advaVoltageLow: To detect whether ADVA system's current voltage is less than voltage threshold or not.
					218: advaVoltageLowNo: 
					===============
					219: advaVoltageHigh: To detect whether ADVA system's current voltage is greater than voltage threshold or not.
					220: advaVoltageHighNo: 
					===============
					301: erpDomainLotp: To detect whether LOTP(Loss of Test Packet) exists a domain of ERP or not. 
							    The Loss of Test Packet defect is defined when a node does not receive 
							    any test packet at any of its ports for a period of 3 times.
					302: erpDomainLotpNo: 
					===============
					303: erpDomainULotp: To detect whether undirectional LOTP(Loss of Test Packet) exists a domain of ERP or not. 
							     The Loss of Test Packet defect is defined when a RM node of one domain does not 
							     receive any test packet at one port for a period of 3 times.
					304: erpDomainULotpNo: 
					===============
					305: erpDomainMultipleRM: To detect whether Multiple RM node is supported or not. 
								  The defect is raised when a RM node receives its own test packets 
								  with an Ack destination address field with a non-zero value.
					306: erpDomainMultipleRMNo: 
					===============
					307: erpDomainRMNodeReacheablity: To detect whether RM reachability is raised or not. 
									  The detection of multiple failures indicates that the ring is segmented and 
								          that the RM Node is unreacheable. 
									  This is only possible at normal ring nodes isolated from the RM node.
					308: erpDomainRMNodeReacheablityNo: 
					===============
					401: eponOnuDeregister: To detect whether ONU is registered into OLT or not. 
								That is, ONU that its operation is service on should be sent registration information to OLT. 
					402: eponOnuRegister: 
					===============
					403: eponOnuRegistrationError: To detect whether ONU is failed registeration process into OLT.
					404: eponOnuNoRegistrationError: 
					===============
					405: eponBadEncryptionKey: To detect wwhether the encryption key is valid or not.
								   A message between ONU and OLT is encrypted using random encryption key. 
								   There is that the encryption key is invalid as transmission failure from time to time.
					406: eponNoBadEncryptionKey: 
					===============
					407: eponLlidMistmatch: To detect whether Llid of message between ONU and OLT is valid or not. 
								On registering, ONU informs unique ID to OLT.
								And then, all communication between ONU and OLT must use the unique ID. 
								The unique ID is called Llid.
					408: eponNoLlidMismatch: 
					===============
					409: eponTooManyRegister: To detect whether the registered ONU per 1 OLT is greater than 32 or not. 
								  That is, ONU can be registered from 1 to the maximum 32 at 1 OLT.
					410: eponNoTooManyRegister: 
					===============
					411: eponDyingGASP: To detect whether a ONU is down from dying gasp or not. 
							    A ONU could be changed to down state as a number of reasons.
							    By the way, ONU that is changed to down as dying gasp would be sent dying gasp signal to OLT and 
							    then ONU's link would be changed to down.
					412: eponNoDyingGASP: 
					===============
					413: eponOnuErrFramePeriod: 
					414: eponOnuNoErrFramePeriod: 
					===============
					415: eponOnuErrFrame: 
					416: eponOnuNoErrFrame: 
					===============
					417: eponOnuErrFrameSecondSummary: 
					418: eponOnuNoErrFrameSecondSummary: 
					===============
					419: eponOnuLastOnuDeregister: To detect whether a deregistered ONU is last ONU or not. 
								       If a deregistered ONU is last ONU, the OLT would be changed to serviceable status. 
					420: eponOnuNoLastOnuDeregister: 
					===============
					421: eponOltCableDown: 
					422: eponOltRecoverCableDown: 
					===============
					501: autoCLIStart: To detect whether the scheduled auto CLI is started or not.
					502: autoCLINoStart: 
					===============
					503: autoCLIComplete: To detect whether the scheduled auto CLI is completed or not. 
					504: autoCLINoComplete: 
					===============
					505: autoCLIRemoveOutputFile: To detect whether the result file of the scheduled auto CLI is removed or not.
								      The reason that the result file is removed is that the configured file size for the result  is
								      less than the stored result file size. 
								      If so, the oldest file would be removed before everything.
					506: autoCLINoRemoveOutputFile: 
					===============
					507: autoResetSystem: To detect whether the system is restarted or not. 
							      The conditions that system is restarted is that ping loss threshold is 
							      less than current ping loss count during the configured interval and 
							      that current free memory size is less than configured free memory size.
					508: autoResetNoSystem: 
					===============
					509: autoResetPingReplyLoss: To detect whether ping reply from the designated network node is received or not.
								     Operator designates any gateway system that can communicate to detect 
								     current network environment. 
								     System sends ICMP packet to the designated gateway system periodically. 
								     If  the system doesn't receive ping reply packet within any interval, 
								     operator recognizes that the system can't communicate any more 
								     because of some problems of the system. 
					510: autoResetNoPingReplyLoss: 
					===============
					511: autoResetMemoryLeakDetect: To detect whether current free memory size is 
									less than the configured free memory size or not. 
									Periodically, free memory size is checked to confirm system availability.
					512: autoResetNoMemoryLeakDetect: 
					===============
					601: arulePacketDropDetect: To detect whether it is dropped some packet by arule or not.
					602: arulePacketDropRelease: 
					===============
					620: bME1CardNoDetect: 
					621: clearBME1CardNoDetect: 
					===============
					622: bME1CardAFEerror: 
					623: clearBME1CardAFEerror: 
					===============
					624: bME1CardIFEerror: 
					625: clearBME1CardIFEerror: 
					===============
					626: bME1CardFWerror: 
					627: clearBME1CardFWerror: 
					===============
					628: bME1CardPROVerror: 
					629: clearBME1CardPROVerror: 
					===============
					630: bME1CrashDetect: 
					631: clearBME1CrashDetect: 
					===============
					632: bME2CardNoDetect: 
					633: clearBME2CardNoDetect: 
					===============
					634: bME2CardAFEerror: 
					635: clearBME2CardAFEerror: 
					===============
					636: bME2CardIFEerror: 
					637: clearBME2CardIFEerror: 
					===============
					638: bME2CardFWerror: 
					639: clearBME2CardFWerror: 
					===============
					640: bME2CardPROVerror: 
					641: clearBME2CardPROVerror: 
					===============
					642: bME2CrashDetect: 
					643: clearBME2CrashDetect: 
					===============
					644: bME3CardNoDetect: 
					645: clearBME3CardNoDetect: 
					===============
					646: bME3CardAFEerror: 
					647: clearBME3CardAFEerror: 
					===============
					648: bME3CardIFEerror: 
					649: clearBME3CardIFEerror: 
					===============
					650: bME3CardFWerror: 
					651: clearBME3CardFWerror: 
					===============
					652: bME3CardPROVerror: 
					653: clearBME3CardPROVerror: 
					===============
					654: bME3CrashDetect: 
					655: clearBME3CrashDetect: 
					===============
					656: powerFromBattery: 
					657: clearPowerFromBattery: 
					===============
					658: invalidBatteryStatus: 
					659: clearInvalidBatteryStatus: 
					===============
					660: batteryChargeLow: 
					661: clearBatteryChargeLow: 
					===============
					662: batteryNotPresent: 
					663: clearBatteryNotPresent: 
					===============
					664: voltageLow: 
					665: clearVoltageLow: 
					===============
					666: tempOverThreshold: 
					667: clearTempOverThreshold: 
					===============
					668: tempUnderThreshold: 
					669: clearTempUnderThreshold: 
					===============
					670: cpuOverThreshold: 
					671: clearCpuOverThreshold: 
					===============
					672: trafficOverload: 
					673: clearTrafficOverload: 
					===============
					674: gEPONModuleNotDetect: 
					675: clearGEPONModuleNotDetect:
					===============
					676: gEPONPortOperationDown: 
					677: clearGEPONPortOperationDown: 
					===============
					678: gEPONNoIncomingTraffic: 
					679: clearGEPONNoIncomingTraffic: 
					===============
					680: processCrashDetect: 
					681: clearProcessCrashDetect: 
					===============
					682: memoryLeakDetect: 
					683: clearMemoryLeakDetect: 
					===============
					684: memoryCorrupDetect: 
					685: clearMemoryCorrupDetect: 
					===============
					686: memoryLowDetect: 
					687: clearMemoryLowDetect: 
					===============
					688: dataLineerror: 
					689: clearDataLineerror: 
					===============
					690: addressLineerror: 
					691: clearAddressLineerror: 
					===============
					692: chipsetNotDetcet: 
					693: clearChipsetNotDetcet: 
					===============
					694: pciBuserror: 
					695: clearPciBuserror: 
					===============
					696: securityAdminConnect: 
					697: clearSecurityAdminConnect: 
					===============
					698: oNUPowerDown: 
					699: clearONUPowerDown: 
					===============
					700: oNUNotRegister: 
					701: clearONUNotRegister: 
					===============
					702: oNTOpticPre: 
					703: clearONTOpticPre: 
					===============
					800: switchoverInitiated: 
					===============
					801: switchoverDone: 
					===============
				"
			::= { sleAlarmSeverityControl 6 }

		
		-- 1.3.6.1.4.1.6296.101.4.2.2.7
		sleAlarmSeverityControlValue OBJECT-TYPE
			SYNTAX INTEGER
				{
				critical(1),
				major(2),
				minor(3),
				warning(4),
				intermediate(5)
				}
			MAX-ACCESS read-write
			STATUS current
			DESCRIPTION
				" The severity of alarm. "
			::= { sleAlarmSeverityControl 7 }

		
		-- 1.3.6.1.4.1.6296.101.4.2.3
		sleAlarmSeverityNotification OBJECT IDENTIFIER ::= { sleAlarmSeverity 3 }

		
		-- 1.3.6.1.4.1.6296.101.4.2.3.1
		sleAlarmSeveriityCreated NOTIFICATION-TYPE
			OBJECTS { sleAlarmSeverityValue, sleAlarmSeverityControlRequest, sleAlarmSeverityControlTimeStamp, sleAlarmSeverityControlReqResult }
			STATUS current
			DESCRIPTION 
				"Description."
			::= { sleAlarmSeverityNotification 1 }

		
		-- 1.3.6.1.4.1.6296.101.4.2.3.2
		sleAlarmSeveriityDestroyed NOTIFICATION-TYPE
			OBJECTS { sleAlarmSeverityControlRequest, sleAlarmSeverityControlTimeStamp, sleAlarmSeverityControlReqResult, sleAlarmSeverityValue }
			STATUS current
			DESCRIPTION 
				"Description."
			::= { sleAlarmSeverityNotification 2 }

		
		-- 1.3.6.1.4.1.6296.101.4.2.3.3
		sleAlarmSeverityChanged NOTIFICATION-TYPE
			OBJECTS { sleAlarmSeverityValue, sleAlarmSeverityControlRequest, sleAlarmSeverityControlTimeStamp, sleAlarmSeverityControlReqResult }
			STATUS current
			DESCRIPTION 
				"Description."
			::= { sleAlarmSeverityNotification 3 }

		
		-- 1.3.6.1.4.1.6296.101.4.3
		sleAlarmReport OBJECT IDENTIFIER ::= { sleFaultMgmt 3 }

		
		-- 1.3.6.1.4.1.6296.101.4.3.1
		sleAlarmReportTable OBJECT-TYPE
			SYNTAX SEQUENCE OF SleAlarmReportEntry
			MAX-ACCESS not-accessible
			STATUS current
			DESCRIPTION
				" The alarm list table is used to store all reported alarms. "
			::= { sleAlarmReport 1 }

		
		-- 1.3.6.1.4.1.6296.101.4.3.1.1
		sleAlarmReportEntry OBJECT-TYPE
			SYNTAX SleAlarmReportEntry
			MAX-ACCESS not-accessible
			STATUS current
			DESCRIPTION
				" Entry of the alarm lis table. "
			INDEX { sleAlarmSpecificCode, sleAlarmReportingSourceType, sleAlarmReportingSource }
			::= { sleAlarmReportTable 1 }

		
		SleAlarmReportEntry ::=
			SEQUENCE { 
				sleAlarmSpecificCode
					INTEGER,
				sleAlarmReportingSourceType
					INTEGER,
				sleAlarmReportingSource
					OCTET STRING,
				sleAlarmSpecificSeverity
					INTEGER,
				sleAlarmSpecificProblem
					Unsigned32,
				sleAlarmSpecificProblemText
					OCTET STRING,
				sleAlarmTimeAndDate
					Integer32,
				sleAlarmSpecificSeqNum
					Counter32
			 }

		-- 1.3.6.1.4.1.6296.101.4.3.1.1.1
		sleAlarmSpecificCode OBJECT-TYPE
			SYNTAX INTEGER
				{
				portDown(1),
				portUp(2),
				portRemoved(3),
				portInstalled(4),
				powerFail(5),
				powerOK(6),
				powerRemoved(7),
				powerInstalled(8),
				fanFail(9),
				fanOK(10),
				fanRemoved(11),
				fanInstalled(12),
				moduleRemoved(13),
				moduleInstalled(14),
				systemRestart(15),
				systemStart(16),
				broadcastOver(17),
				broadcastUnder(18),
				cpuOverLoad(19),
				cpuUnderLoad(20),
				memoryOverUsed(21),
				memoryUnderUsed(22),
				portOverThreshold(23),
				portUnderThreshold(24),
				temperatureHigh(25),
				temperatureLow(26),
				mfgdBlocked(27),
				mfgdReleased(28),
				ipConflict(29),
				ipUnconflict(30),
				dhcpLeaseShortage(31),
				dhcpLeaseSufficient(32),
				dhcpOccuredIllegalEntry(33),
				dhcpRemovedIllegalEntry(34),
				rmonAlarmRising(35),
				rmonAlarmNoRising(36),
				rmonAlarmFalling(37),
				rmonAlarmNoFalling(38),
				bpduGuardDisabled(39),
				rootGuardDisabled(40),
				portSecurity(41),
				userLogin(42),
				userLogout(43),
				igmpGroupJoined(51),
				igmpGroupLeaved(52),
				dhcpIpaddressBound(53),
				dhcpIpaddressFree(54),
				doorOpened(55),
				doorClosed(56),
				powerModeChangedPowerToBattery(57),
				powerModeChangedBatteryToPower(58),
				batterylowcapacity(59),
				batterynormalcapacity(60),
				batteryhighTemperature(61),
				batterynormalTemperature(62),
				authenticationFail(63),
				authenticationNoFail(64),
				psuAcHighTemperature(65),
				psuAcNormalTemperature(66),
				batteryRemoved(67),
				batteryEquipped(68),
				batteryLowVoltage(69),
				batteryNormalVoltage(70),
				adminAccessLogin(71),
				adminAccessLogout(72),
				cfgdBlocked(73),
				cfgdReleased(74),
				sfgdBlocked(75),
				sfgdReleased(76),
				swWatchdogAbnomalState(77),
				swWatchdogNomalState(78),
				swWatchdogDetectError(79),
				swWatchdogClearError(80),
				ppsControlBlocked(81),
				ppsControlReleased(82),
				gotDMITempHighOverAlarm(83),
				gotDMITempHighFallAlarm(84),
				gotDMITempLowOverAlarm(85),
				gotDMITempLowFallAlarm(86),
				gotDMITempHighOverWarning(87),
				gotDMITempHighFallWarning(88),
				gotDMITempLowOverWarning(89),
				gotDMITempLowFallWarning(90),
				gotDMIVolHighOverAlarm(91),
				gotDMIVolHighFallAlarm(92),
				gotDMIVolLowOverAlarm(93),
				gotDMIVolLowFallAlarm(94),
				gotDMIVolHighOverWarning(95),
				gotDMIVolHighFallWarning(96),
				gotDMIVolLowOverWarning(97),
				gotDMIVolLowFallWarning(98),
				gotDMITxBiasHighOverAlarm(99),
				gotDMITxBiasHighFallAlarm(100),
				gotDMITxBiasLowOverAlarm(101),
				gotDMITxBiasLowFallAlarm(102),
				gotDMITxBiasHighOverWarning(103),
				gotDMITxBiasHighFallWarning(104),
				gotDMITxBiasLowOverWarning(105),
				gotDMITxBiasLowFallWarning(106),
				gotDMITxPowerHighOverAlarm(107),
				gotDMITxPowerHighFallAlarm(108),
				gotDMITxPowerLowOverAlarm(109),
				gotDMITxPowerLowFallAlarm(110),
				gotDMITxPowerHighOverWarning(111),
				gotDMITxPowerHighFallWarning(112),
				gotDMITxPowerLowOverWarning(113),
				gotDMITxPowerLowFallWarning(114),
				gotDMIRxPowerHighOverAlarm(115),
				gotDMIRxPowerHighFallAlarm(116),
				gotDMIRxPowerLowOverAlarm(117),
				gotDMIRxPowerLowFallAlarm(118),
				gotDMIRxPowerHighOverWarning(119),
				gotDMIRxPowerHighFallWarning(120),
				gotDMIRxPowerLowOverWarning(121),
				gotDMIRxPowerLowFallWarning(122),
				nosRemoteUpgradeRequest(123),
				nosRemoteUpgradeSuccess(124),
				nosRemoteUpgradeFailAbort(125),
				nosRemoteUpgradeFailHeaderError(126),
				nosRemoteUpgradeFailDownloadError(127),
				nosRemoteUpgradeFailFlashError(128),
				nosRemoteUpgradeStart(129),
				systemDyingGasp(130),
				remoteOamDyingGasp(131),
				remoteOamDyingGaspRestoration(132),
				swWatchdogInetAbnormalState(150),
				swWatchdogInetNormalState(151),
				swWatchdogInetDetectError(152),
				swWatchdogInetClearError(153),
				swWatchdogPonAbnormalState(154),
				swWatchdogPonNormalState(155),
				swWatchdogPonDetectError(156),
				swWatchdogPonClearError(157),
				arpInspectInvalid(158),
				clockModuleInstalled(159),
				clockModuleRemoved(160),
				clockModuleInitOk(161),
				clockModuleInitFail(162),
				advaTemperature(201),
				advaTemperatureNo(202),
				advaPSUFailure(203),
				advaPSUFailureNo(204),
				advaFanFailure(205),
				advaFanFailureNo(206),
				advaInterfaceReceiveFailure(207),
				advaInterfaceReceiveFailureNo(208),
				advaInterfaceOpticalThreshold(209),
				advaInterfaceOpticalThresholdNo(210),
				advaInterfaceTransmitFault(211),
				advaInterfaceTransmitFaultNo(212),
				advaInterfaceMisconfiguration(213),
				advaInterfaceMisconfigurationNo(214),
				advaInterfaceSFPMismatch(215),
				advaInterfaceSFPMismatchNo(216),
				advaVoltageLow(217),
				advaVoltageLowNo(218),
				advaVoltageHigh(219),
				advaVoltageHighNo(220),
				erpDomainLotp(301),
				erpDomainLotpNo(302),
				erpDomainULotp(303),
				erpDomainULotpNo(304),
				erpDomainMultipleRM(305),
				erpDomainMultipleRMNo(306),
				erpDomainRMNodeReacheablity(307),
				erpDomainRMNodeReacheablityNo(308),
				eponOnuDeregister(401),
				eponOnuRegister(402),
				eponOnuRegistrationError(403),
				eponOnuNoRegistrationError(404),
				eponBadEncryptionKey(405),
				eponNoBadEncryptionKey(406),
				eponLlidMistmatch(407),
				eponNoLlidMismatch(408),
				eponTooManyRegister(409),
				eponNoTooManyRegister(410),
				eponDyingGASP(411),
				eponNoDyingGASP(412),
				eponOnuErrFramePeriod(413),
				eponOnuNoErrFramePeriod(414),
				eponOnuErrFrame(415),
				eponOnuNoErrFrame(416),
				eponOnuErrFrameSecondSummary(417),
				eponOnuNoErrFrameSecondSummary(418),
				eponOnuLastOnuDeregister(419),
				eponOnuNoLastOnuDeregister(420),
				eponOltCableDown(421),
				eponOltRecoverCableDown(422),
				autoCLIStart(501),
				autoCLINoStart(502),
				autoCLIComplete(503),
				autoCLINoComplete(504),
				autoCLIRemoveOutputFile(505),
				autoCLINoRemoveOutputFile(506),
				autoResetSystem(507),
				autoResetNoSystem(508),
				autoResetPingReplyLoss(509),
				autoResetNoPingReplyLoss(510),
				autoResetMemoryLeakDetect(511),
				autoResetNoMemoryLeakDetect(512),
				arulePacketDropDetect(601),
				arulePacketDropRelease(602),
				autoCpeUpgradeStart(605),
				autoCpeUpgradeFail(607),
				autoCpeUpgradeSuccess(609),
				batteryUnderTemper(611),
				batteryTemperUnderToNormal(612),
				batteryCellAbnormal(613),
				batteryCellNormal(614),
				batteryCellTestChargeStarted(615),
				batteryCellTestChargeFinished(616),
				batteryAcPowerFault(617),
				batteryAcPowerOk(618),
				bME1CardNoDetect(620),
				clearBME1CardNoDetect(621),
				bME1CardAFEerror(622),
				clearBME1CardAFEerror(623),
				bME1CardIFEerror(624),
				clearBME1CardIFEerror(625),
				bME1CardFWerror(626),
				clearBME1CardFWerror(627),
				bME1CardPROVerror(628),
				clearBME1CardPROVerror(629),
				bME1CrashDetect(630),
				clearBME1CrashDetect(631),
				bME2CardNoDetect(632),
				clearBME2CardNoDetect(633),
				bME2CardAFEerror(634),
				clearBME2CardAFEerror(635),
				bME2CardIFEerror(636),
				clearBME2CardIFEerror(637),
				bME2CardFWerror(638),
				clearBME2CardFWerror(639),
				bME2CardPROVerror(640),
				clearBME2CardPROVerror(641),
				bME2CrashDetect(642),
				clearBME2CrashDetect(643),
				bME3CardNoDetect(644),
				clearBME3CardNoDetect(645),
				bME3CardAFEerror(646),
				clearBME3CardAFEerror(647),
				bME3CardIFEerror(648),
				clearBME3CardIFEerror(649),
				bME3CardFWerror(650),
				clearBME3CardFWerror(651),
				bME3CardPROVerror(652),
				clearBME3CardPROVerror(653),
				bME3CrashDetect(654),
				clearBME3CrashDetect(655),
				powerFromBattery(656),
				clearPowerFromBattery(657),
				invalidBatteryStatus(658),
				clearInvalidBatteryStatus(659),
				batteryChargeLow(660),
				clearBatteryChargeLow(661),
				batteryNotPresent(662),
				clearBatteryNotPresent(663),
				voltageLow(664),
				clearVoltageLow(665),
				tempOverThreshold(666),
				clearTempOverThreshold(667),
				tempUnderThreshold(668),
				clearTempUnderThreshold(669),
				cpuOverThreshold(670),
				clearCpuOverThreshold(671),
				trafficOverload(672),
				clearTrafficOverload(673),
				gEPONModuleNotDetect(674),
				clearGEPONModuleNotDetect(675),
				gEPONPortOperationDown(676),
				clearGEPONPortOperationDown(677),
				gEPONNoIncomingTraffic(678),
				clearGEPONNoIncomingTraffic(679),
				processCrashDetect(680),
				clearProcessCrashDetect(681),
				memoryLeakDetect(682),
				clearMemoryLeakDetect(683),
				memoryCorrupDetect(684),
				clearMemoryCorrupDetect(685),
				memoryLowDetect(686),
				clearMemoryLowDetect(687),
				dataLineerror(688),
				clearDataLineerror(689),
				addressLineerror(690),
				clearAddressLineerror(691),
				chipsetNotDetcet(692),
				clearChipsetNotDetcet(693),
				pciBuserror(694),
				clearPciBuserror(695),
				securityAdminConnect(696),
				clearSecurityAdminConnect(697),
				oNUPowerDown(698),
				clearONUPowerDown(699),
				oNUNotRegister(700),
				clearONUNotRegister(701),
				oNTOpticPre(702),
				clearONTOpticPre(703),
				switchoverInitiated(800),
				switchoverDone(801),
				boardChangeState(802)
				}
			MAX-ACCESS read-only
			STATUS current
			DESCRIPTION
				" The OID of alarm. 
				 The following alarms is devided by the specific character, ===============.
				 The division basis is that alarms is bounded or released.
				
				        001: portDown: To detect whether physical or logical interface's link status is up or down.
					002: portUp: 
					===============
					003: portRemoved: To detect whether physical interface is installed or not.
					004: portInstalled: 
					===============
					005: powerFail: To detect whether power module's operation status is good or not.
							(Without doubt, more than 1 power module should be equipped.)
					006: powerOK: 
					===============
					007: powerRemoved: To detect whether power module is installed or not, through the PLD access.
							   (Without doubt, more than 1 power module should be equipped.)
					008: powerInstalled: 
					===============
					009: fanFail: To detect whether FAN module's operation status is good or not.
					010: fanOK: 
					===============
					011: fanRemoved: To detect whether FAN module is installed or not, through the PLD access.
					012: fanInstalled: 
					===============
					013: moduleRemoved: To detect whether physical interface module is installed or not, through the S/W I2C
					014: moduleInstalled: 
					===============
					015: systemRestart: Network system is restarted by operator. This is not H/W start but S/W start.
					===============
					016: systemStart: Network system is restarted by operator or system status. This is not S/W start but H/W start.
							  (This alarm isn’t used current)
					===============
					017: broadcastOver: To detect the receipt of broadcast packet.
				  			    (This alarm isn’t used current)
					018: broadcastUnder: 
					===============
					019: cpuOverLoad: To detect whether the configured CPU load threshold is less than current CPU load usage or not.
					020: cpuUnderLoad: 
					===============
					021: memoryOverUsed: To detect whether the configured memory threshold is less than current memory usage or not.
					022: memoryUnderUsed: 
					===============
					023: portOverThreshold: To detect whether the configured physical or logical interface threshold is 
								less than delta value of current interface's InOctects or not.
					024: portUnderThreshold: 
					===============
					025: temperatureHigh: To detect whether the configured system's temperature threshold is 
							      less than current temperature or not.
					026: temperatureLow: 
					===============
					027: mfgdBlocked: To detect whether the specific MAC by MAC flood guard is blocked or not.
					028: mfgdReleased: 
					===============
					029: ipConflict: To detect whether the same IP address on different network node is configured or not.
					030: ipUnconflict: 
					===============
					031: dhcpLeaseShortage: To detect whether IP address that can be assigned to subscriber by DHCP server is 
								sufficient or not.
					032: dhcpLeaseSufficient: 
					===============
					033: dhcpOccuredIllegalEntry: To detect whether a subsceiber is using a static IP address or not.
					034: dhcpRemovedIllegalEntry: 
					===============
					035: rmonAlarmRising: To detect whether rising threshold of a specific MO in RMON alarm sampling is 
							      less than current calculated value by alarm sample type or not. But alarm generation 
							      would be issued by means of event type in RMON event.
					036: rmonAlarmNoRising: 
					===============
					037: rmonAlarmFalling: To detect whether falling threshold of a specific MO in RMON alarm sampling is 
							       less than current calculated value by alarm sample type or not. 
							       But alarm generation would be issued by means of event type in RMON event.
					038: rmonAlarmNoFalling: 
					===============
					039: bpduGuardDisabled: To detect whether edge ports is guarded about superior BPDU or not. 
								In case of insertion edge node with 0 or lower priority than priority of current root bridge node, 
								it will be disarrangement during a short time because of recognition a new inserted node 
								as root bridge. 
								So these edge ports is guarded, and then edge ports is blocked about all superior BPDU. 
								So STP reconfiguration doesn't use this edge ports.
					===============
					040: rootGuardDisabled: To detect whether edge ports is guarded about superior BPDU or not. 
								In case of insertion edge node with 0 or lower priority than priority of current root bridge node, 
								it will be disarrangement during a short time because of recognition a new inserted node 
								as root bridge. 
								So, Root guard prevents a new inserted node from being root bridge as well as 
								receiving a superior BPDU from root bridge. 
								but this node participates in STP topology reconfiguration. 
								If root bridge does not send a superior BPDU, then this node acts usually though STP state change.
					===============
					041: portSecurity: To detect whether interface is configured for security or not. 
							   This can be used to prevent MAC from flooding as well as spoofing. 
							   That is, As a result, this will obstruct an attack as like DoS attack.
					===============
					042: userLogin: 
					043: userLogout: 
					===============
					051: igmpGroupJoined: To detect whether a subscriber is joined a multicast group or not.
					052: igmpGroupLeaved: 
					===============
					053: dhcpIpaddressBound: To detect wether a dynamic IP address is assigned to a subscriber or not.
					054: dhcpIpaddressFree: 
					===============
					055: doorOpened: To detect whether outer door is opeded or not, as external alarm.
					056: doorClosed: 
					===============
					057: powerModeChangedPowerToBattery: To detect whether a system is using AC power or battery. 
									     A system is using AC power usually. 
									     If there is any power problems as like a power failure, 
									     a system is using battery instead of AC power. 
					058: powerModeChangedBatteryToPower: 
					===============
					059: batterylowcapacity: To detect whether current battery capacity is less 
								 capacity threshold according to battery usage or not. 
								 The capacity of AC power is 16 voltage and battery is 20. 
								 Capacity threshold is configured by H/W specification.
								 So operator can't change it.
					060: batterynormalcapacity: 
					===============
					061: batteryhighTemperature: To detect whether current temperature of battery is greater than temperature threshold or not. 
					062: batterynormalTemperature: 
					===============
					063: authenticationFail: To detect whether the connected user is authentic or non-authentic.
					064: authenticationNofail: 
					===============
					065: psuAcHighTemperature: To detect whether current temperature of Power Supply Unit is 
								   greater than temperature threshold or not. 
					066: psuAcNormalTemperature: 
					===============
					067: batteryRemoved: To detect whether battery is equipped at network system or not. 
							     Battery is used as redundancy power service. So operator can decide the installation of battery.
					068: batteryEquipped: 
					===============
					069: batteryLowVoltage: To detect whether battery voltage is less than 12.5 volt or not. 
								12.5 volt value is configured by H/W specification. So operator can't change it.
					070: batteryNormalVoltage: 
					===============
					071: adminAccessLogin: To detect whether a operator connects at this network system or not.
					072: adminAccessLogout: 
					===============
					073: cfgdBlocked: To detect whether it is blocked flood to CPU or not.
					074: cfgdReleased: 
					===============
					075: sfgdBlocked: To detect whether it is blocked flood to system or not.
					076: sfgdReleased: 
					===============
					077: swWatchdogAbnormalState: To detect whether a specific process acts normally or not.
					078: swWatchdogNormalState: 
					===============
					079: swWatchdogDetectError: To detect whether a specific process is detected a error related to itself or cleared.
					080: swWatchdogClearError: 
					===============
					081: ppsControlBlocked: To detect whether it is blocked by pps-control or not.
					082: ppsControlReleased: 
					===============
					083: gotDMITempHighOverAlarm: To detect whether internal temperature exceeds high alarm level or not.
					084: gotDMITempHighFallAlarm: 
					===============
					085: gotDMITempLowOverAlarm: To detect whether internal temperature is below low alarm level or not.
					086: gotDMITempLowFallAlarm: 
					===============
					087: gotDMITempHighOverWarning: To detect whether internal temperature exceeds high warning level or not.
					088: gotDMITempHighFallWarning: 
					===============
					089: gotDMITempLowOverWarning: To detect whether internal temperature is below low warning level or not.
					090: gotDMITempLowFallWarning: 
					===============
					091: gotDMIVolHighOverAlarm: To detect whether internal supply voltage exceeds high alarm level or not.
					092: gotDMIVolHighFallAlarm: 
					===============
					093: gotDMIVolLowOverAlarm: To detect whether internal supply voltage is below low alarm level or not.
					094: gotDMIVolLowFallAlarm: 
					===============
					095: gotDMIVolHighOverWarning: To detect whether internal supply voltage exceeds high warning level or not.
					096: gotDMIVolHighFallWarning: 
					===============
					097: gotDMIVolLowOverWarning: To detect whether internal supply voltage is below low warning level or not.
					098: gotDMIVolLowFallWarning: 
					===============
					099: gotDMITxBiasHighOverAlarm: To detect whether TX Bias current exceeds high alarm level or not.
					100: gotDMITxBiasHighFallAlarm: 
					===============
					101: gotDMITxBiasLowOverAlarm: To detect whether TX Bias current is below low alarm level or not.
					102: gotDMITxBiasLowFallAlarm: 
					===============
					103: gotDMITxBiasHighOverWarning: To detect whether TX Bias current exceeds high warning level or not.
					104: gotDMITxBiasHighFallWarning: 
					===============
					105: gotDMITxBiasLowOverWarning: To detect whether TX Bias current is below low warning level or not.
					106: gotDMITxBiasLowFallWarning: 
					===============
					107: gotDMITxPowerHighOverAlarm: To detect whether TX output power exceeds high alarm level or not.
					108: gotDMITxPowerHighFallAlarm: 
					===============
					109: gotDMITxPowerLowOverAlarm: To detect whether TX output power is below low alarm level or not.
					110: gotDMITxPowerLowFallAlarm: 
					===============
					111: gotDMITxPowerHighOverWarning: To detect whether TX output power exceeds high warning level or not.
					112: gotDMITxPowerHighFallWarning: 
					===============
					113: gotDMITxPowerLowOverWarning: To detect whether TX output power is below low warning level or not.
					114: gotDMITxPowerLowFallWarning: 
					===============
					115: gotDMIRxPowerHighOverAlarm: To detect whether RX output power exceeds high alarm level or not.
					116: gotDMIRxPowerHighFallAlarm: 
					===============
					117: gotDMIRxPowerLowOverAlarm: To detect whether RX output power is below low alarm level or not.
					118: gotDMIRxPowerLowFallAlarm: 
					===============
					119: gotDMIRxPowerHighOverWarning: To detect whether RX output power exceeds high warning level or not.
					120: gotDMIRxPowerHighFallWarning: 
					===============
					121: gotDMIRxPowerLowOverWarning: To detect whether RX output power is below low warning level or not.
					122: gotDMIRxPowerLowFallWarning: 
					===============
					123: nosRemoteUpgradeRequest: 
					124: nosRemoteUpgradeSuccess: 
					125: nosRemoteUpgradeFailAbort: 
					126: nosRemoteUpgradeFailHeaderError: 
					127: nosRemoteUpgradeFailDownloadError: 
					128: nosRemoteUpgradeFailFlashError: 
					129: nosRemoteUpgradeStart: 
				        ===============
				        130: systemDyingGasp
					===============
					201: advaTemperature: To detect whether current chassis temperature is less than chassis temperature threshold or not.
					202: advaTemperatureNo: 
					===============
					203: advaPSUFailure: To detect whether ADVA system's power supply unit has a failure or not.
					204: advaPSUFailureNo: 
					===============
					205: advaFanFailure: To detect whether ADVA system's FAN has a failure or not.
					206: advaFanFailureNo: 
					===============
					207: advaInterfaceReceiveFailure: To detect whether ADVA system's receipt has a failure or not.
					208: advaInterfaceReceiveFailureNo:  
					===============
					209: advaInterfaceOpticalThreshold: To detect whether Adva system's optical receive power level is 
									    less than optical threshold or not.
					210: advaInterfaceOpticalThresholdNo: 
					===============
					211: advaInterfaceTransmitFault: To detect whether ADVA system's transmission has a failure or not.
					212: advaInterfaceTransmitFaultNo: 
					===============
					213: dvaInterfaceMisconfiguration: To detect whether ADVA system's interface is configured rightly or not.
					214: advaInterfaceMisconfigurationNo: 
					===============
					215: advaInterfaceSFPMismatch: To detect whether ADVA system's SFP interface is mismatched or not.
					216: advaInterfaceSFPMismatchNo: 
					===============
					217: advaVoltageLow: To detect whether ADVA system's current voltage is less than voltage threshold or not.
					218: advaVoltageLowNo: 
					===============
					219: advaVoltageHigh: To detect whether ADVA system's current voltage is greater than voltage threshold or not.
					220: advaVoltageHighNo: 
					===============
					301: erpDomainLotp: To detect whether LOTP(Loss of Test Packet) exists a domain of ERP or not. 
							    The Loss of Test Packet defect is defined when a node does not receive 
							    any test packet at any of its ports for a period of 3 times.
					302: erpDomainLotpNo: 
					===============
					303: erpDomainULotp: To detect whether undirectional LOTP(Loss of Test Packet) exists a domain of ERP or not. 
							     The Loss of Test Packet defect is defined when a RM node of one domain does not 
							     receive any test packet at one port for a period of 3 times.
					304: erpDomainULotpNo: 
					===============
					305: erpDomainMultipleRM: To detect whether Multiple RM node is supported or not. 
								  The defect is raised when a RM node receives its own test packets 
								  with an Ack destination address field with a non-zero value.
					306: erpDomainMultipleRMNo: 
					===============
					307: erpDomainRMNodeReacheablity: To detect whether RM reachability is raised or not. 
									  The detection of multiple failures indicates that the ring is segmented and 
								          that the RM Node is unreacheable. 
									  This is only possible at normal ring nodes isolated from the RM node.
					308: erpDomainRMNodeReacheablityNo: 
					===============
					401: eponOnuDeregister: To detect whether ONU is registered into OLT or not. 
								That is, ONU that its operation is service on should be sent registration information to OLT. 
					402: eponOnuRegister: 
					===============
					403: eponOnuRegistrationError: To detect whether ONU is failed registeration process into OLT.
					404: eponOnuNoRegistrationError: 
					===============
					405: eponBadEncryptionKey: To detect wwhether the encryption key is valid or not.
								   A message between ONU and OLT is encrypted using random encryption key. 
								   There is that the encryption key is invalid as transmission failure from time to time.
					406: eponNoBadEncryptionKey: 
					===============
					407: eponLlidMistmatch: To detect whether Llid of message between ONU and OLT is valid or not. 
								On registering, ONU informs unique ID to OLT.
								And then, all communication between ONU and OLT must use the unique ID. 
								The unique ID is called Llid.
					408: eponNoLlidMismatch: 
					===============
					409: eponTooManyRegister: To detect whether the registered ONU per 1 OLT is greater than 32 or not. 
								  That is, ONU can be registered from 1 to the maximum 32 at 1 OLT.
					410: eponNoTooManyRegister: 
					===============
					411: eponDyingGASP: To detect whether a ONU is down from dying gasp or not. 
							    A ONU could be changed to down state as a number of reasons.
							    By the way, ONU that is changed to down as dying gasp would be sent dying gasp signal to OLT and 
							    then ONU's link would be changed to down.
					412: eponNoDyingGASP: 
					===============
					413: eponOnuErrFramePeriod: 
					414: eponOnuNoErrFramePeriod: 
					===============
					415: eponOnuErrFrame: 
					416: eponOnuNoErrFrame: 
					===============
					417: eponOnuErrFrameSecondSummary: 
					418: eponOnuNoErrFrameSecondSummary: 
					===============
					419: eponOnuLastOnuDeregister: To detect whether a deregistered ONU is last ONU or not. 
								       If a deregistered ONU is last ONU, the OLT would be changed to serviceable status. 
					420: eponOnuNoLastOnuDeregister: 
					===============
					421: eponOltCableDown: 
					422: eponOltRecoverCableDown: 
					===============
					501: autoCLIStart: To detect whether the scheduled auto CLI is started or not.
					502: autoCLINoStart: 
					===============
					503: autoCLIComplete: To detect whether the scheduled auto CLI is completed or not. 
					504: autoCLINoComplete: 
					===============
					505: autoCLIRemoveOutputFile: To detect whether the result file of the scheduled auto CLI is removed or not.
								      The reason that the result file is removed is that the configured file size for the result  is
								      less than the stored result file size. 
								      If so, the oldest file would be removed before everything.
					506: autoCLINoRemoveOutputFile: 
					===============
					507: autoResetSystem: To detect whether the system is restarted or not. 
							      The conditions that system is restarted is that ping loss threshold is 
							      less than current ping loss count during the configured interval and 
							      that current free memory size is less than configured free memory size.
					508: autoResetNoSystem: 
					===============
					509: autoResetPingReplyLoss: To detect whether ping reply from the designated network node is received or not.
								     Operator designates any gateway system that can communicate to detect 
								     current network environment. 
								     System sends ICMP packet to the designated gateway system periodically. 
								     If  the system doesn't receive ping reply packet within any interval, 
								     operator recognizes that the system can't communicate any more 
								     because of some problems of the system. 
					510: autoResetNoPingReplyLoss: 
					===============
					511: autoResetMemoryLeakDetect: To detect whether current free memory size is 
									less than the configured free memory size or not. 
									Periodically, free memory size is checked to confirm system availability.
					512: autoResetNoMemoryLeakDetect: 
					===============
					601: arulePacketDropDetect: To detect whether it is dropped some packet by arule or not.
					602: arulePacketDropRelease: 
					===============
					620: bME1CardNoDetect: 
					621: clearBME1CardNoDetect: 
					===============
					622: bME1CardAFEerror: 
					623: clearBME1CardAFEerror: 
					===============
					624: bME1CardIFEerror: 
					625: clearBME1CardIFEerror: 
					===============
					626: bME1CardFWerror: 
					627: clearBME1CardFWerror: 
					===============
					628: bME1CardPROVerror: 
					629: clearBME1CardPROVerror: 
					===============
					630: bME1CrashDetect: 
					631: clearBME1CrashDetect: 
					===============
					632: bME2CardNoDetect: 
					633: clearBME2CardNoDetect: 
					===============
					634: bME2CardAFEerror: 
					635: clearBME2CardAFEerror: 
					===============
					636: bME2CardIFEerror: 
					637: clearBME2CardIFEerror: 
					===============
					638: bME2CardFWerror: 
					639: clearBME2CardFWerror: 
					===============
					640: bME2CardPROVerror: 
					641: clearBME2CardPROVerror: 
					===============
					642: bME2CrashDetect: 
					643: clearBME2CrashDetect: 
					===============
					644: bME3CardNoDetect: 
					645: clearBME3CardNoDetect: 
					===============
					646: bME3CardAFEerror: 
					647: clearBME3CardAFEerror: 
					===============
					648: bME3CardIFEerror: 
					649: clearBME3CardIFEerror: 
					===============
					650: bME3CardFWerror: 
					651: clearBME3CardFWerror: 
					===============
					652: bME3CardPROVerror: 
					653: clearBME3CardPROVerror: 
					===============
					654: bME3CrashDetect: 
					655: clearBME3CrashDetect: 
					===============
					656: powerFromBattery: 
					657: clearPowerFromBattery: 
					===============
					658: invalidBatteryStatus: 
					659: clearInvalidBatteryStatus: 
					===============
					660: batteryChargeLow: 
					661: clearBatteryChargeLow: 
					===============
					662: batteryNotPresent: 
					663: clearBatteryNotPresent: 
					===============
					664: voltageLow: 
					665: clearVoltageLow: 
					===============
					666: tempOverThreshold: 
					667: clearTempOverThreshold: 
					===============
					668: tempUnderThreshold: 
					669: clearTempUnderThreshold: 
					===============
					670: cpuOverThreshold: 
					671: clearCpuOverThreshold: 
					===============
					672: trafficOverload: 
					673: clearTrafficOverload: 
					===============
					674: gEPONModuleNotDetect: 
					675: clearGEPONModuleNotDetect:
					===============
					676: gEPONPortOperationDown: 
					677: clearGEPONPortOperationDown: 
					===============
					678: gEPONNoIncomingTraffic: 
					679: clearGEPONNoIncomingTraffic: 
					===============
					680: processCrashDetect: 
					681: clearProcessCrashDetect: 
					===============
					682: memoryLeakDetect: 
					683: clearMemoryLeakDetect: 
					===============
					684: memoryCorrupDetect: 
					685: clearMemoryCorrupDetect: 
					===============
					686: memoryLowDetect: 
					687: clearMemoryLowDetect: 
					===============
					688: dataLineerror: 
					689: clearDataLineerror: 
					===============
					690: addressLineerror: 
					691: clearAddressLineerror: 
					===============
					692: chipsetNotDetcet: 
					693: clearChipsetNotDetcet: 
					===============
					694: pciBuserror: 
					695: clearPciBuserror: 
					===============
					696: securityAdminConnect: 
					697: clearSecurityAdminConnect: 
					===============
					698: oNUPowerDown: 
					699: clearONUPowerDown: 
					===============
					700: oNUNotRegister: 
					701: clearONUNotRegister: 
					===============
					702: oNTOpticPre: 
					703: clearONTOpticPre: 
					===============
					800: switchoverInitiated: 
					===============
					801: switchoverDone: 
					==============="
			::= { sleAlarmReportEntry 1 }

		
		-- 1.3.6.1.4.1.6296.101.4.3.1.1.2
		sleAlarmReportingSourceType OBJECT-TYPE
			SYNTAX INTEGER
				{
				entPhysicalEntity(1),
				ifIndex(2),
				vccTp(3),
				macAddress(4),
				ipv4(5),
				ipv6(6),
				threshold(7),
				advaSource(8),
				number(9),
				general(10),
				eponSource(11)
				}
			MAX-ACCESS read-only
			STATUS current
			DESCRIPTION
				"The type of Reporting source"
			::= { sleAlarmReportEntry 2 }

		
		-- 1.3.6.1.4.1.6296.101.4.3.1.1.3
		sleAlarmReportingSource OBJECT-TYPE
			SYNTAX OCTET STRING (SIZE (0..255))
			MAX-ACCESS read-only
			STATUS current
			DESCRIPTION
				" The alarm severity of alarm. "
			::= { sleAlarmReportEntry 3 }

		
		-- 1.3.6.1.4.1.6296.101.4.3.1.1.4
		sleAlarmSpecificSeverity OBJECT-TYPE
			SYNTAX INTEGER
				{
				critical(1),
				major(2),
				minor(3),
				warning(4),
				intermediate(5),
				cleared(6)
				}
			MAX-ACCESS read-only
			STATUS current
			DESCRIPTION
				"The alarm severity. The value cleared indicates the clearing of alarm."
			::= { sleAlarmReportEntry 4 }

		
		-- 1.3.6.1.4.1.6296.101.4.3.1.1.5
		sleAlarmSpecificProblem OBJECT-TYPE
			SYNTAX Unsigned32
			MAX-ACCESS read-only
			STATUS current
			DESCRIPTION
				"Describes the spefic problems e.g. when a shePhysCardFailure is sent here the  termperature alarm is specified"
			::= { sleAlarmReportEntry 5 }

		
		-- 1.3.6.1.4.1.6296.101.4.3.1.1.6
		sleAlarmSpecificProblemText OBJECT-TYPE
			SYNTAX OCTET STRING (SIZE (0..255))
			MAX-ACCESS read-only
			STATUS current
			DESCRIPTION
				"Textual description of specific problem reported by alarming.
				To be discussed: Option is to define an alarm for every problem
				"
			::= { sleAlarmReportEntry 6 }

		
		-- 1.3.6.1.4.1.6296.101.4.3.1.1.7
		sleAlarmTimeAndDate OBJECT-TYPE
			SYNTAX Integer32
			MAX-ACCESS read-only
			STATUS current
			DESCRIPTION
				"The date and time when the alarm appeared or cleared"
			::= { sleAlarmReportEntry 7 }

		
		-- 1.3.6.1.4.1.6296.101.4.3.1.1.8
		sleAlarmSpecificSeqNum OBJECT-TYPE
			SYNTAX Counter32
			MAX-ACCESS read-only
			STATUS current
			DESCRIPTION
				"Sequence number for the alarm synchronization. 
				This value has a number to be used for the next alarm trap."
			::= { sleAlarmReportEntry 8 }

		
		-- 1.3.6.1.4.1.6296.101.4.3.2
		sleAlarmReportNotification OBJECT IDENTIFIER ::= { sleAlarmReport 2 }

		
		-- 1.3.6.1.4.1.6296.101.4.3.2.1
		sleAlarmReportNotified NOTIFICATION-TYPE
			OBJECTS { sleAlarmSpecificCode, sleAlarmTimeAndDate, sleAlarmReportingSource, sleAlarmReportingSourceType, sleAlarmSpecificSeverity, 
				sleAlarmSpecificProblem, sleAlarmSpecificProblemText, sleAlarmSpecificSeqNum }
			STATUS current
			DESCRIPTION 
				"Description."
			::= { sleAlarmReportNotification 1 }

		
		-- 1.3.6.1.4.1.6296.101.4.3.3
		sleAlarmReportControl OBJECT IDENTIFIER ::= { sleAlarmReport 3 }

		
		-- 1.3.6.1.4.1.6296.101.4.3.3.1
		sleAlarmReportControlRequest OBJECT-TYPE
			SYNTAX INTEGER { clearAlarmReport(1) }
			MAX-ACCESS read-write
			STATUS current
			DESCRIPTION
				"Description."
			::= { sleAlarmReportControl 1 }

		
		-- 1.3.6.1.4.1.6296.101.4.3.3.2
		sleAlarmReportControlStatus OBJECT-TYPE
			SYNTAX SleControlStatusType
			MAX-ACCESS read-only
			STATUS current
			DESCRIPTION
				"Description."
			::= { sleAlarmReportControl 2 }

		
		-- 1.3.6.1.4.1.6296.101.4.3.3.3
		sleAlarmReportControlTimer OBJECT-TYPE
			SYNTAX Gauge32
			MAX-ACCESS read-write
			STATUS current
			DESCRIPTION
				"Description."
			::= { sleAlarmReportControl 3 }

		
		-- 1.3.6.1.4.1.6296.101.4.3.3.4
		sleAlarmReportControlTimeStamp OBJECT-TYPE
			SYNTAX TimeTicks
			MAX-ACCESS read-only
			STATUS current
			DESCRIPTION
				"Description."
			::= { sleAlarmReportControl 4 }

		
		-- 1.3.6.1.4.1.6296.101.4.3.3.5
		sleAlarmReportControlReqResult OBJECT-TYPE
			SYNTAX SleControlRequestResultType
			MAX-ACCESS read-only
			STATUS current
			DESCRIPTION
				"Description."
			::= { sleAlarmReportControl 5 }

		
		-- 1.3.6.1.4.1.6296.101.4.3.4
		sleAlarmReportNotifications OBJECT IDENTIFIER ::= { sleAlarmReport 4 }

		
		-- 1.3.6.1.4.1.6296.101.4.3.4.1
		sleAlarmReportCleared NOTIFICATION-TYPE
			OBJECTS { sleAlarmReportControlRequest, sleAlarmReportControlTimeStamp, sleAlarmReportControlReqResult }
			STATUS current
			DESCRIPTION 
				"Description."
			::= { sleAlarmReportNotifications 1 }

		
		-- 1.3.6.1.4.1.6296.101.4.4
		sleAlarmHistory OBJECT IDENTIFIER ::= { sleFaultMgmt 4 }

		
		-- 1.3.6.1.4.1.6296.101.4.4.1
		sleAlarmHistoryTable OBJECT-TYPE
			SYNTAX SEQUENCE OF SleAlarmHistoryEntry
			MAX-ACCESS not-accessible
			STATUS current
			DESCRIPTION
				" The alarm severity table.
				The alarm severity table associates
				profile index and AlarmID pairs with severities to be
				used for alarm traps.
				(Note that this table does not apply to cleared alarms). "
			::= { sleAlarmHistory 1 }

		
		-- 1.3.6.1.4.1.6296.101.4.4.1.1
		sleAlarmHistoryEntry OBJECT-TYPE
			SYNTAX SleAlarmHistoryEntry
			MAX-ACCESS not-accessible
			STATUS current
			DESCRIPTION
				" Entry of the alarm severity table. "
			INDEX { sleAlarmHistoryIndex }
			::= { sleAlarmHistoryTable 1 }

		
		SleAlarmHistoryEntry ::=
			SEQUENCE { 
				sleAlarmHistoryIndex
					INTEGER,
				sleAlarmHistorySpecific
					INTEGER,
				sleAlarmHistorySeverity
					INTEGER,
				sleAlarmHistoryText
					OCTET STRING,
				sleAlarmHistoryTime
					Integer32,
				sleAlarmHistorySeqNum
					Counter32
			 }

		-- 1.3.6.1.4.1.6296.101.4.4.1.1.1
		sleAlarmHistoryIndex OBJECT-TYPE
			SYNTAX INTEGER (1..65535)
			MAX-ACCESS read-only
			STATUS current
			DESCRIPTION
				" The OID of alarm. "
			::= { sleAlarmHistoryEntry 1 }

		
		-- 1.3.6.1.4.1.6296.101.4.4.1.1.2
		sleAlarmHistorySpecific OBJECT-TYPE
			SYNTAX INTEGER
				{
				portDown(1),
				portUp(2),
				portRemoved(3),
				portInstalled(4),
				powerFail(5),
				powerOK(6),
				powerRemoved(7),
				powerInstalled(8),
				fanFail(9),
				fanOK(10),
				fanRemoved(11),
				fanInstalled(12),
				moduleRemoved(13),
				moduleInstalled(14),
				systemRestart(15),
				systemStart(16),
				broadcastOver(17),
				broadcastUnder(18),
				cpuOverLoad(19),
				cpuUnderLoad(20),
				memoryOverUsed(21),
				memoryUnderUsed(22),
				portOverThreshold(23),
				portUnderThreshold(24),
				temperatureHigh(25),
				temperatureLow(26),
				mfgdBlocked(27),
				mfgdReleased(28),
				ipConflict(29),
				ipUnconflict(30),
				dhcpLeaseShortage(31),
				dhcpLeaseSufficient(32),
				dhcpOccuredIllegalEntry(33),
				dhcpRemovedIllegalEntry(34),
				rmonAlarmRising(35),
				rmonAlarmNoRising(36),
				rmonAlarmFalling(37),
				rmonAlarmNoFalling(38),
				bpduGuardDisabled(39),
				rootGuardDisabled(40),
				portSecurity(41),
				userLogin(42),
				userLogout(43),
				igmpGroupJoined(51),
				igmpGroupLeaved(52),
				dhcpIpaddressBound(53),
				dhcpIpaddressFree(54),
				doorOpened(55),
				doorClosed(56),
				powerModeChangedPowerToBattery(57),
				powerModeChangedBatteryToPower(58),
				batterylowcapacity(59),
				batterynormalcapacity(60),
				batteryhighTemperature(61),
				batterynormalTemperature(62),
				authenticationFail(63),
				authenticationNoFail(64),
				psuAcHighTemperature(65),
				psuAcNormalTemperature(66),
				batteryRemoved(67),
				batteryEquipped(68),
				batteryLowVoltage(69),
				batteryNormalVoltage(70),
				adminAccessLogin(71),
				adminAccessLogout(72),
				cfgdBlocked(73),
				cfgdReleased(74),
				sfgdBlocked(75),
				sfgdReleased(76),
				swWatchdogAbnormalState(77),
				swWatchdogNormalState(78),
				swWatchdogDetectError(79),
				swWatchdogClearError(80),
				ppsControlBlocked(81),
				ppsControlReleased(82),
				gotDMITempHighOverAlarm(83),
				gotDMITempHighFallAlarm(84),
				gotDMITempLowOverAlarm(85),
				gotDMITempLowFallAlarm(86),
				gotDMITempHighOverWarning(87),
				gotDMITempHighFallWarning(88),
				gotDMITempLowOverWarning(89),
				gotDMITempLowFallWarning(90),
				gotDMIVolHighOverAlarm(91),
				gotDMIVolHighFallAlarm(92),
				gotDMIVolLowOverAlarm(93),
				gotDMIVolLowFallAlarm(94),
				gotDMIVolHighOverWarning(95),
				gotDMIVolHighFallWarning(96),
				gotDMIVolLowOverWarning(97),
				gotDMIVolLowFallWarning(98),
				gotDMITxBiasHighOverAlarm(99),
				gotDMITxBiasHighFallAlarm(100),
				gotDMITxBiasLowOverAlarm(101),
				gotDMITxBiasLowFallAlarm(102),
				gotDMITxBiasHighOverWarning(103),
				gotDMITxBiasHighFallWarning(104),
				gotDMITxBiasLowOverWarning(105),
				gotDMITxBiasLowFallWarning(106),
				gotDMITxPowerHighOverAlarm(107),
				gotDMITxPowerHighFallAlarm(108),
				gotDMITxPowerLowOverAlarm(109),
				gotDMITxPowerLowFallAlarm(110),
				gotDMITxPowerHighOverWarning(111),
				gotDMITxPowerHighFallWarning(112),
				gotDMITxPowerLowOverWarning(113),
				gotDMITxPowerLowFallWarning(114),
				gotDMIRxPowerHighOverAlarm(115),
				gotDMIRxPowerHighFallAlarm(116),
				gotDMIRxPowerLowOverAlarm(117),
				gotDMIRxPowerLowFallAlarm(118),
				gotDMIRxPowerHighOverWarning(119),
				gotDMIRxPowerHighFallWarning(120),
				gotDMIRxPowerLowOverWarning(121),
				gotDMIRxPowerLowFallWarning(122),
				nosRemoteUpgradeRequest(123),
				nosRemoteUpgradeSuccess(124),
				nosRemoteUpgradeFailAbort(125),
				nosRemoteUpgradeFailHeaderError(126),
				nosRemoteUpgradeFailDownloadError(127),
				nosRemoteUpgradeFailFlashError(128),
				nosRemoteUpgradeStart(129),
				systemDyingGasp(130),
				remoteOamDyingGasp(131),
				remoteOamDyingGaspRestoration(132),
				swWatchdogInetAbnormalState(150),
				swWatchdogInetNormalState(151),
				swWatchdogInetDetectError(152),
				swWatchdogInetClearError(153),
				swWatchdogPonAbnormalState(154),
				swWatchdogPonNormalState(155),
				swWatchdogPonDetectError(156),
				swWatchdogPonClearError(157),
				advaTemperature(201),
				advaTemperatureNo(202),
				advaPSUFailure(203),
				advaPSUFailureNo(204),
				advaFanFailure(205),
				advaFanFailureNo(206),
				advaInterfaceReceiveFailure(207),
				advaInterfaceReceiveFailureNo(208),
				advaInterfaceOpticalThreshold(209),
				advaInterfaceOpticalThresholdNo(210),
				advaInterfaceTransmitFault(211),
				advaInterfaceTransmitFaultNo(212),
				advaInterfaceMisconfiguration(213),
				advaInterfaceMisconfigurationNo(214),
				advaInterfaceSFPMismatch(215),
				advaInterfaceSFPMismatchNo(216),
				advaVoltageLow(217),
				advaVoltageLowNo(218),
				advaVoltageHigh(219),
				advaVoltageHighNo(220),
				erpDomainLotp(301),
				erpDomainLotpNo(302),
				erpDomainULotp(303),
				erpDomainULotpNo(304),
				erpDomainMultipleRM(305),
				erpDomainMultipleRMNo(306),
				erpDomainRMNodeReacheablity(307),
				erpDomainRMNodeReacheablityNo(308),
				eponOnuDeregister(401),
				eponOnuRegister(402),
				eponOnuRegistrationError(403),
				eponOnuNoRegistrationError(404),
				eponBadEncryptionKey(405),
				eponNoBadEncryptionKey(406),
				eponLlidMistmatch(407),
				eponNoLlidMismatch(408),
				eponTooManyRegister(409),
				eponNoTooManyRegister(410),
				eponDyingGASP(411),
				eponNoDyingGASP(412),
				eponOnuErrFramePeriod(413),
				eponOnuNoErrFramePeriod(414),
				eponOnuErrFrame(415),
				eponOnuNoErrFrame(416),
				eponOnuErrFrameSecondSummary(417),
				eponOnuNoErrFrameSecondSummary(418),
				eponOnuLastOnuDeregister(419),
				eponOnuNoLastOnuDeregister(420),
				eponOltCableDown(421),
				eponOltRecoverCableDown(422),
				autoCLIStart(501),
				autoCLINoStart(502),
				autoCLIComplete(503),
				autoCLINoComplete(504),
				autoCLIRemoveOutputFile(505),
				autoCLINoRemoveOutputFile(506),
				autoResetSystem(507),
				autoResetNoSystem(508),
				autoResetPingReplyLoss(509),
				autoResetNoPingReplyLoss(510),
				autoResetMemoryLeakDetect(511),
				autoResetNoMemoryLeakDetect(512),
				arulePacketDropDetect(601),
				arulePacketDropRelease(602),
				autoCpeUpgradeStart(605),
				autoCpeUpgradeFail(607),
				autoCpeUpgradeSuccess(609),
				batteryUnderTemper(611),
				batteryTemperUnderToNormal(612),
				batteryCellAbnormal(613),
				batteryCellNormal(614),
				batteryCellTestChargeStarted(615),
				batteryCellTestChargeFinished(616),
				batteryAcPowerFault(617),
				batteryAcPowerOk(618),
				bME1CardNoDetect(620),
				clearBME1CardNoDetect(621),
				bME1CardAFEerror(622),
				clearBME1CardAFEerror(623),
				bME1CardIFEerror(624),
				clearBME1CardIFEerror(625),
				bME1CardFWerror(626),
				clearBME1CardFWerror(627),
				bME1CardPROVerror(628),
				clearBME1CardPROVerror(629),
				bME1CrashDetect(630),
				clearBME1CrashDetect(631),
				bME2CardNoDetect(632),
				clearBME2CardNoDetect(633),
				bME2CardAFEerror(634),
				clearBME2CardAFEerror(635),
				bME2CardIFEerror(636),
				clearBME2CardIFEerror(637),
				bME2CardFWerror(638),
				clearBME2CardFWerror(639),
				bME2CardPROVerror(640),
				clearBME2CardPROVerror(641),
				bME2CrashDetect(642),
				clearBME2CrashDetect(643),
				bME3CardNoDetect(644),
				clearBME3CardNoDetect(645),
				bME3CardAFEerror(646),
				clearBME3CardAFEerror(647),
				bME3CardIFEerror(648),
				clearBME3CardIFEerror(649),
				bME3CardFWerror(650),
				clearBME3CardFWerror(651),
				bME3CardPROVerror(652),
				clearBME3CardPROVerror(653),
				bME3CrashDetect(654),
				clearBME3CrashDetect(655),
				powerFromBattery(656),
				clearPowerFromBattery(657),
				invalidBatteryStatus(658),
				clearInvalidBatteryStatus(659),
				batteryChargeLow(660),
				clearBatteryChargeLow(661),
				batteryNotPresent(662),
				clearBatteryNotPresent(663),
				voltageLow(664),
				clearVoltageLow(665),
				tempOverThreshold(666),
				clearTempOverThreshold(667),
				tempUnderThreshold(668),
				clearTempUnderThreshold(669),
				cpuOverThreshold(670),
				clearCpuOverThreshold(671),
				trafficOverload(672),
				clearTrafficOverload(673),
				gEPONModuleNotDetect(674),
				clearGEPONModuleNotDetect(675),
				gEPONPortOperationDown(676),
				clearGEPONPortOperationDown(677),
				gEPONNoIncomingTraffic(678),
				clearGEPONNoIncomingTraffic(679),
				processCrashDetect(680),
				clearProcessCrashDetect(681),
				memoryLeakDetect(682),
				clearMemoryLeakDetect(683),
				memoryCorrupDetect(684),
				clearMemoryCorrupDetect(685),
				memoryLowDetect(686),
				clearMemoryLowDetect(687),
				dataLineerror(688),
				clearDataLineerror(689),
				addressLineerror(690),
				clearAddressLineerror(691),
				chipsetNotDetcet(692),
				clearChipsetNotDetcet(693),
				pciBuserror(694),
				clearPciBuserror(695),
				securityAdminConnect(696),
				clearSecurityAdminConnect(697),
				oNUPowerDown(698),
				clearONUPowerDown(699),
				oNUNotRegister(700),
				clearONUNotRegister(701),
				oNTOpticPre(702),
				clearONTOpticPre(703),
				switchoverInitiated(800),
				switchoverDone(801)
				}
			MAX-ACCESS read-only
			STATUS current
			DESCRIPTION
				" The OID of alarm. 
				 The following alarms is devided by the specific character, ===============.
				 The division basis is that alarms is bounded or released.
				
				        001: portDown: To detect whether physical or logical interface's link status is up or down.
					002: portUp: 
					===============
					003: portRemoved: To detect whether physical interface is installed or not.
					004: portInstalled: 
					===============
					005: powerFail: To detect whether power module's operation status is good or not.
							(Without doubt, more than 1 power module should be equipped.)
					006: powerOK: 
					===============
					007: powerRemoved: To detect whether power module is installed or not, through the PLD access.
							   (Without doubt, more than 1 power module should be equipped.)
					008: powerInstalled: 
					===============
					009: fanFail: To detect whether FAN module's operation status is good or not.
					010: fanOK: 
					===============
					011: fanRemoved: To detect whether FAN module is installed or not, through the PLD access.
					012: fanInstalled: 
					===============
					013: moduleRemoved: To detect whether physical interface module is installed or not, through the S/W I2C
					014: moduleInstalled: 
					===============
					015: systemRestart: Network system is restarted by operator. This is not H/W start but S/W start.
					===============
					016: systemStart: Network system is restarted by operator or system status. This is not S/W start but H/W start.
							  (This alarm isn’t used current)
					===============
					017: broadcastOver: To detect the receipt of broadcast packet.
				  			    (This alarm isn’t used current)
					018: broadcastUnder: 
					===============
					019: cpuOverLoad: To detect whether the configured CPU load threshold is less than current CPU load usage or not.
					020: cpuUnderLoad: 
					===============
					021: memoryOverUsed: To detect whether the configured memory threshold is less than current memory usage or not.
					022: memoryUnderUsed: 
					===============
					023: portOverThreshold: To detect whether the configured physical or logical interface threshold is 
								less than delta value of current interface's InOctects or not.
					024: portUnderThreshold: 
					===============
					025: temperatureHigh: To detect whether the configured system's temperature threshold is 
							      less than current temperature or not.
					026: temperatureLow: 
					===============
					027: mfgdBlocked: To detect whether the specific MAC by MAC flood guard is blocked or not.
					028: mfgdReleased: 
					===============
					029: ipConflict: To detect whether the same IP address on different network node is configured or not.
					030: ipUnconflict: 
					===============
					031: dhcpLeaseShortage: To detect whether IP address that can be assigned to subscriber by DHCP server is 
								sufficient or not.
					032: dhcpLeaseSufficient: 
					===============
					033: dhcpOccuredIllegalEntry: To detect whether a subsceiber is using a static IP address or not.
					034: dhcpRemovedIllegalEntry: 
					===============
					035: rmonAlarmRising: To detect whether rising threshold of a specific MO in RMON alarm sampling is 
							      less than current calculated value by alarm sample type or not. But alarm generation 
							      would be issued by means of event type in RMON event.
					036: rmonAlarmNoRising: 
					===============
					037: rmonAlarmFalling: To detect whether falling threshold of a specific MO in RMON alarm sampling is 
							       less than current calculated value by alarm sample type or not. 
							       But alarm generation would be issued by means of event type in RMON event.
					038: rmonAlarmNoFalling: 
					===============
					039: bpduGuardDisabled: To detect whether edge ports is guarded about superior BPDU or not. 
								In case of insertion edge node with 0 or lower priority than priority of current root bridge node, 
								it will be disarrangement during a short time because of recognition a new inserted node 
								as root bridge. 
								So these edge ports is guarded, and then edge ports is blocked about all superior BPDU. 
								So STP reconfiguration doesn't use this edge ports.
					===============
					040: rootGuardDisabled: To detect whether edge ports is guarded about superior BPDU or not. 
								In case of insertion edge node with 0 or lower priority than priority of current root bridge node, 
								it will be disarrangement during a short time because of recognition a new inserted node 
								as root bridge. 
								So, Root guard prevents a new inserted node from being root bridge as well as 
								receiving a superior BPDU from root bridge. 
								but this node participates in STP topology reconfiguration. 
								If root bridge does not send a superior BPDU, then this node acts usually though STP state change.
					===============
					041: portSecurity: To detect whether interface is configured for security or not. 
							   This can be used to prevent MAC from flooding as well as spoofing. 
							   That is, As a result, this will obstruct an attack as like DoS attack.
					===============
					042: userLogin: 
					043: userLogout: 
					===============
					051: igmpGroupJoined: To detect whether a subscriber is joined a multicast group or not.
					052: igmpGroupLeaved: 
					===============
					053: dhcpIpaddressBound: To detect wether a dynamic IP address is assigned to a subscriber or not.
					054: dhcpIpaddressFree: 
					===============
					055: doorOpened: To detect whether outer door is opeded or not, as external alarm.
					056: doorClosed: 
					===============
					057: powerModeChangedPowerToBattery: To detect whether a system is using AC power or battery. 
									     A system is using AC power usually. 
									     If there is any power problems as like a power failure, 
									     a system is using battery instead of AC power. 
					058: powerModeChangedBatteryToPower: 
					===============
					059: batterylowcapacity: To detect whether current battery capacity is less 
								 capacity threshold according to battery usage or not. 
								 The capacity of AC power is 16 voltage and battery is 20. 
								 Capacity threshold is configured by H/W specification.
								 So operator can't change it.
					060: batterynormalcapacity: 
					===============
					061: batteryhighTemperature: To detect whether current temperature of battery is greater than temperature threshold or not. 
					062: batterynormalTemperature: 
					===============
					063: authenticationFail: To detect whether the connected user is authentic or non-authentic.
					064: authenticationNofail: 
					===============
					065: psuAcHighTemperature: To detect whether current temperature of Power Supply Unit is 
								   greater than temperature threshold or not. 
					066: psuAcNormalTemperature: 
					===============
					067: batteryRemoved: To detect whether battery is equipped at network system or not. 
							     Battery is used as redundancy power service. So operator can decide the installation of battery.
					068: batteryEquipped: 
					===============
					069: batteryLowVoltage: To detect whether battery voltage is less than 12.5 volt or not. 
								12.5 volt value is configured by H/W specification. So operator can't change it.
					070: batteryNormalVoltage: 
					===============
					071: adminAccessLogin: To detect whether a operator connects at this network system or not.
					072: adminAccessLogout: 
					===============
					073: cfgdBlocked: To detect whether it is blocked flood to CPU or not.
					074: cfgdReleased: 
					===============
					075: sfgdBlocked: To detect whether it is blocked flood to system or not.
					076: sfgdReleased: 
					===============
					077: swWatchdogAbnormalState: To detect whether a specific process acts normally or not.
					078: swWatchdogNormalState: 
					===============
					079: swWatchdogDetectError: To detect whether a specific process is detected a error related to itself or cleared.
					080: swWatchdogClearError: 
					===============
					081: ppsControlBlocked: To detect whether it is blocked by pps-control or not.
					082: ppsControlReleased: 
					===============
					083: gotDMITempHighOverAlarm: To detect whether internal temperature exceeds high alarm level or not.
					084: gotDMITempHighFallAlarm: 
					===============
					085: gotDMITempLowOverAlarm: To detect whether internal temperature is below low alarm level or not.
					086: gotDMITempLowFallAlarm: 
					===============
					087: gotDMITempHighOverWarning: To detect whether internal temperature exceeds high warning level or not.
					088: gotDMITempHighFallWarning: 
					===============
					089: gotDMITempLowOverWarning: To detect whether internal temperature is below low warning level or not.
					090: gotDMITempLowFallWarning: 
					===============
					091: gotDMIVolHighOverAlarm: To detect whether internal supply voltage exceeds high alarm level or not.
					092: gotDMIVolHighFallAlarm: 
					===============
					093: gotDMIVolLowOverAlarm: To detect whether internal supply voltage is below low alarm level or not.
					094: gotDMIVolLowFallAlarm: 
					===============
					095: gotDMIVolHighOverWarning: To detect whether internal supply voltage exceeds high warning level or not.
					096: gotDMIVolHighFallWarning: 
					===============
					097: gotDMIVolLowOverWarning: To detect whether internal supply voltage is below low warning level or not.
					098: gotDMIVolLowFallWarning: 
					===============
					099: gotDMITxBiasHighOverAlarm: To detect whether TX Bias current exceeds high alarm level or not.
					100: gotDMITxBiasHighFallAlarm: 
					===============
					101: gotDMITxBiasLowOverAlarm: To detect whether TX Bias current is below low alarm level or not.
					102: gotDMITxBiasLowFallAlarm: 
					===============
					103: gotDMITxBiasHighOverWarning: To detect whether TX Bias current exceeds high warning level or not.
					104: gotDMITxBiasHighFallWarning: 
					===============
					105: gotDMITxBiasLowOverWarning: To detect whether TX Bias current is below low warning level or not.
					106: gotDMITxBiasLowFallWarning: 
					===============
					107: gotDMITxPowerHighOverAlarm: To detect whether TX output power exceeds high alarm level or not.
					108: gotDMITxPowerHighFallAlarm: 
					===============
					109: gotDMITxPowerLowOverAlarm: To detect whether TX output power is below low alarm level or not.
					110: gotDMITxPowerLowFallAlarm: 
					===============
					111: gotDMITxPowerHighOverWarning: To detect whether TX output power exceeds high warning level or not.
					112: gotDMITxPowerHighFallWarning: 
					===============
					113: gotDMITxPowerLowOverWarning: To detect whether TX output power is below low warning level or not.
					114: gotDMITxPowerLowFallWarning: 
					===============
					115: gotDMIRxPowerHighOverAlarm: To detect whether RX output power exceeds high alarm level or not.
					116: gotDMIRxPowerHighFallAlarm: 
					===============
					117: gotDMIRxPowerLowOverAlarm: To detect whether RX output power is below low alarm level or not.
					118: gotDMIRxPowerLowFallAlarm: 
					===============
					119: gotDMIRxPowerHighOverWarning: To detect whether RX output power exceeds high warning level or not.
					120: gotDMIRxPowerHighFallWarning: 
					===============
					121: gotDMIRxPowerLowOverWarning: To detect whether RX output power is below low warning level or not.
					122: gotDMIRxPowerLowFallWarning: 
					===============
					123: nosRemoteUpgradeRequest: 
					124: nosRemoteUpgradeSuccess: 
					125: nosRemoteUpgradeFailAbort: 
					126: nosRemoteUpgradeFailHeaderError: 
					127: nosRemoteUpgradeFailDownloadError: 
					128: nosRemoteUpgradeFailFlashError: 
					129: nosRemoteUpgradeStart: 
					===============
				        130: systemDyingGasp
				        ===============
					201: advaTemperature: To detect whether current chassis temperature is less than chassis temperature threshold or not.
					202: advaTemperatureNo: 
					===============
					203: advaPSUFailure: To detect whether ADVA system's power supply unit has a failure or not.
					204: advaPSUFailureNo: 
					===============
					205: advaFanFailure: To detect whether ADVA system's FAN has a failure or not.
					206: advaFanFailureNo: 
					===============
					207: advaInterfaceReceiveFailure: To detect whether ADVA system's receipt has a failure or not.
					208: advaInterfaceReceiveFailureNo:  
					===============
					209: advaInterfaceOpticalThreshold: To detect whether Adva system's optical receive power level is 
									    less than optical threshold or not.
					210: advaInterfaceOpticalThresholdNo: 
					===============
					211: advaInterfaceTransmitFault: To detect whether ADVA system's transmission has a failure or not.
					212: advaInterfaceTransmitFaultNo: 
					===============
					213: dvaInterfaceMisconfiguration: To detect whether ADVA system's interface is configured rightly or not.
					214: advaInterfaceMisconfigurationNo: 
					===============
					215: advaInterfaceSFPMismatch: To detect whether ADVA system's SFP interface is mismatched or not.
					216: advaInterfaceSFPMismatchNo: 
					===============
					217: advaVoltageLow: To detect whether ADVA system's current voltage is less than voltage threshold or not.
					218: advaVoltageLowNo: 
					===============
					219: advaVoltageHigh: To detect whether ADVA system's current voltage is greater than voltage threshold or not.
					220: advaVoltageHighNo: 
					===============
					301: erpDomainLotp: To detect whether LOTP(Loss of Test Packet) exists a domain of ERP or not. 
							    The Loss of Test Packet defect is defined when a node does not receive 
							    any test packet at any of its ports for a period of 3 times.
					302: erpDomainLotpNo: 
					===============
					303: erpDomainULotp: To detect whether undirectional LOTP(Loss of Test Packet) exists a domain of ERP or not. 
							     The Loss of Test Packet defect is defined when a RM node of one domain does not 
							     receive any test packet at one port for a period of 3 times.
					304: erpDomainULotpNo: 
					===============
					305: erpDomainMultipleRM: To detect whether Multiple RM node is supported or not. 
								  The defect is raised when a RM node receives its own test packets 
								  with an Ack destination address field with a non-zero value.
					306: erpDomainMultipleRMNo: 
					===============
					307: erpDomainRMNodeReacheablity: To detect whether RM reachability is raised or not. 
									  The detection of multiple failures indicates that the ring is segmented and 
								          that the RM Node is unreacheable. 
									  This is only possible at normal ring nodes isolated from the RM node.
					308: erpDomainRMNodeReacheablityNo: 
					===============
					401: eponOnuDeregister: To detect whether ONU is registered into OLT or not. 
								That is, ONU that its operation is service on should be sent registration information to OLT. 
					402: eponOnuRegister: 
					===============
					403: eponOnuRegistrationError: To detect whether ONU is failed registeration process into OLT.
					404: eponOnuNoRegistrationError: 
					===============
					405: eponBadEncryptionKey: To detect wwhether the encryption key is valid or not.
								   A message between ONU and OLT is encrypted using random encryption key. 
								   There is that the encryption key is invalid as transmission failure from time to time.
					406: eponNoBadEncryptionKey: 
					===============
					407: eponLlidMistmatch: To detect whether Llid of message between ONU and OLT is valid or not. 
								On registering, ONU informs unique ID to OLT.
								And then, all communication between ONU and OLT must use the unique ID. 
								The unique ID is called Llid.
					408: eponNoLlidMismatch: 
					===============
					409: eponTooManyRegister: To detect whether the registered ONU per 1 OLT is greater than 32 or not. 
								  That is, ONU can be registered from 1 to the maximum 32 at 1 OLT.
					410: eponNoTooManyRegister: 
					===============
					411: eponDyingGASP: To detect whether a ONU is down from dying gasp or not. 
							    A ONU could be changed to down state as a number of reasons.
							    By the way, ONU that is changed to down as dying gasp would be sent dying gasp signal to OLT and 
							    then ONU's link would be changed to down.
					412: eponNoDyingGASP: 
					===============
					413: eponOnuErrFramePeriod: 
					414: eponOnuNoErrFramePeriod: 
					===============
					415: eponOnuErrFrame: 
					416: eponOnuNoErrFrame: 
					===============
					417: eponOnuErrFrameSecondSummary: 
					418: eponOnuNoErrFrameSecondSummary: 
					===============
					419: eponOnuLastOnuDeregister: To detect whether a deregistered ONU is last ONU or not. 
								       If a deregistered ONU is last ONU, the OLT would be changed to serviceable status. 
					420: eponOnuNoLastOnuDeregister: 
					===============
					421: eponOltCableDown: 
					422: eponOltRecoverCableDown: 
					===============
					501: autoCLIStart: To detect whether the scheduled auto CLI is started or not.
					502: autoCLINoStart: 
					===============
					503: autoCLIComplete: To detect whether the scheduled auto CLI is completed or not. 
					504: autoCLINoComplete: 
					===============
					505: autoCLIRemoveOutputFile: To detect whether the result file of the scheduled auto CLI is removed or not.
								      The reason that the result file is removed is that the configured file size for the result  is
								      less than the stored result file size. 
								      If so, the oldest file would be removed before everything.
					506: autoCLINoRemoveOutputFile: 
					===============
					507: autoResetSystem: To detect whether the system is restarted or not. 
							      The conditions that system is restarted is that ping loss threshold is 
							      less than current ping loss count during the configured interval and 
							      that current free memory size is less than configured free memory size.
					508: autoResetNoSystem: 
					===============
					509: autoResetPingReplyLoss: To detect whether ping reply from the designated network node is received or not.
								     Operator designates any gateway system that can communicate to detect 
								     current network environment. 
								     System sends ICMP packet to the designated gateway system periodically. 
								     If  the system doesn't receive ping reply packet within any interval, 
								     operator recognizes that the system can't communicate any more 
								     because of some problems of the system. 
					510: autoResetNoPingReplyLoss: 
					===============
					511: autoResetMemoryLeakDetect: To detect whether current free memory size is 
									less than the configured free memory size or not. 
									Periodically, free memory size is checked to confirm system availability.
					512: autoResetNoMemoryLeakDetect: 
					===============
					601: arulePacketDropDetect: To detect whether it is dropped some packet by arule or not.
					602: arulePacketDropRelease: 
					===============
					620: bME1CardNoDetect: 
					621: clearBME1CardNoDetect: 
					===============
					622: bME1CardAFEerror: 
					623: clearBME1CardAFEerror: 
					===============
					624: bME1CardIFEerror: 
					625: clearBME1CardIFEerror: 
					===============
					626: bME1CardFWerror: 
					627: clearBME1CardFWerror: 
					===============
					628: bME1CardPROVerror: 
					629: clearBME1CardPROVerror: 
					===============
					630: bME1CrashDetect: 
					631: clearBME1CrashDetect: 
					===============
					632: bME2CardNoDetect: 
					633: clearBME2CardNoDetect: 
					===============
					634: bME2CardAFEerror: 
					635: clearBME2CardAFEerror: 
					===============
					636: bME2CardIFEerror: 
					637: clearBME2CardIFEerror: 
					===============
					638: bME2CardFWerror: 
					639: clearBME2CardFWerror: 
					===============
					640: bME2CardPROVerror: 
					641: clearBME2CardPROVerror: 
					===============
					642: bME2CrashDetect: 
					643: clearBME2CrashDetect: 
					===============
					644: bME3CardNoDetect: 
					645: clearBME3CardNoDetect: 
					===============
					646: bME3CardAFEerror: 
					647: clearBME3CardAFEerror: 
					===============
					648: bME3CardIFEerror: 
					649: clearBME3CardIFEerror: 
					===============
					650: bME3CardFWerror: 
					651: clearBME3CardFWerror: 
					===============
					652: bME3CardPROVerror: 
					653: clearBME3CardPROVerror: 
					===============
					654: bME3CrashDetect: 
					655: clearBME3CrashDetect: 
					===============
					656: powerFromBattery: 
					657: clearPowerFromBattery: 
					===============
					658: invalidBatteryStatus: 
					659: clearInvalidBatteryStatus: 
					===============
					660: batteryChargeLow: 
					661: clearBatteryChargeLow: 
					===============
					662: batteryNotPresent: 
					663: clearBatteryNotPresent: 
					===============
					664: voltageLow: 
					665: clearVoltageLow: 
					===============
					666: tempOverThreshold: 
					667: clearTempOverThreshold: 
					===============
					668: tempUnderThreshold: 
					669: clearTempUnderThreshold: 
					===============
					670: cpuOverThreshold: 
					671: clearCpuOverThreshold: 
					===============
					672: trafficOverload: 
					673: clearTrafficOverload: 
					===============
					674: gEPONModuleNotDetect: 
					675: clearGEPONModuleNotDetect:
					===============
					676: gEPONPortOperationDown: 
					677: clearGEPONPortOperationDown: 
					===============
					678: gEPONNoIncomingTraffic: 
					679: clearGEPONNoIncomingTraffic: 
					===============
					680: processCrashDetect: 
					681: clearProcessCrashDetect: 
					===============
					682: memoryLeakDetect: 
					683: clearMemoryLeakDetect: 
					===============
					684: memoryCorrupDetect: 
					685: clearMemoryCorrupDetect: 
					===============
					686: memoryLowDetect: 
					687: clearMemoryLowDetect: 
					===============
					688: dataLineerror: 
					689: clearDataLineerror: 
					===============
					690: addressLineerror: 
					691: clearAddressLineerror: 
					===============
					692: chipsetNotDetcet: 
					693: clearChipsetNotDetcet: 
					===============
					694: pciBuserror: 
					695: clearPciBuserror: 
					===============
					696: securityAdminConnect: 
					697: clearSecurityAdminConnect: 
					===============
					698: oNUPowerDown: 
					699: clearONUPowerDown: 
					===============
					700: oNUNotRegister: 
					701: clearONUNotRegister: 
					===============
					702: oNTOpticPre: 
					703: clearONTOpticPre: 
					===============
					800: switchoverInitiated: 
					===============
					801: switchoverDone: 
					==============="
			::= { sleAlarmHistoryEntry 2 }

		
		-- 1.3.6.1.4.1.6296.101.4.4.1.1.3
		sleAlarmHistorySeverity OBJECT-TYPE
			SYNTAX INTEGER
				{
				critical(1),
				major(2),
				minor(3),
				warning(4),
				intermediate(5)
				}
			MAX-ACCESS read-only
			STATUS current
			DESCRIPTION
				" The severity of alarm. "
			::= { sleAlarmHistoryEntry 3 }

		
		-- 1.3.6.1.4.1.6296.101.4.4.1.1.4
		sleAlarmHistoryText OBJECT-TYPE
			SYNTAX OCTET STRING (SIZE (0..255))
			MAX-ACCESS read-only
			STATUS current
			DESCRIPTION
				"Textual description of specific problem reported by alarming.
				To be discussed: Option is to define an alarm for every problem
				"
			::= { sleAlarmHistoryEntry 4 }

		
		-- 1.3.6.1.4.1.6296.101.4.4.1.1.5
		sleAlarmHistoryTime OBJECT-TYPE
			SYNTAX Integer32
			MAX-ACCESS read-only
			STATUS current
			DESCRIPTION
				" The severity of alarm. "
			::= { sleAlarmHistoryEntry 5 }

		
		-- 1.3.6.1.4.1.6296.101.4.4.1.1.6
		sleAlarmHistorySeqNum OBJECT-TYPE
			SYNTAX Counter32
			MAX-ACCESS read-only
			STATUS current
			DESCRIPTION
				"Sequence number for the alarm synchronization. 
				This value has a number to be used for the next alarm trap."
			::= { sleAlarmHistoryEntry 6 }

		
		-- 1.3.6.1.4.1.6296.101.4.4.2
		sleAlarmHistoryControl OBJECT IDENTIFIER ::= { sleAlarmHistory 2 }

		
		-- 1.3.6.1.4.1.6296.101.4.4.2.1
		sleAlarmHistoryControlRequest OBJECT-TYPE
			SYNTAX INTEGER { clearAlarmHistory(1) }
			MAX-ACCESS read-write
			STATUS current
			DESCRIPTION
				" This attribute identifies the control commands.
				updateAlarmList:
				   the NE updates entries of alarms in the sleAlarmListTable
				   after having changed alarm severities of alarms 
				   (due to change profile pointers in
				   managed entities or after modification of alarm severities 
				   in profiles). This command should be applied once after having 
				   finisled modifications of severties.
				modifyAlarmSeverity: 
				   modifies the severity of an alarm in specific profile.
				createAlarmSeverityProfile: 
				   creates a new profile with default severities.
				   The severities then have to be modified with command changeAlarmSeverity.
				deleteAlarmSeverityProfile: 
				   deletes a profile. Profile 1 is not allowed to be deleted.
				 
				Notifications : none "
			::= { sleAlarmHistoryControl 1 }

		
		-- 1.3.6.1.4.1.6296.101.4.4.2.2
		sleAlarmHistoryControlStatus OBJECT-TYPE
			SYNTAX SleControlStatusType
			MAX-ACCESS read-only
			STATUS current
			DESCRIPTION
				" The status of a control request. "
			::= { sleAlarmHistoryControl 2 }

		
		-- 1.3.6.1.4.1.6296.101.4.4.2.3
		sleAlarmHistoryControlTimer OBJECT-TYPE
			SYNTAX Unsigned32
			MAX-ACCESS read-write
			STATUS current
			DESCRIPTION
				" The maximum wait time for the manager for command ending.
				For long running commands.
				The manager reads this value from the DSLAM. "
			::= { sleAlarmHistoryControl 3 }

		
		-- 1.3.6.1.4.1.6296.101.4.4.2.4
		sleAlarmHistoryControlTimeStamp OBJECT-TYPE
			SYNTAX TimeTicks
			MAX-ACCESS read-only
			STATUS current
			DESCRIPTION
				" The time stamp of the last command (end of command). "
			::= { sleAlarmHistoryControl 4 }

		
		-- 1.3.6.1.4.1.6296.101.4.4.2.5
		sleAlarmHistoryControlReqResult OBJECT-TYPE
			SYNTAX SleControlRequestResultType
			MAX-ACCESS read-only
			STATUS current
			DESCRIPTION
				" The result of the last user command. "
			::= { sleAlarmHistoryControl 5 }

		
		-- 1.3.6.1.4.1.6296.101.4.4.3
		sleAlarmHistoryNotification OBJECT IDENTIFIER ::= { sleAlarmHistory 3 }

		
		-- 1.3.6.1.4.1.6296.101.4.4.3.1
		sleAlarmHistoryCleared NOTIFICATION-TYPE
			OBJECTS { sleAlarmHistoryControlRequest, sleAlarmHistoryControlTimeStamp, sleAlarmHistoryControlReqResult }
			STATUS current
			DESCRIPTION 
				"Description."
			::= { sleAlarmHistoryNotification 1 }

		
		-- 1.3.6.1.4.1.6296.101.4.5
		sleEfmOam OBJECT IDENTIFIER ::= { sleFaultMgmt 5 }

		
		-- 1.3.6.1.4.1.6296.101.4.5.1
		sleEfmOamTable OBJECT-TYPE
			SYNTAX SEQUENCE OF SleEfmOamEntry
			MAX-ACCESS not-accessible
			STATUS current
			DESCRIPTION
				"Description."
			::= { sleEfmOam 1 }

		
		-- 1.3.6.1.4.1.6296.101.4.5.1.1
		sleEfmOamEntry OBJECT-TYPE
			SYNTAX SleEfmOamEntry
			MAX-ACCESS not-accessible
			STATUS current
			DESCRIPTION
				"Description."
			INDEX { sleOamPortIndex }
			::= { sleEfmOamTable 1 }

		
		SleEfmOamEntry ::=
			SEQUENCE { 
				sleOamPortIndex
					INTEGER,
				sleOamMuxAction
					INTEGER,
				sleOamParAction
					INTEGER,
				sleOamAdminState
					INTEGER,
				sleOamMode
					INTEGER,
				sleOamUnidirectionMode
					INTEGER,
				sleOamFunctionsSupported
					BITS,
				sleOamPeerStatus
					INTEGER,
				sleOamPeerMacAddress
					MacAddress,
				sleOamPeerMode
					INTEGER,
				sleOamPeerFunctionsSupported
					BITS,
				sleOamRemLoopback
					INTEGER
			 }

		-- 1.3.6.1.4.1.6296.101.4.5.1.1.1
		sleOamPortIndex OBJECT-TYPE
			SYNTAX INTEGER (1..255)
			MAX-ACCESS read-only
			STATUS current
			DESCRIPTION
				"Description."
			::= { sleEfmOamEntry 1 }

		
		-- 1.3.6.1.4.1.6296.101.4.5.1.1.2
		sleOamMuxAction OBJECT-TYPE
			SYNTAX INTEGER
				{
				fwd(1),
				discard(2)
				}
			MAX-ACCESS read-only
			STATUS current
			DESCRIPTION
				"This value governs the flow of frames from 
				the MAC client to the Muliplexer function."
			::= { sleEfmOamEntry 2 }

		
		-- 1.3.6.1.4.1.6296.101.4.5.1.1.3
		sleOamParAction OBJECT-TYPE
			SYNTAX INTEGER
				{
				fwd(1),
				lb(2),
				discard(3)
				}
			MAX-ACCESS read-only
			STATUS current
			DESCRIPTION
				"This value governs the flow of non-OAMPDUs 
				within the Parser function."
			::= { sleEfmOamEntry 3 }

		
		-- 1.3.6.1.4.1.6296.101.4.5.1.1.4
		sleOamAdminState OBJECT-TYPE
			SYNTAX INTEGER
				{
				disable(0),
				enable(1)
				}
			MAX-ACCESS read-only
			STATUS current
			DESCRIPTION
				"This object is used to provision the default 
				administrative OAM mode for this interface."
			::= { sleEfmOamEntry 4 }

		
		-- 1.3.6.1.4.1.6296.101.4.5.1.1.5
		sleOamMode OBJECT-TYPE
			SYNTAX INTEGER
				{
				passive(0),
				active(1)
				}
			MAX-ACCESS read-only
			STATUS current
			DESCRIPTION
				"This object configures the mode of OAM 
				operation for this Ethernet like interface."
			::= { sleEfmOamEntry 5 }

		
		-- 1.3.6.1.4.1.6296.101.4.5.1.1.6
		sleOamUnidirectionMode OBJECT-TYPE
			SYNTAX INTEGER
				{
				notAvaliable(-2),
				disable(0),
				enable(1)
				}
			MAX-ACCESS read-only
			STATUS current
			DESCRIPTION
				"Description."
			::= { sleEfmOamEntry 6 }

		
		-- 1.3.6.1.4.1.6296.101.4.5.1.1.7
		sleOamFunctionsSupported OBJECT-TYPE
			SYNTAX BITS
				{
				unidirectionalSupport(0),
				loopbackSupport(1),
				eventSupport(2),
				variableSupport(3)
				}
			MAX-ACCESS read-only
			STATUS current
			DESCRIPTION
				"The OAM functions supported on this 
				Ethernet like interface."
			::= { sleEfmOamEntry 7 }

		
		-- 1.3.6.1.4.1.6296.101.4.5.1.1.8
		sleOamPeerStatus OBJECT-TYPE
			SYNTAX INTEGER
				{
				inactive(0),
				active(1)
				}
			MAX-ACCESS read-only
			STATUS current
			DESCRIPTION
				"This object indicates whether the information 
				in this row should be considered valid."
			::= { sleEfmOamEntry 8 }

		
		-- 1.3.6.1.4.1.6296.101.4.5.1.1.9
		sleOamPeerMacAddress OBJECT-TYPE
			SYNTAX MacAddress
			MAX-ACCESS read-only
			STATUS current
			DESCRIPTION
				"The MAC address of the peer OAM entity."
			::= { sleEfmOamEntry 9 }

		
		-- 1.3.6.1.4.1.6296.101.4.5.1.1.10
		sleOamPeerMode OBJECT-TYPE
			SYNTAX INTEGER
				{
				passive(0),
				active(1),
				unknown(2)
				}
			MAX-ACCESS read-only
			STATUS current
			DESCRIPTION
				"The mode Info of the OAM peer as reflected 
				in the latest Information OAMPDU received with 
				a Local Information TLV."
			::= { sleEfmOamEntry 10 }

		
		-- 1.3.6.1.4.1.6296.101.4.5.1.1.11
		sleOamPeerFunctionsSupported OBJECT-TYPE
			SYNTAX BITS
				{
				unidirectionalSupport(0),
				loopbackSupport(1),
				eventSupport(2),
				variableSupport(3)
				}
			MAX-ACCESS read-only
			STATUS current
			DESCRIPTION
				"The OAM functions supported on this 
				Ethernet like interface."
			::= { sleEfmOamEntry 11 }

		
		-- 1.3.6.1.4.1.6296.101.4.5.1.1.12
		sleOamRemLoopback OBJECT-TYPE
			SYNTAX INTEGER
				{
				disable(0),
				enable(1)
				}
			MAX-ACCESS read-only
			STATUS current
			DESCRIPTION
				"Description."
			::= { sleEfmOamEntry 12 }

		
		-- 1.3.6.1.4.1.6296.101.4.5.2
		sleEfmOamControl OBJECT IDENTIFIER ::= { sleEfmOam 2 }

		
		-- 1.3.6.1.4.1.6296.101.4.5.2.1
		sleOamControlRequest OBJECT-TYPE
			SYNTAX INTEGER
				{
				setEfmOamPortProfile(1),
				setEfmOamPortRemLoopback(2)
				}
			MAX-ACCESS read-write
			STATUS current
			DESCRIPTION
				"The MIB object for the user command.."
			::= { sleEfmOamControl 1 }

		
		-- 1.3.6.1.4.1.6296.101.4.5.2.2
		sleOamControlStatus OBJECT-TYPE
			SYNTAX SleControlStatusType
			MAX-ACCESS read-only
			STATUS current
			DESCRIPTION
				"Describes the status of a user command group, 
				used for block commands while a command execution in process."
			::= { sleEfmOamControl 2 }

		
		-- 1.3.6.1.4.1.6296.101.4.5.2.3
		sleOamControlTimer OBJECT-TYPE
			SYNTAX Gauge32
			MAX-ACCESS read-write
			STATUS current
			DESCRIPTION
				"Maximum command duration time in case of long running"
			::= { sleEfmOamControl 3 }

		
		-- 1.3.6.1.4.1.6296.101.4.5.2.4
		sleOamControlTimeStamp OBJECT-TYPE
			SYNTAX TimeStamp
			MAX-ACCESS read-only
			STATUS current
			DESCRIPTION
				"Time stamp attribute set at end of command."
			::= { sleEfmOamControl 4 }

		
		-- 1.3.6.1.4.1.6296.101.4.5.2.5
		sleOamControlReqResult OBJECT-TYPE
			SYNTAX SleControlRequestResultType
			MAX-ACCESS read-only
			STATUS current
			DESCRIPTION
				"Command result attribute"
			::= { sleEfmOamControl 5 }

		
		-- 1.3.6.1.4.1.6296.101.4.5.2.6
		sleOamControlIndex OBJECT-TYPE
			SYNTAX Integer32
			MAX-ACCESS read-write
			STATUS current
			DESCRIPTION
				"Description."
			::= { sleEfmOamControl 6 }

		
		-- 1.3.6.1.4.1.6296.101.4.5.2.7
		sleOamControlPortAdminState OBJECT-TYPE
			SYNTAX INTEGER
				{
				disable(0),
				enable(1)
				}
			MAX-ACCESS read-write
			STATUS current
			DESCRIPTION
				"This object is used to provision the default 
				administrative OAM mode for this interface."
			::= { sleEfmOamControl 7 }

		
		-- 1.3.6.1.4.1.6296.101.4.5.2.8
		sleOamControlPortMode OBJECT-TYPE
			SYNTAX INTEGER
				{
				passive(0),
				active(1)
				}
			MAX-ACCESS read-write
			STATUS current
			DESCRIPTION
				"This object configures the mode of OAM 
				operation for this Ethernet like interface."
			::= { sleEfmOamControl 8 }

		
		-- 1.3.6.1.4.1.6296.101.4.5.2.9
		sleOamControlPortUnidirectionMode OBJECT-TYPE
			SYNTAX INTEGER
				{
				notAvaliable(-2),
				disable(0),
				enable(1)
				}
			MAX-ACCESS read-write
			STATUS current
			DESCRIPTION
				"Description."
			::= { sleEfmOamControl 9 }

		
		-- 1.3.6.1.4.1.6296.101.4.5.2.10
		sleOamControlPortRemLoopback OBJECT-TYPE
			SYNTAX INTEGER
				{
				disable(0),
				enable(1),
				start(2)
				}
			MAX-ACCESS read-write
			STATUS current
			DESCRIPTION
				"The value indicates an optional data link 
				layer frame-level loopback mode, which is 
				controlled remotely."
			::= { sleEfmOamControl 10 }

		
		-- 1.3.6.1.4.1.6296.101.4.5.3
		sleEfmOamNotification OBJECT IDENTIFIER ::= { sleEfmOam 3 }

		
		-- 1.3.6.1.4.1.6296.101.4.5.3.1
		sleEfmOamPortProfileChanged NOTIFICATION-TYPE
			OBJECTS { sleOamControlReqResult, sleOamControlTimeStamp, sleOamControlRequest, sleOamAdminState, sleOamMode, 
				sleOamUnidirectionMode }
			STATUS current
			DESCRIPTION 
				" "
			::= { sleEfmOamNotification 1 }

		
		-- 1.3.6.1.4.1.6296.101.4.5.3.2
		sleEfmOamPortRemLoopback NOTIFICATION-TYPE
			OBJECTS { sleOamControlRequest, sleOamControlReqResult, sleOamControlTimeStamp, sleOamRemLoopback }
			STATUS current
			DESCRIPTION 
				"Description."
			::= { sleEfmOamNotification 2 }

		
		-- 1.3.6.1.4.1.6296.101.4.6
		sleAdvaSystem OBJECT IDENTIFIER ::= { sleFaultMgmt 6 }

		
		-- 1.3.6.1.4.1.6296.101.4.6.1
		sleAdvaSystemTable OBJECT-TYPE
			SYNTAX SEQUENCE OF SleAdvaSystemEntry
			MAX-ACCESS not-accessible
			STATUS current
			DESCRIPTION
				"Description."
			::= { sleAdvaSystem 1 }

		
		-- 1.3.6.1.4.1.6296.101.4.6.1.1
		sleAdvaSystemEntry OBJECT-TYPE
			SYNTAX SleAdvaSystemEntry
			MAX-ACCESS not-accessible
			STATUS current
			DESCRIPTION
				"Description."
			INDEX { sleOamPortIndex }
			::= { sleAdvaSystemTable 1 }

		
		SleAdvaSystemEntry ::=
			SEQUENCE { 
				sleAdvaFSPOperationMode
					INTEGER,
				sleAdvaActiveNetworkInterface
					INTEGER,
				sleAdvaForceNetworkInterface
					INTEGER,
				sleAdvaReportingInterval
					INTEGER,
				sleAdvaNEMIFitted
					INTEGER,
				sleAdvaForceReset
					INTEGER,
				sleAdvaManagerAddress
					IpAddress,
				sleAdvaMinRailVoltageThreshold
					INTEGER,
				sleAdvaMaxRailVoltageThreshold
					INTEGER,
				sleAdvaTemperatureThreshold
					INTEGER,
				sleAdvaPartNumber
					OCTET STRING,
				sleAdvaSerialNumber
					OCTET STRING,
				sleAdvaFirmwareVersion
					OCTET STRING,
				sleAdvaFPGAVersion
					OCTET STRING,
				sleAdvaHardwareRevision
					OCTET STRING,
				sleAdvaCLEICode
					OCTET STRING,
				sleAdvaTemperature
					INTEGER,
				sleAdvaRailVoltage
					INTEGER,
				sleAdvaPSUStates
					INTEGER,
				sleAdvaPSUType
					INTEGER,
				sleAdvaFansFitted
					INTEGER,
				sleAdvaFanState
					INTEGER,
				sleAdvaTransmitMode
					INTEGER
			 }

		-- 1.3.6.1.4.1.6296.101.4.6.1.1.1
		sleAdvaFSPOperationMode OBJECT-TYPE
			SYNTAX INTEGER
				{
				master(1),
				slave(2)
				}
			MAX-ACCESS read-only
			STATUS current
			DESCRIPTION
				"Mode in which the FSP 150 is to operate"
			::= { sleAdvaSystemEntry 1 }

		
		-- 1.3.6.1.4.1.6296.101.4.6.1.1.2
		sleAdvaActiveNetworkInterface OBJECT-TYPE
			SYNTAX INTEGER
				{
				both(0),
				portA(1),
				portB(2)
				}
			MAX-ACCESS read-only
			STATUS current
			DESCRIPTION
				"Which of the network interfaces is the active one"
			::= { sleAdvaSystemEntry 2 }

		
		-- 1.3.6.1.4.1.6296.101.4.6.1.1.3
		sleAdvaForceNetworkInterface OBJECT-TYPE
			SYNTAX INTEGER
				{
				unforced(0),
				forceA(1),
				forceB(2)
				}
			MAX-ACCESS read-only
			STATUS current
			DESCRIPTION
				"Description."
			::= { sleAdvaSystemEntry 3 }

		
		-- 1.3.6.1.4.1.6296.101.4.6.1.1.4
		sleAdvaReportingInterval OBJECT-TYPE
			SYNTAX INTEGER (0..255)
			MAX-ACCESS read-only
			STATUS current
			DESCRIPTION
				"Repeat period in 1/10th seconds for Organisation Specific Alarm 
				Status OAMPDU.  If non-zero and there are any alarms active, 
				repeat the last-sent AS after this interval from when it was 
				last sent.If zero then only send on changes.As a special action, 
				writing zero to this will cause the Alarm Status OAMPDU to be sent (poll)."
			::= { sleAdvaSystemEntry 4 }

		
		-- 1.3.6.1.4.1.6296.101.4.6.1.1.5
		sleAdvaNEMIFitted OBJECT-TYPE
			SYNTAX INTEGER (0..1)
			MAX-ACCESS read-only
			STATUS current
			DESCRIPTION
				"Indicator as to whether a NEMI is fitted."
			::= { sleAdvaSystemEntry 5 }

		
		-- 1.3.6.1.4.1.6296.101.4.6.1.1.6
		sleAdvaForceReset OBJECT-TYPE
			SYNTAX INTEGER (0..1)
			MAX-ACCESS read-only
			STATUS current
			DESCRIPTION
				"Writing True (1) causes the system to be reset."
			::= { sleAdvaSystemEntry 6 }

		
		-- 1.3.6.1.4.1.6296.101.4.6.1.1.7
		sleAdvaManagerAddress OBJECT-TYPE
			SYNTAX IpAddress
			MAX-ACCESS read-only
			STATUS current
			DESCRIPTION
				"The IP address of the Management station monitoring this sytem."
			::= { sleAdvaSystemEntry 7 }

		
		-- 1.3.6.1.4.1.6296.101.4.6.1.1.8
		sleAdvaMinRailVoltageThreshold OBJECT-TYPE
			SYNTAX INTEGER (0..65535)
			MAX-ACCESS read-only
			STATUS current
			DESCRIPTION
				"Threshold in mV below which the Voltage low alarm will be 
				activated. (Alarm Configuration)"
			::= { sleAdvaSystemEntry 8 }

		
		-- 1.3.6.1.4.1.6296.101.4.6.1.1.9
		sleAdvaMaxRailVoltageThreshold OBJECT-TYPE
			SYNTAX INTEGER (0..65535)
			MAX-ACCESS read-only
			STATUS current
			DESCRIPTION
				"Threshold in mV above which the Voltage high alarm will be activated. 
				(Alarm Configuration)"
			::= { sleAdvaSystemEntry 9 }

		
		-- 1.3.6.1.4.1.6296.101.4.6.1.1.10
		sleAdvaTemperatureThreshold OBJECT-TYPE
			SYNTAX INTEGER (0..255)
			MAX-ACCESS read-only
			STATUS current
			DESCRIPTION
				"Threshold in C above which the Temperature alarm will be activated. (Alarm Configuration)"
			::= { sleAdvaSystemEntry 10 }

		
		-- 1.3.6.1.4.1.6296.101.4.6.1.1.11
		sleAdvaPartNumber OBJECT-TYPE
			SYNTAX OCTET STRING (SIZE (0..32))
			MAX-ACCESS read-only
			STATUS current
			DESCRIPTION
				"Part number for the chassis. (Chassis)"
			::= { sleAdvaSystemEntry 11 }

		
		-- 1.3.6.1.4.1.6296.101.4.6.1.1.12
		sleAdvaSerialNumber OBJECT-TYPE
			SYNTAX OCTET STRING (SIZE (0..32))
			MAX-ACCESS read-only
			STATUS current
			DESCRIPTION
				"Serial number for the chassis. (Chassis)"
			::= { sleAdvaSystemEntry 12 }

		
		-- 1.3.6.1.4.1.6296.101.4.6.1.1.13
		sleAdvaFirmwareVersion OBJECT-TYPE
			SYNTAX OCTET STRING (SIZE (0..32))
			MAX-ACCESS read-only
			STATUS current
			DESCRIPTION
				"Firmware version for the chassis. (Chassis)
				(0-length string if unknown)."
			::= { sleAdvaSystemEntry 13 }

		
		-- 1.3.6.1.4.1.6296.101.4.6.1.1.14
		sleAdvaFPGAVersion OBJECT-TYPE
			SYNTAX OCTET STRING (SIZE (0..32))
			MAX-ACCESS read-only
			STATUS current
			DESCRIPTION
				"FPGA version for the chassis. (Chassis)
				(0-length string if unknown)."
			::= { sleAdvaSystemEntry 14 }

		
		-- 1.3.6.1.4.1.6296.101.4.6.1.1.15
		sleAdvaHardwareRevision OBJECT-TYPE
			SYNTAX OCTET STRING (SIZE (0..4))
			MAX-ACCESS read-only
			STATUS current
			DESCRIPTION
				"Hardware revision for the chassis. 
				(Chassis)(0-length string if unknown)."
			::= { sleAdvaSystemEntry 15 }

		
		-- 1.3.6.1.4.1.6296.101.4.6.1.1.16
		sleAdvaCLEICode OBJECT-TYPE
			SYNTAX OCTET STRING (SIZE (0..14))
			MAX-ACCESS read-only
			STATUS current
			DESCRIPTION
				"CLEI for the chassis. (Chassis)"
			::= { sleAdvaSystemEntry 16 }

		
		-- 1.3.6.1.4.1.6296.101.4.6.1.1.17
		sleAdvaTemperature OBJECT-TYPE
			SYNTAX INTEGER (0..255)
			MAX-ACCESS read-only
			STATUS current
			DESCRIPTION
				"Current chassis temperature in degrees C. (Chassis)"
			::= { sleAdvaSystemEntry 17 }

		
		-- 1.3.6.1.4.1.6296.101.4.6.1.1.18
		sleAdvaRailVoltage OBJECT-TYPE
			SYNTAX INTEGER (0..65535)
			MAX-ACCESS read-only
			STATUS current
			DESCRIPTION
				"Current DC power rail voltage (mV). (Chassis)"
			::= { sleAdvaSystemEntry 18 }

		
		-- 1.3.6.1.4.1.6296.101.4.6.1.1.19
		sleAdvaPSUStates OBJECT-TYPE
			SYNTAX INTEGER (0..255)
			MAX-ACCESS read-only
			STATUS current
			DESCRIPTION
				"Bit-mask representing the state of the PSUs.  
				Starting at the LSB, each failed PSU is indicated 
				by a bit set to '1'. (Chassis)"
			::= { sleAdvaSystemEntry 19 }

		
		-- 1.3.6.1.4.1.6296.101.4.6.1.1.20
		sleAdvaPSUType OBJECT-TYPE
			SYNTAX INTEGER
				{
				ac(1),
				dc(2)
				}
			MAX-ACCESS read-only
			STATUS current
			DESCRIPTION
				"Type of PSUs fitted. (Chassis)"
			::= { sleAdvaSystemEntry 20 }

		
		-- 1.3.6.1.4.1.6296.101.4.6.1.1.21
		sleAdvaFansFitted OBJECT-TYPE
			SYNTAX INTEGER (0..255)
			MAX-ACCESS read-only
			STATUS current
			DESCRIPTION
				"Bit-mask representing which fans are fitted.  
				Starting at the LSB, each bit set to '1' indicates a fitted fan.  
				Knowledge of which fans ought to be fitted is assumed. (Chassis)"
			::= { sleAdvaSystemEntry 21 }

		
		-- 1.3.6.1.4.1.6296.101.4.6.1.1.22
		sleAdvaFanState OBJECT-TYPE
			SYNTAX INTEGER (0..255)
			MAX-ACCESS read-only
			STATUS current
			DESCRIPTION
				"Bit-mask representing the state of the fan.  
				Starting at the LSB, each failed fan is indicated by a 
				bit set to '1'. (Chassis)"
			::= { sleAdvaSystemEntry 22 }

		
		-- 1.3.6.1.4.1.6296.101.4.6.1.1.23
		sleAdvaTransmitMode OBJECT-TYPE
			SYNTAX INTEGER
				{
				halfDuplex(0),
				fullDuplex(1)
				}
			MAX-ACCESS read-only
			STATUS current
			DESCRIPTION
				"Electrical Interface for remote instance 4"
			::= { sleAdvaSystemEntry 23 }

		
		-- 1.3.6.1.4.1.6296.101.4.6.2
		sleAdvaSystemControl OBJECT IDENTIFIER ::= { sleAdvaSystem 2 }

		
		-- 1.3.6.1.4.1.6296.101.4.6.2.1
		sleAdvaSystemControlRequest OBJECT-TYPE
			SYNTAX INTEGER
				{
				setAdvaSystemProfile(1),
				setAdvaAlarmProfile(2),
				setAdvaElectricalInterface(3)
				}
			MAX-ACCESS read-write
			STATUS current
			DESCRIPTION
				"The MIB object for the user command.."
			::= { sleAdvaSystemControl 1 }

		
		-- 1.3.6.1.4.1.6296.101.4.6.2.2
		sleAdvaSystemControlStatus OBJECT-TYPE
			SYNTAX SleControlStatusType
			MAX-ACCESS read-only
			STATUS current
			DESCRIPTION
				"Describes the status of a user command group, 
				used for block commands while a command execution in process."
			::= { sleAdvaSystemControl 2 }

		
		-- 1.3.6.1.4.1.6296.101.4.6.2.3
		sleAdvaSystemControlTimer OBJECT-TYPE
			SYNTAX Gauge32
			MAX-ACCESS read-write
			STATUS current
			DESCRIPTION
				"Description."
			::= { sleAdvaSystemControl 3 }

		
		-- 1.3.6.1.4.1.6296.101.4.6.2.4
		sleAdvaSystemControlTimeStamp OBJECT-TYPE
			SYNTAX TimeTicks
			MAX-ACCESS read-write
			STATUS current
			DESCRIPTION
				"Description."
			::= { sleAdvaSystemControl 4 }

		
		-- 1.3.6.1.4.1.6296.101.4.6.2.5
		sleAdvaSystemControlReqResult OBJECT-TYPE
			SYNTAX SleControlRequestResultType
			MAX-ACCESS read-write
			STATUS current
			DESCRIPTION
				"Description."
			::= { sleAdvaSystemControl 5 }

		
		-- 1.3.6.1.4.1.6296.101.4.6.2.6
		sleAdvaSystemControlPortIndex OBJECT-TYPE
			SYNTAX INTEGER (1..255)
			MAX-ACCESS read-write
			STATUS current
			DESCRIPTION
				"Description."
			::= { sleAdvaSystemControl 6 }

		
		-- 1.3.6.1.4.1.6296.101.4.6.2.7
		sleAdvaSystemControlFSPOperationMode OBJECT-TYPE
			SYNTAX INTEGER
				{
				master(1),
				save(2)
				}
			MAX-ACCESS read-write
			STATUS current
			DESCRIPTION
				"Description."
			::= { sleAdvaSystemControl 7 }

		
		-- 1.3.6.1.4.1.6296.101.4.6.2.8
		sleAdvaSystemControlForceNetworkInterface OBJECT-TYPE
			SYNTAX INTEGER
				{
				unforced(0),
				forceA(1),
				forceB(2)
				}
			MAX-ACCESS read-write
			STATUS current
			DESCRIPTION
				"Description."
			::= { sleAdvaSystemControl 8 }

		
		-- 1.3.6.1.4.1.6296.101.4.6.2.9
		sleAdvaSystemControlReportingInterval OBJECT-TYPE
			SYNTAX INTEGER (0..255)
			MAX-ACCESS read-write
			STATUS current
			DESCRIPTION
				"Description."
			::= { sleAdvaSystemControl 9 }

		
		-- 1.3.6.1.4.1.6296.101.4.6.2.10
		sleAdvaSystemControlForceReset OBJECT-TYPE
			SYNTAX INTEGER (0..1)
			MAX-ACCESS read-write
			STATUS current
			DESCRIPTION
				"Description."
			::= { sleAdvaSystemControl 10 }

		
		-- 1.3.6.1.4.1.6296.101.4.6.2.11
		sleAdvaSystemControlMinRailVoltageThreshold OBJECT-TYPE
			SYNTAX INTEGER (0..65535)
			MAX-ACCESS read-write
			STATUS current
			DESCRIPTION
				"Description."
			::= { sleAdvaSystemControl 11 }

		
		-- 1.3.6.1.4.1.6296.101.4.6.2.12
		sleAdvaSystemControlMaxRailVoltageThreshold OBJECT-TYPE
			SYNTAX INTEGER (0..65535)
			MAX-ACCESS read-write
			STATUS current
			DESCRIPTION
				"Description."
			::= { sleAdvaSystemControl 12 }

		
		-- 1.3.6.1.4.1.6296.101.4.6.2.13
		sleAdvaSystemControlTemperatureThreshold OBJECT-TYPE
			SYNTAX INTEGER (0..255)
			MAX-ACCESS read-write
			STATUS current
			DESCRIPTION
				"Description."
			::= { sleAdvaSystemControl 13 }

		
		-- 1.3.6.1.4.1.6296.101.4.6.2.14
		sleAdvaSystemControlTransmitMode OBJECT-TYPE
			SYNTAX INTEGER
				{
				halfDuplex(0),
				fullDuplex(1)
				}
			MAX-ACCESS read-write
			STATUS current
			DESCRIPTION
				"Description."
			::= { sleAdvaSystemControl 14 }

		
		-- 1.3.6.1.4.1.6296.101.4.6.3
		sleAdvaSystemNotification OBJECT IDENTIFIER ::= { sleAdvaSystem 3 }

		
		-- 1.3.6.1.4.1.6296.101.4.6.3.1
		sleAdvaSystemProfileChanged NOTIFICATION-TYPE
			OBJECTS { sleAdvaSystemControlRequest, sleAdvaSystemControlReqResult, sleAdvaSystemControlTimeStamp, sleAdvaFSPOperationMode, sleAdvaForceNetworkInterface, 
				sleAdvaReportingInterval, sleAdvaForceReset }
			STATUS current
			DESCRIPTION 
				"Description."
			::= { sleAdvaSystemNotification 1 }

		
		-- 1.3.6.1.4.1.6296.101.4.6.3.2
		sleAdvaAlarmProfileChanged NOTIFICATION-TYPE
			OBJECTS { sleAdvaSystemControlRequest, sleAdvaSystemControlReqResult, sleAdvaSystemControlTimeStamp, sleAdvaMinRailVoltageThreshold, sleAdvaMaxRailVoltageThreshold, 
				sleAdvaTemperatureThreshold }
			STATUS current
			DESCRIPTION 
				"Description."
			::= { sleAdvaSystemNotification 2 }

		
		-- 1.3.6.1.4.1.6296.101.4.6.3.3
		sleAdvaElectricalInterfaceChanged NOTIFICATION-TYPE
			OBJECTS { sleAdvaSystemControlRequest, sleAdvaSystemControlReqResult, sleAdvaSystemControlTimeStamp, sleAdvaTransmitMode }
			STATUS current
			DESCRIPTION 
				"Description."
			::= { sleAdvaSystemNotification 3 }

		
		-- 1.3.6.1.4.1.6296.101.4.7
		sleAdvaGeneral OBJECT IDENTIFIER ::= { sleFaultMgmt 7 }

		
		-- 1.3.6.1.4.1.6296.101.4.7.1
		sleAdvaGeneralTable OBJECT-TYPE
			SYNTAX SEQUENCE OF SleAdvaGeneralEntry
			MAX-ACCESS not-accessible
			STATUS current
			DESCRIPTION
				"Description."
			::= { sleAdvaGeneral 1 }

		
		-- 1.3.6.1.4.1.6296.101.4.7.1.1
		sleAdvaGeneralEntry OBJECT-TYPE
			SYNTAX SleAdvaGeneralEntry
			MAX-ACCESS not-accessible
			STATUS current
			DESCRIPTION
				"Description."
			INDEX { sleOamPortIndex, sleAdvaRemInstance }
			::= { sleAdvaGeneralTable 1 }

		
		SleAdvaGeneralEntry ::=
			SEQUENCE { 
				sleAdvaRemInstance
					INTEGER,
				sleAdvaOperationalStatus
					INTEGER,
				sleAdvaLineSpeed
					Integer32,
				sleAdvaMACAddress
					MacAddress,
				sleAdvaConnectorType
					INTEGER,
				sleAdvaAutonegiotation
					INTEGER,
				sleAdvaLinkLossForwarding
					INTEGER,
				sleAdvaAdminState
					INTEGER,
				sleAdvaRemoteInterfaceIndex
					INTEGER,
				sleAdvaUserDefinedString
					OCTET STRING,
				sleAdvaRemoteSignalling
					INTEGER,
				sleAdvaConfiguration
					INTEGER,
				sleAdvaLocalTechnologyAbility
					BITS,
				sleAdvaAdvertisedTechnologyAbility
					BITS,
				sleAdvaReceivedTechnologyAbility
					BITS,
				sleAdvaLocalSectorAbility
					BITS,
				sleAdvaAdvertisedSectorAbility
					BITS,
				sleAdvaReceivedSectorAbility
					BITS,
				sleAdvaDuplexCapabilities
					INTEGER,
				sleAdvaPHYType
					INTEGER,
				sleAdvaPHYTypeList
					BITS,
				sleAdvaMIIDetect
					INTEGER,
				sleAdvaPHYState
					INTEGER,
				sleAdvaGoodFramesTransmitted
					Integer32,
				sleAdvaSingleCollisionFrames
					Integer32,
				sleAdvaMultipleCollisionFrames
					Integer32,
				sleAdvaGoodFramesReceived
					Integer32,
				sleAdvaFCSErrors
					Integer32,
				sleAdvaAlignmentErrors
					Integer32,
				sleAdvaFramesTooLong
					Integer32,
				sleAdvaBytesTransmitted
					Integer32,
				sleAdvaBytesReceived
					Integer32,
				sleAdvaSymbolErrors
					Integer32
			 }

		-- 1.3.6.1.4.1.6296.101.4.7.1.1.1
		sleAdvaRemInstance OBJECT-TYPE
			SYNTAX INTEGER (0..4)
			MAX-ACCESS read-only
			STATUS current
			DESCRIPTION
				"Description."
			::= { sleAdvaGeneralEntry 1 }

		
		-- 1.3.6.1.4.1.6296.101.4.7.1.1.2
		sleAdvaOperationalStatus OBJECT-TYPE
			SYNTAX INTEGER
				{
				up(1),
				down(2),
				outofservice(3),
				unknown(4)
				}
			MAX-ACCESS read-only
			STATUS current
			DESCRIPTION
				"encoding TBD. (General)"
			::= { sleAdvaGeneralEntry 2 }

		
		-- 1.3.6.1.4.1.6296.101.4.7.1.1.3
		sleAdvaLineSpeed OBJECT-TYPE
			SYNTAX Integer32
			MAX-ACCESS read-only
			STATUS current
			DESCRIPTION
				"Line speed in kbit/s. (General)"
			::= { sleAdvaGeneralEntry 3 }

		
		-- 1.3.6.1.4.1.6296.101.4.7.1.1.4
		sleAdvaMACAddress OBJECT-TYPE
			SYNTAX MacAddress
			MAX-ACCESS read-only
			STATUS current
			DESCRIPTION
				"The Ethernet address of the interface. (General)"
			::= { sleAdvaGeneralEntry 4 }

		
		-- 1.3.6.1.4.1.6296.101.4.7.1.1.5
		sleAdvaConnectorType OBJECT-TYPE
			SYNTAX INTEGER
				{
				sc(1),
				fc(2),
				mu(3),
				rj45(4),
				lu(5)
				}
			MAX-ACCESS read-only
			STATUS current
			DESCRIPTION
				"encoding TBD. (General)"
			::= { sleAdvaGeneralEntry 5 }

		
		-- 1.3.6.1.4.1.6296.101.4.7.1.1.6
		sleAdvaAutonegiotation OBJECT-TYPE
			SYNTAX INTEGER
				{
				enable(1),
				disable(2)
				}
			MAX-ACCESS read-only
			STATUS current
			DESCRIPTION
				"Autonegiotation package - aAutoNegAdminState. (General)Enabled or disabled.	"
			::= { sleAdvaGeneralEntry 6 }

		
		-- 1.3.6.1.4.1.6296.101.4.7.1.1.7
		sleAdvaLinkLossForwarding OBJECT-TYPE
			SYNTAX INTEGER (0..1)
			MAX-ACCESS read-only
			STATUS current
			DESCRIPTION
				"When enabled access interface is brought down, when both network interfaces are down. (General)"
			::= { sleAdvaGeneralEntry 7 }

		
		-- 1.3.6.1.4.1.6296.101.4.7.1.1.8
		sleAdvaAdminState OBJECT-TYPE
			SYNTAX INTEGER
				{
				up(1),
				down(2)
				}
			MAX-ACCESS read-only
			STATUS current
			DESCRIPTION
				"Whether the interface is available. (General)"
			::= { sleAdvaGeneralEntry 8 }

		
		-- 1.3.6.1.4.1.6296.101.4.7.1.1.9
		sleAdvaRemoteInterfaceIndex OBJECT-TYPE
			SYNTAX INTEGER (0..255)
			MAX-ACCESS read-only
			STATUS current
			DESCRIPTION
				"The index of the remote interface the interface is connected to. (General)"
			::= { sleAdvaGeneralEntry 9 }

		
		-- 1.3.6.1.4.1.6296.101.4.7.1.1.10
		sleAdvaUserDefinedString OBJECT-TYPE
			SYNTAX OCTET STRING (SIZE (0..32))
			MAX-ACCESS read-only
			STATUS current
			DESCRIPTION
				"User definable string associated with interface. (General)"
			::= { sleAdvaGeneralEntry 10 }

		
		-- 1.3.6.1.4.1.6296.101.4.7.1.1.11
		sleAdvaRemoteSignalling OBJECT-TYPE
			SYNTAX INTEGER
				{
				detected(1),
				notdetected(2)
				}
			MAX-ACCESS read-only
			STATUS current
			DESCRIPTION
				"Autonegiotation package - aAutoNegRemoteSignalling. (AutoNego)"
			::= { sleAdvaGeneralEntry 11 }

		
		-- 1.3.6.1.4.1.6296.101.4.7.1.1.12
		sleAdvaConfiguration OBJECT-TYPE
			SYNTAX INTEGER
				{
				other(1),
				configuring(2),
				completed(3),
				disabled(4),
				parallelDetectFail(5)
				}
			MAX-ACCESS read-only
			STATUS current
			DESCRIPTION
				"Autonegiotation package - aAutoNegConfig. 
				(AutoNego)Indicates whether Auto-Negotiation 
				signaling is in progress or has completed."
			::= { sleAdvaGeneralEntry 12 }

		
		-- 1.3.6.1.4.1.6296.101.4.7.1.1.13
		sleAdvaLocalTechnologyAbility OBJECT-TYPE
			SYNTAX BITS
				{
				global(0),
				unknown(1),
				base10T(2),
				base10TFD(3),
				base100T4(4),
				base100TX(5),
				base100TXFD(6),
				fdxpause(7),
				fdxapause(8),
				fdxspause(9),
				fdxbpause(10),
				base100T2(11),
				base100T2FD(12),
				base1000X(13),
				base1000XFD(14),
				base1000T(15),
				base1000TFD(16),
				remFault1(17),
				remFault2(18),
				isoEthernet(19)
				}
			MAX-ACCESS read-only
			STATUS current
			DESCRIPTION
				"Autonegiotation package - aAutoNegLocalTechnologyAbility. 
				(AutoNego)This indicates the technology ability of the local device"
			::= { sleAdvaGeneralEntry 13 }

		
		-- 1.3.6.1.4.1.6296.101.4.7.1.1.14
		sleAdvaAdvertisedTechnologyAbility OBJECT-TYPE
			SYNTAX BITS
				{
				global(0),
				unknown(1),
				base10T(2),
				base10TFD(3),
				base100T4(4),
				base100TX(5),
				base100TXFD(6),
				fdxpause(7),
				fdxapause(8),
				fdxspause(9),
				fdxbpause(10),
				base100T2(11),
				base100T2FD(12),
				base1000X(13),
				base1000XFD(14),
				base1000T(15),
				base1000TFD(16),
				remFault1(17),
				remFault2(18),
				isoEthernet(19)
				}
			MAX-ACCESS read-only
			STATUS current
			DESCRIPTION
				"Autonegiotation package - aAutoNegAdvertisedTechnologyAbility. 
				(AutoNego)The advertised technology ability of the local device."
			::= { sleAdvaGeneralEntry 14 }

		
		-- 1.3.6.1.4.1.6296.101.4.7.1.1.15
		sleAdvaReceivedTechnologyAbility OBJECT-TYPE
			SYNTAX BITS
				{
				global(0),
				unknown(1),
				base10T(2),
				base10TFD(3),
				base100T4(4),
				base100TX(5),
				base100TXFD(6),
				fdxpause(7),
				fdxapause(8),
				fdxspause(9),
				fdxbpause(10),
				base100T2(11),
				base100T2FD(12),
				base1000X(13),
				base1000XFD(14),
				base1000T(15),
				base1000TFD(16),
				remFault1(17),
				remFault2(18),
				isoEthernet(19)
				}
			MAX-ACCESS read-only
			STATUS current
			DESCRIPTION
				"Autonegiotation package - aAutoNegReceivedTechnologyAbility. 
				(AutoNego)Indicates the advertised technology ability of the 
				remote hardware."
			::= { sleAdvaGeneralEntry 15 }

		
		-- 1.3.6.1.4.1.6296.101.4.7.1.1.16
		sleAdvaLocalSectorAbility OBJECT-TYPE
			SYNTAX BITS
				{
				other(0),
				ethernet(1),
				isoethernet(2)
				}
			MAX-ACCESS read-only
			STATUS current
			DESCRIPTION
				"Autonegiotation package - aAutoNegLocalSectorAbility. (AutoNego)"
			::= { sleAdvaGeneralEntry 16 }

		
		-- 1.3.6.1.4.1.6296.101.4.7.1.1.17
		sleAdvaAdvertisedSectorAbility OBJECT-TYPE
			SYNTAX BITS
				{
				other(0),
				ethernet(1),
				isoethernet(2)
				}
			MAX-ACCESS read-only
			STATUS current
			DESCRIPTION
				"Autonegiotation package - aAutoNegLocalSectorAbility. (AutoNego)"
			::= { sleAdvaGeneralEntry 17 }

		
		-- 1.3.6.1.4.1.6296.101.4.7.1.1.18
		sleAdvaReceivedSectorAbility OBJECT-TYPE
			SYNTAX BITS
				{
				other(0),
				ethernet(1),
				isoethernet(2)
				}
			MAX-ACCESS read-only
			STATUS current
			DESCRIPTION
				"Autonegiotation package - aAutoNegLocalSectorAbility. (AutoNego)"
			::= { sleAdvaGeneralEntry 18 }

		
		-- 1.3.6.1.4.1.6296.101.4.7.1.1.19
		sleAdvaDuplexCapabilities OBJECT-TYPE
			SYNTAX INTEGER
				{
				halfduplex(0),
				fullduplex(1)
				}
			MAX-ACCESS read-only
			STATUS current
			DESCRIPTION
				"Mandatory package - aMacCapabilities. 
				(PHY)The modes of duplex the access interface can support"
			::= { sleAdvaGeneralEntry 19 }

		
		-- 1.3.6.1.4.1.6296.101.4.7.1.1.20
		sleAdvaPHYType OBJECT-TYPE
			SYNTAX INTEGER
				{
				other(1),
				unknown(2),
				none(3),
				base10(4),
				base100T4(5),
				base100X(6),
				base100T2(7),
				base1000X(8),
				base1000T(9)
				}
			MAX-ACCESS read-only
			STATUS current
			DESCRIPTION
				"Basic Package - aPhyType. (PHY)"
			::= { sleAdvaGeneralEntry 20 }

		
		-- 1.3.6.1.4.1.6296.101.4.7.1.1.21
		sleAdvaPHYTypeList OBJECT-TYPE
			SYNTAX BITS
				{
				other(0),
				unknown(1),
				none(2),
				base10(3),
				base100T4(4),
				base100X(5),
				base100T2(6),
				base1000X(7),
				base1000T(8)
				}
			MAX-ACCESS read-only
			STATUS current
			DESCRIPTION
				"Basic Package - aPhyTypeList. (PHY)"
			::= { sleAdvaGeneralEntry 21 }

		
		-- 1.3.6.1.4.1.6296.101.4.7.1.1.22
		sleAdvaMIIDetect OBJECT-TYPE
			SYNTAX INTEGER
				{
				unknown(1),
				nothingConnected(2),
				connected(3),
				absent(4)
				}
			MAX-ACCESS read-only
			STATUS current
			DESCRIPTION
				"Basic Package - aMIIDetect. (PHY)"
			::= { sleAdvaGeneralEntry 22 }

		
		-- 1.3.6.1.4.1.6296.101.4.7.1.1.23
		sleAdvaPHYState OBJECT-TYPE
			SYNTAX INTEGER
				{
				enable(1),
				disable(2)
				}
			MAX-ACCESS read-only
			STATUS current
			DESCRIPTION
				"Description."
			::= { sleAdvaGeneralEntry 23 }

		
		-- 1.3.6.1.4.1.6296.101.4.7.1.1.24
		sleAdvaGoodFramesTransmitted OBJECT-TYPE
			SYNTAX Integer32
			MAX-ACCESS read-only
			STATUS current
			DESCRIPTION
				"Mandatory package - aFramesTransmittedOK. (PHY)Non-resettable, 
				wrapping count of good frames transmitted since OAM enabled."
			::= { sleAdvaGeneralEntry 24 }

		
		-- 1.3.6.1.4.1.6296.101.4.7.1.1.25
		sleAdvaSingleCollisionFrames OBJECT-TYPE
			SYNTAX Integer32
			MAX-ACCESS read-only
			STATUS current
			DESCRIPTION
				"Mandatory package - aSingleCollisionFrames. (PHY)Non-resettable, 
				wrapping count of single collisions since OAM enabled."
			::= { sleAdvaGeneralEntry 25 }

		
		-- 1.3.6.1.4.1.6296.101.4.7.1.1.26
		sleAdvaMultipleCollisionFrames OBJECT-TYPE
			SYNTAX Integer32
			MAX-ACCESS read-only
			STATUS current
			DESCRIPTION
				"Mandatory package - aMultipleCollisionFrames. (PHY)Non-resettable, 
				wrapping count of multiple collisions since OAM enabled."
			::= { sleAdvaGeneralEntry 26 }

		
		-- 1.3.6.1.4.1.6296.101.4.7.1.1.27
		sleAdvaGoodFramesReceived OBJECT-TYPE
			SYNTAX Integer32
			MAX-ACCESS read-only
			STATUS current
			DESCRIPTION
				"Mandatory package - aFramesReceivedOKNon-resettable, 
				wrapping count of good frames received since OAM enabled"
			::= { sleAdvaGeneralEntry 27 }

		
		-- 1.3.6.1.4.1.6296.101.4.7.1.1.28
		sleAdvaFCSErrors OBJECT-TYPE
			SYNTAX Integer32
			MAX-ACCESS read-only
			STATUS current
			DESCRIPTION
				"Mandatory package - aFrameCheckSequenceErrors. (PHY)Non-resettable, 
				wrapping count of frames received with frame check sequence 
				error since OAM enabled."
			::= { sleAdvaGeneralEntry 28 }

		
		-- 1.3.6.1.4.1.6296.101.4.7.1.1.29
		sleAdvaAlignmentErrors OBJECT-TYPE
			SYNTAX Integer32
			MAX-ACCESS read-only
			STATUS current
			DESCRIPTION
				"Mandatory package - aAlignmentErrors. (PHY)Non-resettable, 
				wrapping count of frames received with alignment error since OAM enabled."
			::= { sleAdvaGeneralEntry 29 }

		
		-- 1.3.6.1.4.1.6296.101.4.7.1.1.30
		sleAdvaFramesTooLong OBJECT-TYPE
			SYNTAX Integer32
			MAX-ACCESS read-only
			STATUS current
			DESCRIPTION
				"aFrameTooLongErrors. (PHY)Non-resettable, wrapping count 
				of frames received longer than maxFrameSize"
			::= { sleAdvaGeneralEntry 30 }

		
		-- 1.3.6.1.4.1.6296.101.4.7.1.1.31
		sleAdvaBytesTransmitted OBJECT-TYPE
			SYNTAX Integer32
			MAX-ACCESS read-only
			STATUS current
			DESCRIPTION
				"Non-resettable, wrapping count of bytes transmitted 
				since OAM enabled. (PHY)"
			::= { sleAdvaGeneralEntry 31 }

		
		-- 1.3.6.1.4.1.6296.101.4.7.1.1.32
		sleAdvaBytesReceived OBJECT-TYPE
			SYNTAX Integer32
			MAX-ACCESS read-only
			STATUS current
			DESCRIPTION
				"Non-resettable, wrapping count of bytes received since OAM enabled. (PHY)"
			::= { sleAdvaGeneralEntry 32 }

		
		-- 1.3.6.1.4.1.6296.101.4.7.1.1.33
		sleAdvaSymbolErrors OBJECT-TYPE
			SYNTAX Integer32
			MAX-ACCESS read-only
			STATUS current
			DESCRIPTION
				"Non-resettable, wrapping count of symbol errors received.  
				Note: some interfaces may only report one symbol error per frame. (PHY)"
			::= { sleAdvaGeneralEntry 33 }

		
		-- 1.3.6.1.4.1.6296.101.4.7.2
		sleAdvaGeneralControl OBJECT IDENTIFIER ::= { sleAdvaGeneral 2 }

		
		-- 1.3.6.1.4.1.6296.101.4.7.2.1
		sleAdvaGeneralControlRequest OBJECT-TYPE
			SYNTAX INTEGER
				{
				setAdvaGeneralProfile(1),
				setAdvaAutonegProfile(2)
				}
			MAX-ACCESS read-write
			STATUS current
			DESCRIPTION
				"Description."
			::= { sleAdvaGeneralControl 1 }

		
		-- 1.3.6.1.4.1.6296.101.4.7.2.2
		sleAdvaGeneralControlStatus OBJECT-TYPE
			SYNTAX SleControlStatusType
			MAX-ACCESS read-only
			STATUS current
			DESCRIPTION
				"Description."
			::= { sleAdvaGeneralControl 2 }

		
		-- 1.3.6.1.4.1.6296.101.4.7.2.3
		sleAdvaGeneralControlTimer OBJECT-TYPE
			SYNTAX Gauge32
			MAX-ACCESS read-write
			STATUS current
			DESCRIPTION
				"Description."
			::= { sleAdvaGeneralControl 3 }

		
		-- 1.3.6.1.4.1.6296.101.4.7.2.4
		sleAdvaGeneralControlTimeStamp OBJECT-TYPE
			SYNTAX TimeTicks
			MAX-ACCESS read-write
			STATUS current
			DESCRIPTION
				"Description."
			::= { sleAdvaGeneralControl 4 }

		
		-- 1.3.6.1.4.1.6296.101.4.7.2.5
		sleAdvaGeneralControlReqResult OBJECT-TYPE
			SYNTAX SleControlRequestResultType
			MAX-ACCESS read-write
			STATUS current
			DESCRIPTION
				"Description."
			::= { sleAdvaGeneralControl 5 }

		
		-- 1.3.6.1.4.1.6296.101.4.7.2.6
		sleAdvaGeneralControlPortIndex OBJECT-TYPE
			SYNTAX INTEGER (1..255)
			MAX-ACCESS read-write
			STATUS current
			DESCRIPTION
				"Description."
			::= { sleAdvaGeneralControl 6 }

		
		-- 1.3.6.1.4.1.6296.101.4.7.2.7
		sleAdvaGeneralControlRemInstance OBJECT-TYPE
			SYNTAX INTEGER (1..4)
			MAX-ACCESS read-write
			STATUS current
			DESCRIPTION
				"Description."
			::= { sleAdvaGeneralControl 7 }

		
		-- 1.3.6.1.4.1.6296.101.4.7.2.8
		sleAdvaGeneralControlLineSpeed OBJECT-TYPE
			SYNTAX Integer32
			MAX-ACCESS read-write
			STATUS current
			DESCRIPTION
				"Description."
			::= { sleAdvaGeneralControl 8 }

		
		-- 1.3.6.1.4.1.6296.101.4.7.2.9
		sleAdvaGeneralControlAutonegiotation OBJECT-TYPE
			SYNTAX INTEGER
				{
				enable(1),
				disable(2)
				}
			MAX-ACCESS read-write
			STATUS current
			DESCRIPTION
				"Description."
			::= { sleAdvaGeneralControl 9 }

		
		-- 1.3.6.1.4.1.6296.101.4.7.2.10
		sleAdvaGeneralControlLinkLossForwarding OBJECT-TYPE
			SYNTAX INTEGER (0..1)
			MAX-ACCESS read-write
			STATUS current
			DESCRIPTION
				"Description."
			::= { sleAdvaGeneralControl 10 }

		
		-- 1.3.6.1.4.1.6296.101.4.7.2.11
		sleAdvaGeneralControlUserDefinedString OBJECT-TYPE
			SYNTAX OCTET STRING (SIZE (0..32))
			MAX-ACCESS read-write
			STATUS current
			DESCRIPTION
				"Description."
			::= { sleAdvaGeneralControl 11 }

		
		-- 1.3.6.1.4.1.6296.101.4.7.2.12
		sleAdvaGeneralControlAdvertisedTechnologyAbility OBJECT-TYPE
			SYNTAX BITS
				{
				global(0),
				unknown(1),
				base10T(2),
				base10TFD(3),
				base100T4(4),
				base100TX(5),
				base100TXFD(6),
				fdxpause(7),
				fdxapause(8),
				fdxspause(9),
				fdxbpause(10),
				base100T2(11),
				base100T2FD(12),
				base1000X(13),
				base1000XFD(14),
				base1000T(15),
				base1000TFD(16),
				remFault1(17),
				remFault2(18),
				isoEthernet(19)
				}
			MAX-ACCESS read-write
			STATUS current
			DESCRIPTION
				"Description."
			::= { sleAdvaGeneralControl 12 }

		
		-- 1.3.6.1.4.1.6296.101.4.7.2.13
		sleAdvaGeneralControlAdvertisedSectorAbility OBJECT-TYPE
			SYNTAX BITS
				{
				other(0),
				ethernet(1),
				isoethernet(2)
				}
			MAX-ACCESS read-write
			STATUS current
			DESCRIPTION
				"Description."
			::= { sleAdvaGeneralControl 13 }

		
		-- 1.3.6.1.4.1.6296.101.4.7.3
		sleAdvaGeneralNotification OBJECT IDENTIFIER ::= { sleAdvaGeneral 3 }

		
		-- 1.3.6.1.4.1.6296.101.4.7.3.1
		sleAdvaGeneralProfileChanged NOTIFICATION-TYPE
			OBJECTS { sleAdvaGeneralControlRequest, sleAdvaGeneralControlReqResult, sleAdvaGeneralControlTimeStamp, sleAdvaLineSpeed, sleAdvaAutonegiotation, 
				sleAdvaLinkLossForwarding, sleAdvaUserDefinedString }
			STATUS current
			DESCRIPTION 
				"Description."
			::= { sleAdvaGeneralNotification 1 }

		
		-- 1.3.6.1.4.1.6296.101.4.7.3.2
		sleAdvaAutonegProfileChanged NOTIFICATION-TYPE
			OBJECTS { sleAdvaGeneralControlRequest, sleAdvaGeneralControlReqResult, sleAdvaGeneralControlTimeStamp, sleAdvaAdvertisedTechnologyAbility, sleAdvaAdvertisedSectorAbility
				 }
			STATUS current
			DESCRIPTION 
				"Description."
			::= { sleAdvaGeneralNotification 2 }

		
		-- 1.3.6.1.4.1.6296.101.4.8
		sleAdvaModule OBJECT IDENTIFIER ::= { sleFaultMgmt 8 }

		
		-- 1.3.6.1.4.1.6296.101.4.8.1
		sleAdvaModuleTable OBJECT-TYPE
			SYNTAX SEQUENCE OF SleAdvaModuleEntry
			MAX-ACCESS not-accessible
			STATUS current
			DESCRIPTION
				"Description."
			::= { sleAdvaModule 1 }

		
		-- 1.3.6.1.4.1.6296.101.4.8.1.1
		sleAdvaModuleEntry OBJECT-TYPE
			SYNTAX SleAdvaModuleEntry
			MAX-ACCESS not-accessible
			STATUS current
			DESCRIPTION
				"Description."
			INDEX { sleOamPortIndex, sleAdvaRemInstance }
			::= { sleAdvaModuleTable 1 }

		
		SleAdvaModuleEntry ::=
			SEQUENCE { 
				sleAdvaModuleType
					INTEGER,
				sleAdvaModulePartNumber
					OCTET STRING,
				sleAdvaModuleSerialNumber
					OCTET STRING,
				sleAdvaModuleFirmwareVersion
					OCTET STRING,
				sleAdvaModuleSoftwareVersion
					OCTET STRING,
				sleAdvaModuleHardwareRevision
					OCTET STRING,
				sleAdvaModuleCLEICode
					OCTET STRING
			 }

		-- 1.3.6.1.4.1.6296.101.4.8.1.1.1
		sleAdvaModuleType OBJECT-TYPE
			SYNTAX INTEGER
				{
				sfp(1),
				nemi(2),
				other(3)
				}
			MAX-ACCESS read-only
			STATUS current
			DESCRIPTION
				"encoding TBD"
			::= { sleAdvaModuleEntry 1 }

		
		-- 1.3.6.1.4.1.6296.101.4.8.1.1.2
		sleAdvaModulePartNumber OBJECT-TYPE
			SYNTAX OCTET STRING (SIZE (0..16))
			MAX-ACCESS read-only
			STATUS current
			DESCRIPTION
				"Part number for the module"
			::= { sleAdvaModuleEntry 2 }

		
		-- 1.3.6.1.4.1.6296.101.4.8.1.1.3
		sleAdvaModuleSerialNumber OBJECT-TYPE
			SYNTAX OCTET STRING (SIZE (0..16))
			MAX-ACCESS read-only
			STATUS current
			DESCRIPTION
				"Serial number for the module"
			::= { sleAdvaModuleEntry 3 }

		
		-- 1.3.6.1.4.1.6296.101.4.8.1.1.4
		sleAdvaModuleFirmwareVersion OBJECT-TYPE
			SYNTAX OCTET STRING (SIZE (0..16))
			MAX-ACCESS read-only
			STATUS current
			DESCRIPTION
				"Firmware version for the module."
			::= { sleAdvaModuleEntry 4 }

		
		-- 1.3.6.1.4.1.6296.101.4.8.1.1.5
		sleAdvaModuleSoftwareVersion OBJECT-TYPE
			SYNTAX OCTET STRING (SIZE (0..16))
			MAX-ACCESS read-only
			STATUS current
			DESCRIPTION
				"Software version for the module"
			::= { sleAdvaModuleEntry 5 }

		
		-- 1.3.6.1.4.1.6296.101.4.8.1.1.6
		sleAdvaModuleHardwareRevision OBJECT-TYPE
			SYNTAX OCTET STRING (SIZE (0..4))
			MAX-ACCESS read-only
			STATUS current
			DESCRIPTION
				"Hardware revision for the module."
			::= { sleAdvaModuleEntry 6 }

		
		-- 1.3.6.1.4.1.6296.101.4.8.1.1.7
		sleAdvaModuleCLEICode OBJECT-TYPE
			SYNTAX OCTET STRING (SIZE (0..14))
			MAX-ACCESS read-only
			STATUS current
			DESCRIPTION
				"CLEI for the module."
			::= { sleAdvaModuleEntry 7 }

		
		-- 1.3.6.1.4.1.6296.101.4.9
		sleAdvaOptical OBJECT IDENTIFIER ::= { sleFaultMgmt 9 }

		
		-- 1.3.6.1.4.1.6296.101.4.9.1
		sleAdvaOpticalTable OBJECT-TYPE
			SYNTAX SEQUENCE OF SleAdvaOpticalEntry
			MAX-ACCESS not-accessible
			STATUS current
			DESCRIPTION
				"Description."
			::= { sleAdvaOptical 1 }

		
		-- 1.3.6.1.4.1.6296.101.4.9.1.1
		sleAdvaOpticalEntry OBJECT-TYPE
			SYNTAX SleAdvaOpticalEntry
			MAX-ACCESS not-accessible
			STATUS current
			DESCRIPTION
				"Description."
			INDEX { sleOamPortIndex, sleAdvaRemInstance }
			::= { sleAdvaOpticalTable 1 }

		
		SleAdvaOpticalEntry ::=
			SEQUENCE { 
				sleAdvaOpticalThresholdLevel
					INTEGER,
				sleAdvaLinkLength1
					INTEGER,
				sleAdvaLinkLength2
					INTEGER,
				sleAdvaLinkLength3
					INTEGER,
				sleAdvaLinkLength4
					INTEGER,
				sleAdvaLinkLengthCu
					INTEGER,
				sleAdvaWaveLength
					INTEGER,
				sleAdvaLaserBias
					INTEGER,
				sleAdvaTransmitPower
					INTEGER,
				sleAdvaReceivePower
					INTEGER,
				sleAdvaLaserTxTemperature
					INTEGER
			 }

		-- 1.3.6.1.4.1.6296.101.4.9.1.1.1
		sleAdvaOpticalThresholdLevel OBJECT-TYPE
			SYNTAX INTEGER (0..65535)
			MAX-ACCESS read-only
			STATUS current
			DESCRIPTION
				"Threshold for the receive power level in dBm below which 
				the Interface optical threshold alarm will be activated.Per interface."
			::= { sleAdvaOpticalEntry 1 }

		
		-- 1.3.6.1.4.1.6296.101.4.9.1.1.2
		sleAdvaLinkLength1 OBJECT-TYPE
			SYNTAX INTEGER (0..255)
			MAX-ACCESS read-only
			STATUS current
			DESCRIPTION
				"Link length supported for 9/125 mm fiber, units of km"
			::= { sleAdvaOpticalEntry 2 }

		
		-- 1.3.6.1.4.1.6296.101.4.9.1.1.3
		sleAdvaLinkLength2 OBJECT-TYPE
			SYNTAX INTEGER (0..255)
			MAX-ACCESS read-only
			STATUS current
			DESCRIPTION
				"Link length supported for 9/125 mm fiber, units of 100 m"
			::= { sleAdvaOpticalEntry 3 }

		
		-- 1.3.6.1.4.1.6296.101.4.9.1.1.4
		sleAdvaLinkLength3 OBJECT-TYPE
			SYNTAX INTEGER (0..255)
			MAX-ACCESS read-only
			STATUS current
			DESCRIPTION
				"Link length supported for 50/125 mm fiber, units of 10 m"
			::= { sleAdvaOpticalEntry 4 }

		
		-- 1.3.6.1.4.1.6296.101.4.9.1.1.5
		sleAdvaLinkLength4 OBJECT-TYPE
			SYNTAX INTEGER (0..255)
			MAX-ACCESS read-only
			STATUS current
			DESCRIPTION
				"Link length supported for 62.5/125 mm fiber, units of 10 m"
			::= { sleAdvaOpticalEntry 5 }

		
		-- 1.3.6.1.4.1.6296.101.4.9.1.1.6
		sleAdvaLinkLengthCu OBJECT-TYPE
			SYNTAX INTEGER (0..255)
			MAX-ACCESS read-only
			STATUS current
			DESCRIPTION
				"Link length supported for copper, units of meters"
			::= { sleAdvaOpticalEntry 6 }

		
		-- 1.3.6.1.4.1.6296.101.4.9.1.1.7
		sleAdvaWaveLength OBJECT-TYPE
			SYNTAX INTEGER (0..65535)
			MAX-ACCESS read-only
			STATUS current
			DESCRIPTION
				"Nominal wavelength in nm"
			::= { sleAdvaOpticalEntry 7 }

		
		-- 1.3.6.1.4.1.6296.101.4.9.1.1.8
		sleAdvaLaserBias OBJECT-TYPE
			SYNTAX INTEGER (0..65535)
			MAX-ACCESS read-only
			STATUS current
			DESCRIPTION
				"Current laser bias current in mA."
			::= { sleAdvaOpticalEntry 8 }

		
		-- 1.3.6.1.4.1.6296.101.4.9.1.1.9
		sleAdvaTransmitPower OBJECT-TYPE
			SYNTAX INTEGER (0..65535)
			MAX-ACCESS read-only
			STATUS current
			DESCRIPTION
				"Current transmit power in dBm as reported by optics."
			::= { sleAdvaOpticalEntry 9 }

		
		-- 1.3.6.1.4.1.6296.101.4.9.1.1.10
		sleAdvaReceivePower OBJECT-TYPE
			SYNTAX INTEGER (0..65535)
			MAX-ACCESS read-only
			STATUS current
			DESCRIPTION
				"Current receive power in dBm as reported by optics.  "
			::= { sleAdvaOpticalEntry 10 }

		
		-- 1.3.6.1.4.1.6296.101.4.9.1.1.11
		sleAdvaLaserTxTemperature OBJECT-TYPE
			SYNTAX INTEGER (0..65535)
			MAX-ACCESS read-only
			STATUS current
			DESCRIPTION
				"Current temperature of laser in degrees C."
			::= { sleAdvaOpticalEntry 11 }

		
		-- 1.3.6.1.4.1.6296.101.4.9.2
		sleAdvaOpticalControl OBJECT IDENTIFIER ::= { sleAdvaOptical 2 }

		
		-- 1.3.6.1.4.1.6296.101.4.9.2.1
		sleAdvaOpticalControlRequest OBJECT-TYPE
			SYNTAX INTEGER { setAdvaOpticalAlarm(1) }
			MAX-ACCESS read-write
			STATUS current
			DESCRIPTION
				"Description."
			::= { sleAdvaOpticalControl 1 }

		
		-- 1.3.6.1.4.1.6296.101.4.9.2.2
		sleAdvaOpticalControlStatus OBJECT-TYPE
			SYNTAX SleControlStatusType
			MAX-ACCESS read-only
			STATUS current
			DESCRIPTION
				"Description."
			::= { sleAdvaOpticalControl 2 }

		
		-- 1.3.6.1.4.1.6296.101.4.9.2.3
		sleAdvaOpticalControlTimer OBJECT-TYPE
			SYNTAX Gauge32
			MAX-ACCESS read-write
			STATUS current
			DESCRIPTION
				"Description."
			::= { sleAdvaOpticalControl 3 }

		
		-- 1.3.6.1.4.1.6296.101.4.9.2.4
		sleAdvaOpticalControlTimeStamp OBJECT-TYPE
			SYNTAX TimeTicks
			MAX-ACCESS read-write
			STATUS current
			DESCRIPTION
				"Description."
			::= { sleAdvaOpticalControl 4 }

		
		-- 1.3.6.1.4.1.6296.101.4.9.2.5
		sleAdvaOpticalControlReqResult OBJECT-TYPE
			SYNTAX SleControlRequestResultType
			MAX-ACCESS read-write
			STATUS current
			DESCRIPTION
				"Description."
			::= { sleAdvaOpticalControl 5 }

		
		-- 1.3.6.1.4.1.6296.101.4.9.2.6
		sleAdvaOpticalControlPortIndex OBJECT-TYPE
			SYNTAX INTEGER (1..255)
			MAX-ACCESS read-write
			STATUS current
			DESCRIPTION
				"Description."
			::= { sleAdvaOpticalControl 6 }

		
		-- 1.3.6.1.4.1.6296.101.4.9.2.7
		sleAdvaOpticalControlRemInstance OBJECT-TYPE
			SYNTAX INTEGER (1..3)
			MAX-ACCESS read-write
			STATUS current
			DESCRIPTION
				"Description."
			::= { sleAdvaOpticalControl 7 }

		
		-- 1.3.6.1.4.1.6296.101.4.9.2.8
		sleAdvaOpticalControlThresholdLevel OBJECT-TYPE
			SYNTAX INTEGER (0..65535)
			MAX-ACCESS read-write
			STATUS current
			DESCRIPTION
				"Description."
			::= { sleAdvaOpticalControl 8 }

		
		-- 1.3.6.1.4.1.6296.101.4.9.3
		sleAdvaOpticalNotification OBJECT IDENTIFIER ::= { sleAdvaOptical 3 }

		
		-- 1.3.6.1.4.1.6296.101.4.9.3.1
		sleAdvaOpticalAlarmChanged NOTIFICATION-TYPE
			OBJECTS { sleAdvaOpticalControlRequest, sleAdvaOpticalControlReqResult, sleAdvaOpticalControlTimeStamp, sleAdvaOpticalThresholdLevel }
			STATUS current
			DESCRIPTION 
				"Description."
			::= { sleAdvaOpticalNotification 1 }

		
		-- 1.3.6.1.4.1.6296.101.4.10
		sleAdvaOam OBJECT IDENTIFIER ::= { sleFaultMgmt 10 }

		
		-- 1.3.6.1.4.1.6296.101.4.10.1
		sleAdvaOamTable OBJECT-TYPE
			SYNTAX SEQUENCE OF SleAdvaOamEntry
			MAX-ACCESS not-accessible
			STATUS current
			DESCRIPTION
				"Description."
			::= { sleAdvaOam 1 }

		
		-- 1.3.6.1.4.1.6296.101.4.10.1.1
		sleAdvaOamEntry OBJECT-TYPE
			SYNTAX SleAdvaOamEntry
			MAX-ACCESS not-accessible
			STATUS current
			DESCRIPTION
				"Description."
			INDEX { sleOamPortIndex, sleAdvaRemInstance }
			::= { sleAdvaOamTable 1 }

		
		SleAdvaOamEntry ::=
			SEQUENCE { 
				sleAdvaAdminStatus
					INTEGER,
				sleAdvaMode
					INTEGER,
				sleAdvaRemMACAddress
					OCTET STRING,
				sleAdvaRemConfig
					BITS,
				sleAdvaRemPduConfig
					INTEGER,
				sleAdvaLocFlags
					BITS,
				sleAdvaRemFlags
					BITS,
				sleAdvaRemState
					BITS,
				sleAdvaRemVendorOUI
					INTEGER,
				sleAdvaRemDeviceNumber
					INTEGER,
				sleAdvaRemVendorVersion
					INTEGER,
				sleAdvaLocErrSymbolPeriodEventConfig
					INTEGER,
				sleAdvaLocErrFrameEventConfig
					INTEGER,
				sleAdvaLocErrFramePeriodEventConfig
					INTEGER,
				sleAdvaLocErrFrameSecsSummaryEventConfig
					INTEGER,
				sleAdvaPDUsTx
					Integer32,
				sleAdvaPDUsRx
					Integer32,
				sleAdvaUnsupportedCodesRx
					Integer32,
				sleAdvaInfoPDUsTx
					Integer32,
				sleAdvaInfoPDUsRx
					Integer32,
				sleAdvaEventNotificationPDUsTx
					Integer32,
				sleAdvaUniqueEventNotificationPDUsTx
					Integer32,
				sleAdvaDupEventNotificationPDUsTx
					Integer32,
				sleAdvaLoopbackControlPDUsTx
					Integer32,
				sleAdvaLoopbackControlPDUsRx
					Integer32,
				sleAdvaVariableRequestPDUsTx
					Integer32,
				sleAdvaVariableRequestPDUsRx
					Integer32,
				sleAdvaVariableResponsePDUsTx
					Integer32,
				sleAdvaVariableResponsePDUsRx
					Integer32,
				sleAdvaVendorPDUsTx
					Integer32,
				sleAdvaVendorPDUsRx
					Integer32,
				sleAdvaRemFramesLostDuetoOAMErr
					Integer32,
				sleAdvaLocErrSymbolPeriodEvent
					Integer32,
				sleAdvaLocErrFrameSecsEvent
					Integer32,
				sleAdvaLocErrFramePeriodEvent
					Integer32,
				sleAdvaLocErrFrameSecsSummaryEvent
					Integer32,
				sleAdvaRemErrSymbolPeriodEvent
					Integer32,
				sleAdvaRemErrFrameSecsEvent
					Integer32,
				sleAdvaRemoteErrorFramePeriodEvent
					Integer32,
				sleAdvaRemoteErrorFrameSecsSummaryEvent
					Integer32
			 }

		-- 1.3.6.1.4.1.6296.101.4.10.1.1.1
		sleAdvaAdminStatus OBJECT-TYPE
			SYNTAX INTEGER
				{
				disable(0),
				enable(1)
				}
			MAX-ACCESS read-only
			STATUS current
			DESCRIPTION
				"OAM package - aOAMAdminState (Configuration)Whether 
				the OAM sublayer is enabled or disabled."
			::= { sleAdvaOamEntry 1 }

		
		-- 1.3.6.1.4.1.6296.101.4.10.1.1.2
		sleAdvaMode OBJECT-TYPE
			SYNTAX INTEGER
				{
				passive(0),
				active(1)
				}
			MAX-ACCESS read-only
			STATUS current
			DESCRIPTION
				"OAM package - aOAMMode. (Configuration)Mode of the OAM client"
			::= { sleAdvaOamEntry 2 }

		
		-- 1.3.6.1.4.1.6296.101.4.10.1.1.3
		sleAdvaRemMACAddress OBJECT-TYPE
			SYNTAX OCTET STRING
			MAX-ACCESS read-only
			STATUS current
			DESCRIPTION
				"OAM package - aOAMRemoteMACAddress. (Configuration)"
			::= { sleAdvaOamEntry 3 }

		
		-- 1.3.6.1.4.1.6296.101.4.10.1.1.4
		sleAdvaRemConfig OBJECT-TYPE
			SYNTAX BITS
				{
				unidirSupport(0),
				loopbackSupport(1),
				linkEvents(2),
				variableRetrieval(3),
				orgSpecific(4),
				orgSpecificEvents(5),
				orgSpecificInfoTLV(6)
				}
			MAX-ACCESS read-only
			STATUS current
			DESCRIPTION
				"OAM package - aOAMRemoteConfiguration. (Configuration)Bit-mask 
				corresponding to the OAM configuration field:"
			::= { sleAdvaOamEntry 4 }

		
		-- 1.3.6.1.4.1.6296.101.4.10.1.1.5
		sleAdvaRemPduConfig OBJECT-TYPE
			SYNTAX INTEGER (0..65535)
			MAX-ACCESS read-only
			STATUS current
			DESCRIPTION
				"OAM package - aOAMRemotePDUConfiguration. (Configuration)The maximum 
				PDU size supported"
			::= { sleAdvaOamEntry 5 }

		
		-- 1.3.6.1.4.1.6296.101.4.10.1.1.6
		sleAdvaLocFlags OBJECT-TYPE
			SYNTAX BITS
				{
				linkFault(0),
				dyingGasp(1),
				criticalEvent(2),
				localStableDiscovering(3),
				localStable(4),
				remoteStableDiscovering(5),
				remoteStable(6)
				}
			MAX-ACCESS read-only
			STATUS current
			DESCRIPTION
				"OAM package - aOAMLocalFlags. (Configuration)Bit-mask corresponding 
				to the OAM flag field transmitted:"
			::= { sleAdvaOamEntry 6 }

		
		-- 1.3.6.1.4.1.6296.101.4.10.1.1.7
		sleAdvaRemFlags OBJECT-TYPE
			SYNTAX BITS
				{
				linkFault(0),
				dyingGasp(1),
				criticalEvent(2),
				localStableDiscovering(3),
				localStable(4),
				remoteStableDiscovering(5),
				remoteStable(6)
				}
			MAX-ACCESS read-only
			STATUS current
			DESCRIPTION
				"OAM package - aOAMRemoteFlags. (Configuration)Bit-mask corresponding 
				to the OAM flag field received"
			::= { sleAdvaOamEntry 7 }

		
		-- 1.3.6.1.4.1.6296.101.4.10.1.1.8
		sleAdvaRemState OBJECT-TYPE
			SYNTAX BITS
				{
				reserved(0),
				parserAction1(1),
				parserAction2(2),
				muxAction(3)
				}
			MAX-ACCESS read-only
			STATUS current
			DESCRIPTION
				"OAM package - aOAMRemoteState. (Configuration)Bit-mask corresponding 
				to the OAM State field received"
			::= { sleAdvaOamEntry 8 }

		
		-- 1.3.6.1.4.1.6296.101.4.10.1.1.9
		sleAdvaRemVendorOUI OBJECT-TYPE
			SYNTAX INTEGER (0..65535)
			MAX-ACCESS read-only
			STATUS current
			DESCRIPTION
				"OAM package - aOAMRemoteVendorOUI. (Configuration)The value of 
				the OUI from the remote end of the OAM link."
			::= { sleAdvaOamEntry 9 }

		
		-- 1.3.6.1.4.1.6296.101.4.10.1.1.10
		sleAdvaRemDeviceNumber OBJECT-TYPE
			SYNTAX INTEGER (0..65535)
			MAX-ACCESS read-only
			STATUS current
			DESCRIPTION
				"OAM package - aOAMRemoteVendorIdDeviceNumber. (Configuration)
				The value of the Device Identifier  from the remote end of the OAM link."
			::= { sleAdvaOamEntry 10 }

		
		-- 1.3.6.1.4.1.6296.101.4.10.1.1.11
		sleAdvaRemVendorVersion OBJECT-TYPE
			SYNTAX INTEGER (0..65535)
			MAX-ACCESS read-only
			STATUS current
			DESCRIPTION
				"OAM package - aOAMRemoteVendorIdVersion. (Configuration)
				The value of the Version Identifier from the remote end of the OAM link."
			::= { sleAdvaOamEntry 11 }

		
		-- 1.3.6.1.4.1.6296.101.4.10.1.1.12
		sleAdvaLocErrSymbolPeriodEventConfig OBJECT-TYPE
			SYNTAX INTEGER (0..65535)
			MAX-ACCESS read-only
			STATUS current
			DESCRIPTION
				"OAM package - aOAMLocalErrSymPeriodConfig. (Configuration) 
				Configuration for the event indicating the duration of 
				the period and the number of symbols that must be exceeded."
			::= { sleAdvaOamEntry 12 }

		
		-- 1.3.6.1.4.1.6296.101.4.10.1.1.13
		sleAdvaLocErrFrameEventConfig OBJECT-TYPE
			SYNTAX INTEGER (0..65535)
			MAX-ACCESS read-only
			STATUS current
			DESCRIPTION
				"OAM package - aOAMLocalErrFrameConfig. (Configuration)
				Configuration for the event indicating the duration and 
				the number of errored frames that must be exceeded."
			::= { sleAdvaOamEntry 13 }

		
		-- 1.3.6.1.4.1.6296.101.4.10.1.1.14
		sleAdvaLocErrFramePeriodEventConfig OBJECT-TYPE
			SYNTAX INTEGER (0..65535)
			MAX-ACCESS read-only
			STATUS current
			DESCRIPTION
				"OAM package - aOAMLocalErrFramePeriodConfig. (Configuration)
				Configuration for the event indicating the durationin terms of 
				minFrameSize that can be transmitted and that number of errored 
				frames that must be exceeded."
			::= { sleAdvaOamEntry 14 }

		
		-- 1.3.6.1.4.1.6296.101.4.10.1.1.15
		sleAdvaLocErrFrameSecsSummaryEventConfig OBJECT-TYPE
			SYNTAX INTEGER (0..65535)
			MAX-ACCESS read-only
			STATUS current
			DESCRIPTION
				"OAM package - aOAMLocalErrFrameSecsSummaryConfig. (Configuration)
				Configuration for the evert indicating duration window and number 
				of errored frame seconds in that duration that must be exceeded."
			::= { sleAdvaOamEntry 15 }

		
		-- 1.3.6.1.4.1.6296.101.4.10.1.1.16
		sleAdvaPDUsTx OBJECT-TYPE
			SYNTAX Integer32
			MAX-ACCESS read-only
			STATUS current
			DESCRIPTION
				"OAM package - aOAMPDUTx. (PDU Performance)Non-resettable, 
				wrapping count of OAM PDUs transmitted since OAM enabled."
			::= { sleAdvaOamEntry 16 }

		
		-- 1.3.6.1.4.1.6296.101.4.10.1.1.17
		sleAdvaPDUsRx OBJECT-TYPE
			SYNTAX Integer32
			MAX-ACCESS read-only
			STATUS current
			DESCRIPTION
				"OAM package - aOAMPDURx. (PDU Performance)Non-resettable, 
				wrapping count of OAM PDUs received since OAM enabled."
			::= { sleAdvaOamEntry 17 }

		
		-- 1.3.6.1.4.1.6296.101.4.10.1.1.18
		sleAdvaUnsupportedCodesRx OBJECT-TYPE
			SYNTAX Integer32
			MAX-ACCESS read-only
			STATUS current
			DESCRIPTION
				"OAM package - aOAMUnsupportedCodesRx. (PDU Performance)Non-resettable, 
				wrapping count of OAM PDUs received that are not supported by device 
				since OAM enabled."
			::= { sleAdvaOamEntry 18 }

		
		-- 1.3.6.1.4.1.6296.101.4.10.1.1.19
		sleAdvaInfoPDUsTx OBJECT-TYPE
			SYNTAX Integer32
			MAX-ACCESS read-only
			STATUS current
			DESCRIPTION
				"OAM package - aOAMInformationTx. (PDU Performance)Non-resettable, 
				wrapping count of OAM Info PDUs transmitted since OAM enabled."
			::= { sleAdvaOamEntry 19 }

		
		-- 1.3.6.1.4.1.6296.101.4.10.1.1.20
		sleAdvaInfoPDUsRx OBJECT-TYPE
			SYNTAX Integer32
			MAX-ACCESS read-only
			STATUS current
			DESCRIPTION
				"OAM package - aOAMInformationRx. (PDU Performance)Non-resettable, 
				wrapping count of OAM Info PDUs received since OAM enabled."
			::= { sleAdvaOamEntry 20 }

		
		-- 1.3.6.1.4.1.6296.101.4.10.1.1.21
		sleAdvaEventNotificationPDUsTx OBJECT-TYPE
			SYNTAX Integer32
			MAX-ACCESS read-only
			STATUS current
			DESCRIPTION
				"OAM package - aOAMEventNotificationTx. (PDU Performance)Non-resettable, 
				wrapping count of OAM Event PDUs transmitted since OAM enabled."
			::= { sleAdvaOamEntry 21 }

		
		-- 1.3.6.1.4.1.6296.101.4.10.1.1.22
		sleAdvaUniqueEventNotificationPDUsTx OBJECT-TYPE
			SYNTAX Integer32
			MAX-ACCESS read-only
			STATUS current
			DESCRIPTION
				"OAM package - aOAMUniqueEventNotificationTx. (PDU Performance)
				Non-resettable, wrapping count of OAM Event PDUs received with 
				a different sequence number than previously since OAM enabled."
			::= { sleAdvaOamEntry 22 }

		
		-- 1.3.6.1.4.1.6296.101.4.10.1.1.23
		sleAdvaDupEventNotificationPDUsTx OBJECT-TYPE
			SYNTAX Integer32
			MAX-ACCESS read-only
			STATUS current
			DESCRIPTION
				"OAM package - aOAMDuplicateEventNotificationTx. (PDU Performance)
				Non-resettable, wrapping count of OAM Event PDUs received with the 
				same sequence number as previously since OAM enabled."
			::= { sleAdvaOamEntry 23 }

		
		-- 1.3.6.1.4.1.6296.101.4.10.1.1.24
		sleAdvaLoopbackControlPDUsTx OBJECT-TYPE
			SYNTAX Integer32
			MAX-ACCESS read-only
			STATUS current
			DESCRIPTION
				"OAM package - aOAMLoopbackControlTx. (PDU Performance)
				Non-resettable, wrapping count of OAM Loopback Control PDUs 
				transmitted since OAM enabled."
			::= { sleAdvaOamEntry 24 }

		
		-- 1.3.6.1.4.1.6296.101.4.10.1.1.25
		sleAdvaLoopbackControlPDUsRx OBJECT-TYPE
			SYNTAX Integer32
			MAX-ACCESS read-only
			STATUS current
			DESCRIPTION
				"OAM package - aOAMLoopbackControlRx. (PDU Performance)
				Non-resettable, wrapping count of OAM Loopback Control PDUs 
				received since OAM enabled."
			::= { sleAdvaOamEntry 25 }

		
		-- 1.3.6.1.4.1.6296.101.4.10.1.1.26
		sleAdvaVariableRequestPDUsTx OBJECT-TYPE
			SYNTAX Integer32
			MAX-ACCESS read-only
			STATUS current
			DESCRIPTION
				"OAM package - aOAMVariableRequestTx. (PDU Performance)
				Non-resettable, wrapping count of OAM Variable Request PDUs 
				transmitted since OAM enabled."
			::= { sleAdvaOamEntry 26 }

		
		-- 1.3.6.1.4.1.6296.101.4.10.1.1.27
		sleAdvaVariableRequestPDUsRx OBJECT-TYPE
			SYNTAX Integer32
			MAX-ACCESS read-only
			STATUS current
			DESCRIPTION
				"OAM package - aOAMVariableRequestRx. (PDU Performance)
				Non-resettable, wrapping count of OAM Variable Request PDUs 
				received since OAM enabled."
			::= { sleAdvaOamEntry 27 }

		
		-- 1.3.6.1.4.1.6296.101.4.10.1.1.28
		sleAdvaVariableResponsePDUsTx OBJECT-TYPE
			SYNTAX Integer32
			MAX-ACCESS read-only
			STATUS current
			DESCRIPTION
				"OAM package - aOAMVariableResponseTx. (PDU Performance)
				Non-resettable, wrapping count of OAM Variable Response PDUs 
				transmitted since OAM enabled."
			::= { sleAdvaOamEntry 28 }

		
		-- 1.3.6.1.4.1.6296.101.4.10.1.1.29
		sleAdvaVariableResponsePDUsRx OBJECT-TYPE
			SYNTAX Integer32
			MAX-ACCESS read-only
			STATUS current
			DESCRIPTION
				"OAM package - aOAMVariableResponseRx. (PDU Performance)
				Non-resettable, wrapping count of OAM Variable Response PDUs 
				received since OAM enabled"
			::= { sleAdvaOamEntry 29 }

		
		-- 1.3.6.1.4.1.6296.101.4.10.1.1.30
		sleAdvaVendorPDUsTx OBJECT-TYPE
			SYNTAX Integer32
			MAX-ACCESS read-only
			STATUS current
			DESCRIPTION
				"OAM package - aOAMOrganizationSpecificTx . (PDU Performance)
				Non-resettable, wrapping count of OAM Vendor PDUs transmitted 
				since OAM enabled."
			::= { sleAdvaOamEntry 30 }

		
		-- 1.3.6.1.4.1.6296.101.4.10.1.1.31
		sleAdvaVendorPDUsRx OBJECT-TYPE
			SYNTAX Integer32
			MAX-ACCESS read-only
			STATUS current
			DESCRIPTION
				"OAM package - aOAMOrganizationSpecificRx. (PDU Performance)"
			::= { sleAdvaOamEntry 31 }

		
		-- 1.3.6.1.4.1.6296.101.4.10.1.1.32
		sleAdvaRemFramesLostDuetoOAMErr OBJECT-TYPE
			SYNTAX Integer32
			MAX-ACCESS read-only
			STATUS current
			DESCRIPTION
				"OAM package - aFramesLostDueToOAMError. (PDU Performance)
				Non-resettable, wrapping count of frames that would have been 
				transmitted but for an OAM sublayer error."
			::= { sleAdvaOamEntry 32 }

		
		-- 1.3.6.1.4.1.6296.101.4.10.1.1.33
		sleAdvaLocErrSymbolPeriodEvent OBJECT-TYPE
			SYNTAX Integer32
			MAX-ACCESS read-only
			STATUS current
			DESCRIPTION
				"The most recently transmitted event of this type. (Error)"
			::= { sleAdvaOamEntry 33 }

		
		-- 1.3.6.1.4.1.6296.101.4.10.1.1.34
		sleAdvaLocErrFrameSecsEvent OBJECT-TYPE
			SYNTAX Integer32
			MAX-ACCESS read-only
			STATUS current
			DESCRIPTION
				"The most recently transmitted event of this type. (Error)"
			::= { sleAdvaOamEntry 34 }

		
		-- 1.3.6.1.4.1.6296.101.4.10.1.1.35
		sleAdvaLocErrFramePeriodEvent OBJECT-TYPE
			SYNTAX Integer32
			MAX-ACCESS read-only
			STATUS current
			DESCRIPTION
				"The most recently transmitted event of this type. (Error)"
			::= { sleAdvaOamEntry 35 }

		
		-- 1.3.6.1.4.1.6296.101.4.10.1.1.36
		sleAdvaLocErrFrameSecsSummaryEvent OBJECT-TYPE
			SYNTAX Integer32
			MAX-ACCESS read-only
			STATUS current
			DESCRIPTION
				"The most recently transmitted event of this type. (Error)"
			::= { sleAdvaOamEntry 36 }

		
		-- 1.3.6.1.4.1.6296.101.4.10.1.1.37
		sleAdvaRemErrSymbolPeriodEvent OBJECT-TYPE
			SYNTAX Integer32
			MAX-ACCESS read-only
			STATUS current
			DESCRIPTION
				"The most recently received event of this type. (Error)"
			::= { sleAdvaOamEntry 37 }

		
		-- 1.3.6.1.4.1.6296.101.4.10.1.1.38
		sleAdvaRemErrFrameSecsEvent OBJECT-TYPE
			SYNTAX Integer32
			MAX-ACCESS read-only
			STATUS current
			DESCRIPTION
				"The most recently received event of this type. (Error)"
			::= { sleAdvaOamEntry 38 }

		
		-- 1.3.6.1.4.1.6296.101.4.10.1.1.39
		sleAdvaRemoteErrorFramePeriodEvent OBJECT-TYPE
			SYNTAX Integer32
			MAX-ACCESS read-only
			STATUS current
			DESCRIPTION
				"The most recently received event of this type. (Error)"
			::= { sleAdvaOamEntry 39 }

		
		-- 1.3.6.1.4.1.6296.101.4.10.1.1.40
		sleAdvaRemoteErrorFrameSecsSummaryEvent OBJECT-TYPE
			SYNTAX Integer32
			MAX-ACCESS read-only
			STATUS current
			DESCRIPTION
				"The most recently received event of this type. (Error)"
			::= { sleAdvaOamEntry 40 }

		
		-- 1.3.6.1.4.1.6296.101.4.10.2
		sleAdvaOamControl OBJECT IDENTIFIER ::= { sleAdvaOam 2 }

		
		-- 1.3.6.1.4.1.6296.101.4.10.2.1
		sleAdvaOamControlRequest OBJECT-TYPE
			SYNTAX INTEGER { setAdvaOamProfile(1) }
			MAX-ACCESS read-write
			STATUS current
			DESCRIPTION
				"Description."
			::= { sleAdvaOamControl 1 }

		
		-- 1.3.6.1.4.1.6296.101.4.10.2.2
		sleAdvaOamControlStatus OBJECT-TYPE
			SYNTAX SleControlStatusType
			MAX-ACCESS read-only
			STATUS current
			DESCRIPTION
				"Description."
			::= { sleAdvaOamControl 2 }

		
		-- 1.3.6.1.4.1.6296.101.4.10.2.3
		sleAdvaOamControlTimer OBJECT-TYPE
			SYNTAX Gauge32
			MAX-ACCESS read-write
			STATUS current
			DESCRIPTION
				"Description."
			::= { sleAdvaOamControl 3 }

		
		-- 1.3.6.1.4.1.6296.101.4.10.2.4
		sleAdvaOamControlTimeStamp OBJECT-TYPE
			SYNTAX TimeTicks
			MAX-ACCESS read-write
			STATUS current
			DESCRIPTION
				"Description."
			::= { sleAdvaOamControl 4 }

		
		-- 1.3.6.1.4.1.6296.101.4.10.2.5
		sleAdvaOamControlReqResult OBJECT-TYPE
			SYNTAX SleControlRequestResultType
			MAX-ACCESS read-write
			STATUS current
			DESCRIPTION
				"Description."
			::= { sleAdvaOamControl 5 }

		
		-- 1.3.6.1.4.1.6296.101.4.10.2.6
		sleAdvaOamControlPortIndex OBJECT-TYPE
			SYNTAX INTEGER (1..255)
			MAX-ACCESS read-write
			STATUS current
			DESCRIPTION
				"Description."
			::= { sleAdvaOamControl 6 }

		
		-- 1.3.6.1.4.1.6296.101.4.10.2.7
		sleAdvaOamControlRemInstance OBJECT-TYPE
			SYNTAX INTEGER (1..2)
			MAX-ACCESS read-write
			STATUS current
			DESCRIPTION
				"Description."
			::= { sleAdvaOamControl 7 }

		
		-- 1.3.6.1.4.1.6296.101.4.10.2.8
		sleAdvaOamControlAdminStatus OBJECT-TYPE
			SYNTAX INTEGER
				{
				disable(0),
				enable(1)
				}
			MAX-ACCESS read-write
			STATUS current
			DESCRIPTION
				"Description."
			::= { sleAdvaOamControl 8 }

		
		-- 1.3.6.1.4.1.6296.101.4.10.2.9
		sleAdvaOamControlMode OBJECT-TYPE
			SYNTAX INTEGER
				{
				passive(0),
				active(1)
				}
			MAX-ACCESS read-write
			STATUS current
			DESCRIPTION
				"Description."
			::= { sleAdvaOamControl 9 }

		
		-- 1.3.6.1.4.1.6296.101.4.10.3
		sleAdvaOamNotification OBJECT IDENTIFIER ::= { sleAdvaOam 3 }

		
		-- 1.3.6.1.4.1.6296.101.4.10.3.1
		setAdvaOamProfileChanged NOTIFICATION-TYPE
			OBJECTS { sleAdvaOamControlRequest, sleAdvaOamControlReqResult, sleAdvaOamControlTimeStamp, sleAdvaAdminStatus, sleAdvaMode
				 }
			STATUS current
			DESCRIPTION 
				"Description."
			::= { sleAdvaOamNotification 1 }

		
		-- 1.3.6.1.4.1.6296.101.4.11
		sleFaultMgmtGroup OBJECT-GROUP
			OBJECTS { sleFaultDefaultSeverity, sleFaultCriteriaSeverity, sleFaultNotifiyActivity, sleFaultControlRequest, sleFaultControlStatus, 
				sleFaultControlTimer, sleFaultControlTimeStamp, sleFaultControlReqResult, sleFaultControlDefaultSeverity, sleFaultControlCriteriaSeverity, 
				sleFaultControlNotifiyActivity, sleAlarmSeverityIndex, sleAlarmSeverityValue, sleAlarmSeverityControlRequest, sleAlarmSeverityControlStatus, 
				sleAlarmSeverityControlTimer, sleAlarmSeverityControlTimeStamp, sleAlarmSeverityControlReqResult, sleAlarmSeverityControlIndex, sleAlarmSeverityControlValue, 
				sleAlarmSpecificCode, sleAlarmReportingSourceType, sleAlarmReportingSource, sleAlarmSpecificSeverity, sleAlarmSpecificProblem, 
				sleAlarmSpecificProblemText, sleAlarmTimeAndDate, sleAlarmHistoryIndex, sleAlarmHistorySpecific, sleAlarmHistorySeverity, 
				sleAlarmHistoryText, sleAlarmHistoryTime, sleAlarmHistoryControlRequest, sleAlarmHistoryControlStatus, sleAlarmHistoryControlTimer, 
				sleAlarmHistoryControlTimeStamp, sleAlarmHistoryControlReqResult, sleOamPortIndex, sleOamMuxAction, sleOamParAction, 
				sleOamAdminState, sleOamMode, sleOamUnidirectionMode, sleOamFunctionsSupported, sleOamPeerStatus, 
				sleOamPeerMacAddress, sleOamPeerMode, sleOamPeerFunctionsSupported, sleOamRemLoopback, sleOamControlRequest, 
				sleOamControlStatus, sleOamControlTimer, sleOamControlTimeStamp, sleOamControlReqResult, sleOamControlIndex, 
				sleOamControlPortAdminState, sleOamControlPortMode, sleOamControlPortUnidirectionMode, sleOamControlPortRemLoopback, sleAdvaFSPOperationMode, 
				sleAdvaActiveNetworkInterface, sleAdvaForceNetworkInterface, sleAdvaReportingInterval, sleAdvaNEMIFitted, sleAdvaForceReset, 
				sleAdvaManagerAddress, sleAdvaMinRailVoltageThreshold, sleAdvaMaxRailVoltageThreshold, sleAdvaTemperatureThreshold, sleAdvaPartNumber, 
				sleAdvaSerialNumber, sleAdvaFirmwareVersion, sleAdvaFPGAVersion, sleAdvaHardwareRevision, sleAdvaCLEICode, 
				sleAdvaTemperature, sleAdvaRailVoltage, sleAdvaPSUStates, sleAdvaPSUType, sleAdvaFansFitted, 
				sleAdvaFanState, sleAdvaTransmitMode, sleAdvaSystemControlRequest, sleAdvaSystemControlStatus, sleAdvaSystemControlTimer, 
				sleAdvaSystemControlTimeStamp, sleAdvaSystemControlReqResult, sleAdvaSystemControlPortIndex, sleAdvaSystemControlFSPOperationMode, sleAdvaSystemControlForceNetworkInterface, 
				sleAdvaSystemControlReportingInterval, sleAdvaSystemControlForceReset, sleAdvaSystemControlMinRailVoltageThreshold, sleAdvaSystemControlMaxRailVoltageThreshold, sleAdvaSystemControlTemperatureThreshold, 
				sleAdvaSystemControlTransmitMode, sleAdvaRemInstance, sleAdvaOperationalStatus, sleAdvaLineSpeed, sleAdvaMACAddress, 
				sleAdvaConnectorType, sleAdvaAutonegiotation, sleAdvaLinkLossForwarding, sleAdvaAdminState, sleAdvaRemoteInterfaceIndex, 
				sleAdvaUserDefinedString, sleAdvaRemoteSignalling, sleAdvaConfiguration, sleAdvaLocalTechnologyAbility, sleAdvaAdvertisedTechnologyAbility, 
				sleAdvaReceivedTechnologyAbility, sleAdvaLocalSectorAbility, sleAdvaAdvertisedSectorAbility, sleAdvaReceivedSectorAbility, sleAdvaDuplexCapabilities, 
				sleAdvaPHYType, sleAdvaPHYTypeList, sleAdvaMIIDetect, sleAdvaPHYState, sleAdvaGoodFramesTransmitted, 
				sleAdvaSingleCollisionFrames, sleAdvaMultipleCollisionFrames, sleAdvaGoodFramesReceived, sleAdvaFCSErrors, sleAdvaAlignmentErrors, 
				sleAdvaFramesTooLong, sleAdvaBytesTransmitted, sleAdvaBytesReceived, sleAdvaSymbolErrors, sleAdvaGeneralControlRequest, 
				sleAdvaGeneralControlStatus, sleAdvaGeneralControlTimer, sleAdvaGeneralControlTimeStamp, sleAdvaGeneralControlReqResult, sleAdvaGeneralControlPortIndex, 
				sleAdvaGeneralControlRemInstance, sleAdvaGeneralControlLineSpeed, sleAdvaGeneralControlAutonegiotation, sleAdvaGeneralControlLinkLossForwarding, sleAdvaGeneralControlUserDefinedString, 
				sleAdvaGeneralControlAdvertisedTechnologyAbility, sleAdvaGeneralControlAdvertisedSectorAbility, sleAdvaModuleType, sleAdvaModulePartNumber, sleAdvaModuleSerialNumber, 
				sleAdvaModuleFirmwareVersion, sleAdvaModuleSoftwareVersion, sleAdvaModuleHardwareRevision, sleAdvaModuleCLEICode, sleAdvaOpticalThresholdLevel, 
				sleAdvaLinkLength1, sleAdvaLinkLength2, sleAdvaLinkLength3, sleAdvaLinkLength4, sleAdvaLinkLengthCu, 
				sleAdvaWaveLength, sleAdvaLaserBias, sleAdvaTransmitPower, sleAdvaReceivePower, sleAdvaLaserTxTemperature, 
				sleAdvaOpticalControlRequest, sleAdvaOpticalControlStatus, sleAdvaOpticalControlTimer, sleAdvaOpticalControlTimeStamp, sleAdvaOpticalControlReqResult, 
				sleAdvaOpticalControlPortIndex, sleAdvaOpticalControlRemInstance, sleAdvaOpticalControlThresholdLevel, sleAdvaAdminStatus, sleAdvaMode, 
				sleAdvaRemMACAddress, sleAdvaRemConfig, sleAdvaRemPduConfig, sleAdvaLocFlags, sleAdvaRemFlags, 
				sleAdvaRemState, sleAdvaRemVendorOUI, sleAdvaRemDeviceNumber, sleAdvaRemVendorVersion, sleAdvaLocErrSymbolPeriodEventConfig, 
				sleAdvaLocErrFrameEventConfig, sleAdvaLocErrFramePeriodEventConfig, sleAdvaLocErrFrameSecsSummaryEventConfig, sleAdvaPDUsTx, sleAdvaPDUsRx, 
				sleAdvaUnsupportedCodesRx, sleAdvaInfoPDUsTx, sleAdvaInfoPDUsRx, sleAdvaEventNotificationPDUsTx, sleAdvaUniqueEventNotificationPDUsTx, 
				sleAdvaDupEventNotificationPDUsTx, sleAdvaLoopbackControlPDUsTx, sleAdvaLoopbackControlPDUsRx, sleAdvaVariableRequestPDUsTx, sleAdvaVariableRequestPDUsRx, 
				sleAdvaVariableResponsePDUsTx, sleAdvaVariableResponsePDUsRx, sleAdvaVendorPDUsTx, sleAdvaVendorPDUsRx, sleAdvaRemFramesLostDuetoOAMErr, 
				sleAdvaLocErrSymbolPeriodEvent, sleAdvaLocErrFrameSecsEvent, sleAdvaLocErrFramePeriodEvent, sleAdvaLocErrFrameSecsSummaryEvent, sleAdvaRemErrSymbolPeriodEvent, 
				sleAdvaRemErrFrameSecsEvent, sleAdvaRemoteErrorFramePeriodEvent, sleAdvaRemoteErrorFrameSecsSummaryEvent, sleAdvaOamControlRequest, sleAdvaOamControlStatus, 
				sleAdvaOamControlTimer, sleAdvaOamControlTimeStamp, sleAdvaOamControlReqResult, sleAdvaOamControlPortIndex, sleAdvaOamControlRemInstance, 
				sleAdvaOamControlAdminStatus, sleAlarmHistorySeqNum, sleAlarmSpecificSeqNum, sleFaultNextSeqNum, sleAdvaOamControlMode, 
				sleAlarmReportControlRequest, sleAlarmReportControlStatus, sleAlarmReportControlTimer, sleAlarmReportControlTimeStamp, sleAlarmReportControlReqResult
				 }
			STATUS current
			DESCRIPTION 
				"Description."
			::= { sleFaultMgmt 11 }

		
		-- 1.3.6.1.4.1.6296.101.4.12
		sleFaultMgmtNotificationGroup NOTIFICATION-GROUP
			NOTIFICATIONS { sleAlarmDefaultSeverityChanged, sleAlarmDefaultCriteriaChanged, sleNotificationActivityChanged, sleAlarmSeveriityCreated, sleAlarmSeveriityDestroyed, 
				sleAlarmSeverityChanged, sleAlarmReportNotified, sleAlarmHistoryCleared, sleEfmOamPortProfileChanged, sleEfmOamPortRemLoopback, 
				sleAdvaSystemProfileChanged, sleAdvaAlarmProfileChanged, sleAdvaElectricalInterfaceChanged, sleAdvaGeneralProfileChanged, sleAdvaAutonegProfileChanged, 
				sleAdvaOpticalAlarmChanged, setAdvaOamProfileChanged, sleAlarmReportCleared }
			STATUS current
			DESCRIPTION 
				"Description."
			::= { sleFaultMgmt 12 }

		
	
	END

--
-- SLE-FAULTMGMT-MIB.my
--
