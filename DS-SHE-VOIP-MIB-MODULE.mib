--
-- she-voip-mib-module.mib
-- MIB generated by MG-SOFT Visual MIB Builder Version 6.0  Build 88
-- Wednesday, October 24, 2007 at 10:05:24
--

	DS-SHE-VOIP-MIB-MODULE DEFINITIONS ::= BEGIN
 
		IMPORTS
			she			
				FROM AN-MIB
			dsShe
				FROM DASAN-SMI							
			ifIndex			
				FROM IF-MIB			
			sheAlarmTimeAndDate, sheAlarmReportingSource, sheAlarmReportingSourceType, sheAlarmSeverity, SheAlarmSevProfileIndex			
				FROM DS-SHE-ALARMING-MIB			
			SheControlStatusType			
				FROM DS-SHE-TC-MIB			
			SnmpAdminString			
				FROM SNMP-FRAMEWORK-MIB			
			OBJECT-GROUP, MODULE-COMPLIANCE, NOTIFICATION-GROUP			
				FROM SNMPv2-CONF			
			TimeTicks, IpAddress, Unsigned32, Gauge32, Counter64, 
			OBJECT-TYPE, MODULE-IDENTITY, NOTIFICATION-TYPE			
				FROM SNMPv2-SMI			
			DisplayString, DateAndTime			
				FROM SNMPv2-TC;
	
	
		sheVoipMib MODULE-IDENTITY 
			LAST-UPDATED "200710241440Z"		-- October 24, 2007 at 14:40 GMT
			ORGANIZATION 
				"Nokia Siemens Networks"
			CONTACT-INFO 
				"Yang Xu
				Com CD/FN RDC BJ
				yang.xu@siemens.com
				+0086 58671204
				
				Gerd Barchmann
				COO BBA DSLAM RD SDE
				gerd.barchmann@nsn.com 
				+49 3834 555654
				
				Lin Tao
				SNLB FN RDC NA(BJ)
				lin.tao@siemens.com
				"
			DESCRIPTION 
				"This MIB contains all needed informations about VoIP and
				all supported she VoIP features."
			REVISION "200509071632Z"		-- September 07, 2005 at 16:32 GMT
			DESCRIPTION 
				"new she mib"
			REVISION "200605171632Z"		-- May 17, 2006 at 16:32 GMT
			DESCRIPTION 
				"change sheVoipMgConfigProfile to sheVoipH248MgConfigProfile
				remove sheVoipDigitMapEvents,commands ID in SheVoipControlRequestType rearranged
				modify sheVoipVoipVoiceCtpIpHostDataIndex to sheVoipVoipVoiceCtpIpHostProfileIndex 
				Type of sheVoipIpHostProfileDhcp changed to Unsigned32
				Type of sheVoipMgcConfigProfileIPAddress changed to IpAdress
				 More commments added in controlRequsts"
			REVISION "200605191632Z"		-- May 19, 2006 at 16:32 GMT
			DESCRIPTION 
				"Type of **profileNames changed to DisplayString.
				sheVoipVgwDmList added in sheVoipVgwTable
				command addVoipVgwDmMember and removeVoipVgwDmMember added in sheVoipVgwControlReq
				command modifySheVoipVoipVoiceCtpRtpUdpPorts added into sheVoipVoipVoiceCtpControlReq
				sheVoipVoipVoiceCtpH248RtpUdpPortBase added in sheVoipVoipVoiceCtpTable
				sheVoipVoipVoiceCtpControlRtpUdpPortBase added in sheVoipVoipVoiceCtpControl
				sheVoipRtpRtcpProfile table and control group changed to sheVoipRtcpProfile table and control group
				sheVoipRtcpProfilePortMin and sheVoipRtcpProfilePortMax removed from sheVoipRtcpProfileTable
				sheVoipMediaFaxProfileFax changed to sheVoipMediaFaxProfileFaxTypeUsed "
			REVISION "200605201632Z"		-- May 20, 2006 at 16:32 GMT
			DESCRIPTION 
				"default value of sheVoipH248MgConfigProfileHeartBeatTime changed from 16 to 200.
				default value of sheVoipH248MgConfigProfileMWD changed from 120 to 0 
				sheVoipIpHostProfileIpaddress changed to sheVoipIpHostProfileIpAddress
				sheVoipIpHostProfileSubnetmask --> sheVoipIpHostProfileSubnetMask"
			REVISION "200605221632Z"		-- May 22, 2006 at 16:32 GMT
			DESCRIPTION 
				"Modified based on comments of reviewers rename sheVoipmib as sheVoipMibModule
				size limitation (size(0.32)) added to syntax of all profileNames
				commands add/deleteVgwMember and add/deleteDmMember deleted.
				VgwMemberAddedTrap/DeletedTrap, DmMemberAddedTrap/DeletedTrap deleted.
				two attributes - sheVoipVgwControlMemberList and sheVoipVgwControlDmList
				added into command modifyVoipVgwConfig.
				More comments added to comments of sheVoipVgwDmList.
				Type of sheVoipIpHostProfileControlDhcp changed to SheVoipIpHostProfileUseDhcpType
				sheVoipDigitMapModifiedTrap, sheVoipDigitMapAddedTrap, sheVoipDigitMapDeletedTrap added
				size limitation added to sheVoipVoipVoiceCtpRtpUdpPortBase syntax
				Rename sheVoipDigitMap to sheVoipDigitMapProfile
				Default value of sheVoipVgwControlDmList changed from 0 to 1"
			REVISION "200608231414Z"		-- August 23, 2006 at 14:14 GMT
			DESCRIPTION 
				"performance groups added"
			REVISION "200610191415Z"		-- October 19, 2006 at 14:15 GMT
			DESCRIPTION 
				"parameters modified for optimization of mib
							sheVoipMediaJitterBufProfileJitterFaxModem added
							sheVoipH248MgConfigProfileTopology deleted
							sheVoipH248MgConfigProfilePropertyRootMaxContexts removed
							sheVoipH248MgConfigProfilePropertyRootMaxTerm removed"
			REVISION "200703121416Z"		-- March 12, 2007 at 14:16 GMT
			DESCRIPTION 
				"heVoipMgcConfigProfileSoftswitch1,sheVoipMgcConfigProfileSoftswitch2,sheVoipMgcConfigProfileSoftswitch3,
							sheVoipMgcConfigProfileSoftswitch4,sheVoipMgcConfigProfileSoftswitch5 added into SheVoipMgcConfigProfileEntry"
			REVISION "200703141417Z"		-- March 14, 2007 at 14:17 GMT
			DESCRIPTION 
				"More value added into SheVoipH248MgConfigProfileEncodingSchemeType
				sheVoipVoipVoiceCtpRtpStreamTos added into SheVoipVoipVoiceCtpEntry, control group and trap
				value range of sheVoipH248MgConfigProfileMarkTos changed to (0..255), SheVoipMediaCodecProfileVadType
				value changed, sheVoipRtcpProfileFecPayLoadType added into sheVoipRtcpProfileEntry, control group and trap.
				More description added into sheVoipMediaCodecProfileVad."
			REVISION "200705091418Z"		-- May 09, 2007 at 14:18 GMT
			DESCRIPTION 
				"Merge current R2.0M maintenance release to SHE R2.5.2.
				This version is not backward compatible to SHE R2.5.1."
			REVISION "200705231006Z"		-- May 23, 2007 at 10:06 GMT
			DESCRIPTION 
				"Modify default value for sheVoipH248MgConfigProfileHeartBeatTime."
			REVISION "200709121455Z"		-- September 12, 2007 at 14:55 GMT
			DESCRIPTION 
				"Merge R2.0M APS38 release.
				Add zxss10 into SheVoipMgcConfigProfileSoftswitchType,
				due to this IP/Port/SS #6 are added into sheVoipH248DataGroup.
				The range of sheVoipVgwPrioProfileIndex is set to 0 ~ 65535, defval is 0."
			REVISION "200710231225Z"		-- October 23, 2007 at 12:25 GMT
			DESCRIPTION 
				"Add SIP support for R2.6S and R2.7."
			::= { dsShe 18 }

		
	
--
-- Type definitions
--
	
		SheVoipVgwStatusType ::= INTEGER
			{
			down(0),
			up(1)
			}

		SheVoipVgwSignalingProtocolType ::= INTEGER
			{
			none(0),
			sip(1),
			h248(2),
			mgcp(3)
			}

		SheVoipControlRequestType ::= INTEGER
			{
			noRequest(1),
			createVoipVgw(10),
			deleteVoipVgw(11),
			modifyVoipVgwConfig(12),
			setVoipVgwAdminStatus(13),
			createVoipCallPriorityProfile(14),
			deleteVoipCallPriorityProfile(15),
			modifyVoipCallPriorityProfile(16),
			createVoipMgcConfigProfile(20),
			modifyVoipMgcConfigProfile(21),
			deleteVoipMgcConfigProfile(22),
			createVoipH248MgConfigProfile(23),
			modifyVoipH248MgConfigProfile(24),
			deleteVoipH248MgConfigProfile(25),
			createVoipMediaCodecProfile(30),
			modifyVoipMediaCodecProfile(31),
			deleteVoipMediaCodecProfile(32),
			createVoipMediaJitterBufProfile(33),
			modifyVoipMediaJitterBufProfile(34),
			deleteVoipMediaJitterBufProfile(35),
			createVoipMediaFaxProfile(36),
			modifyVoipMediaFaxProfile(37),
			deleteVoipMediaFaxProfile(38),
			createsheVoipRtcpProfile(40),
			modifysheVoipRtcpProfile(41),
			deletesheVoipRtcpProfile(42),
			modifySheVoipVoipVoiceCtpConfig(43),
			createVoipIpHostProfile(50),
			deleteVoipIpHostProfile(51),
			modifyVoipIpHostProfile(52),
			createVoipDigitMapProfile(60),
			deleteVoipDigitMapProfile(61),
			modifyVoipDigitMapProfile(62),
			setCallCtrlPmMonitorTime(70),
			setRtpMonitorTime(80),
			setVgwMonitorTime(90),
			createSipUAConfigProfile(100),
			deleteSipUAConfigProfile(110),
			modifySipUAConfigProfile(120),
			createSipProfile(130),
			deleteSipProfile(140),
			modifySipProfile(150),
			createSipServerConfigProfile(160),
			deleteSipServerConfigProfile(170),
			modifySipServerConfigProfile(180),
			createSipFACProfile(190),
			deleteSipFACProfile(200),
			modifySipFACProfile(210)
			}

		SheVoipControlRequestResultType ::= INTEGER
			{
			noRequest(1),
			failed(2),
			voipNotInitialized(3),
			memoryAllocFailure(4),
			defProfilesCreationFailure(5),
			exceedMaxProfileNum(6),
			exceedMaxVgwNum(7),
			exceedMaxSlotNum(8),
			invalidParameter(9),
			vgwMemberListNotEmpty(10),
			profileIsInUse(11),
			duplicatedIndex(12),
			duplicatedPort(13),
			duplicatedName(14),
			tooLongName(15),
			profileEntryNotFound(16),
			cannotDeleteDefProfile(17),
			cannotModifyDefProfileName(18),
			tableIsEmpty(19),
			tableEntryNotFound(20),
			memberBelongsToOtherVgw(21),
			testOnGoing(22),
			porNotInTestStatus(23),
			maxLessThanMin(24),
			duplicatedIpAddress(25),
			duplicatedSlotIpHost(26),
			ipHostGatewayFailed(27),
			adminNotInTestStatus(28),
			dhcpNotSupported(29),
			comExecStarted(30),
			paramFaulty(31),
			requestBusy(32),
			setDataFailed(34),
			aswTimeout(35),
			commandFailed(36),
			commandSucceeded(37),
			ipHostProtection(38)
			}

		SheVoipMgcConfigProfileSoftswitchType ::= INTEGER
			{
			common(0),
			siemensHie9200(1),
			alcatelA5020(2),
			huaweiSoftX3000(3),
			nortelCs2000(4),
			ericssionTesTSS(5),
			zxss10(6)
			}

		SheVoipH248MgConfigProfileEncodingSchemeType ::= INTEGER
			{
			mgTextShort(0),
			mgTextLong(1),
			mgBinary(2)
			}

		SheVoipH248MgConfigProfileProtocolVersionType ::= INTEGER
			{
			megacoV1(1),
			megacoV2(2)
			}

		SheVoipH248MgConfigProfileUseTimestampType ::= INTEGER
			{
			timeStampNoUse(0),
			timeStampUse(1)
			}

		SheVoipH248MgConfigProfileStartupType ::= INTEGER
			{
			normal(1),
			expedited(2),
			local(3)
			}

		SheVoipH248MgConfigProfileTermQuitModeType ::= INTEGER
			{
			graceful(1),
			forced(2)
			}

		SheVoipH248MgConfigProfileTcpUdpCfgProtocolType ::= INTEGER
			{
			udp(1),
			tcp(2),
			sctp(3)
			}

		SheVoipMediaCodecProfileG723BitrateType ::= INTEGER
			{
			bps6300(0),
			bps5300(1)
			}

		SheVoipMediaCodecProfileG726BitrateType ::= INTEGER
			{
			gbt16kbps(0),
			gbt24kbps(1),
			gbt32kbps(2),
			gbt40kbps(3)
			}

		SheVoipMediaCodecProfileCodecPTimeG711Type ::= INTEGER
			{
			g711pgc10msec(0),
			g711pgc20msec(1),
			g711pgc30msec(2),
			g711pgc40msec(3),
			g711pgc50msec(4),
			g711pgc60msec(5)
			}

		SheVoipMediaCodecProfileCodecPTimeG723Type ::= INTEGER
			{
			g723pgc30msec(0),
			g723pgc60msec(1)
			}

		SheVoipMediaCodecProfileCodecPTimeG726Type ::= INTEGER
			{
			g726pgc10msec(0),
			g726pgc20msec(1),
			g726pgc30msec(2)
			}

		SheVoipMediaCodecProfileVadType ::= INTEGER
			{
			off(0),
			defaultMethod(1),
			appendixIIScheme(2)
			}

		SheVoipMediaCodecProfilePLCType ::= INTEGER
			{
			plcOff(0),
			plcon(1)
			}

		SheVoipMediaCodecProfileCngType ::= INTEGER
			{
			cngOff(0),
			cngOn(1)
			}

		SheVoipMediaCodecProfileAutoSwitchCodecType ::= INTEGER
			{
			off(0),
			pcma(1),
			pcmu(2)
			}

		SheVoipMediaCodecProfileG711passThruCodecType ::= INTEGER
			{
			pcma(1),
			pcmu(2)
			}

		SheVoipMediaJitterBufProfileJitterModeType ::= INTEGER
			{
			dynamic(0),
			static(1)
			}

		SheVoipMediaFaxProfileModemDetectType ::= INTEGER
			{
			modemOff(0),
			modemAuto(1),
			modemMgc(2)
			}

		SheVoipMediaFaxProfileFaxTypeUsedType ::= INTEGER
			{
			faxOff(0),
			t30auto(1),
			t30mgc(2),
			t38auto(3),
			t38mgc(4)
			}

		SheVoipMediaFaxProfileFaxMaxBaudrateType ::= INTEGER
			{
			nospeed(0),
			fmb2400bps(1),
			fmb4800bps(2),
			fmb7200bps(3),
			fmb9600bps(4),
			fmb12000bps(5),
			fmb14400bps(6)
			}

		SheVoipMediaFaxProfileT38FaxEcmType ::= INTEGER
			{
			ecmOff(0),
			ecmOn(1)
			}

		SheVoipMediaFaxProfileT38FaxTcfmodeType ::= INTEGER
			{
			procedure2(0),
			procedure1(1)
			}

		SheVoipMediaFaxProfileT38FaxBytemodeType ::= INTEGER
			{
			bytemode(0),
			framemode(1)
			}

		SheVoipRtcpProfileDtmfType ::= INTEGER
			{
			inBandDtmf(0),
			rfc2833(1)
			}

		SheVoipRtcpProfileRtcpGenType ::= INTEGER
			{
			rtcpGenOff(0),
			rtcpGenOn(1)
			}

		SheVoipIpHostProfileUseDhcpType ::= INTEGER
			{
			noUseDhcp(0),
			useDhcp(1)
			}

		SheVoipSipProfileOvlFlagType ::= INTEGER
			{
			no(0),
			yes(1)
			}

		SheVoipSipServerFunctionType ::= INTEGER
			{
			proxy(2),
			redirect(3),
			registrar(4)
			}

	
	
--
-- Node definitions
--
	
		sheVoipMibModule OBJECT IDENTIFIER ::= { sheVoipMib 100 }

		
		sheVoipVgwGroup OBJECT IDENTIFIER ::= { sheVoipMibModule 1 }

		
		sheVoipVgwTable OBJECT-TYPE
			SYNTAX SEQUENCE OF SheVoipVgwEntry
			MAX-ACCESS not-accessible
			STATUS current
			DESCRIPTION
				"This table contains attributes for each VGW."
			::= { sheVoipVgwGroup 1 }

		
		sheVoipVgwEntry OBJECT-TYPE
			SYNTAX SheVoipVgwEntry
			MAX-ACCESS not-accessible
			STATUS current
			DESCRIPTION
				"An entry in sheVoipVgwTable."
			INDEX { sheVoipVgwIndex }
			::= { sheVoipVgwTable 1 }

		
		SheVoipVgwEntry ::=
			SEQUENCE { 
				sheVoipVgwIndex
					Unsigned32,
				sheVoipVgwName
					DisplayString,
				sheVoipVgwAdminStatus
					SheVoipVgwStatusType,
				sheVoipVgwOperStatus
					SheVoipVgwStatusType,
				sheVoipVgwMemberList
					OCTET STRING,
				sheVoipVgwDmList
					OCTET STRING,
				sheVoipVgwIpAddr
					IpAddress,
				sheVoipVgwPortNumber
					Unsigned32,
				sheVoipVgwSignalingProtocol
					SheVoipVgwSignalingProtocolType,
				sheVoipVgwMgConfigProfileIndex
					Unsigned32,
				sheVoipVgwMgcConfigProfileIndex
					Unsigned32,
				sheVoipVgwAlarmSeverityIndex
					SheAlarmSevProfileIndex,
				sheVoipVgwPrioProfileIndex
					INTEGER,
				sheVoipVgwSipUAConfigProfileIndex
					Unsigned32,
				sheVoipVgwSipServerConfigProfileIndex
					Unsigned32
			 }

		sheVoipVgwIndex OBJECT-TYPE
			SYNTAX Unsigned32
			MAX-ACCESS read-only
			STATUS current
			DESCRIPTION
				"Table index. Each index uniquely identifies one VGW entry."
			::= { sheVoipVgwEntry 1 }

		
		sheVoipVgwName OBJECT-TYPE
			SYNTAX DisplayString (SIZE (0..31))
			MAX-ACCESS read-only
			STATUS current
			DESCRIPTION
				"A describable name that uniquely identifies a profile entry  
				of this table. It should be user specified."
			::= { sheVoipVgwEntry 2 }

		
		sheVoipVgwAdminStatus OBJECT-TYPE
			SYNTAX SheVoipVgwStatusType
			MAX-ACCESS read-only
			STATUS current
			DESCRIPTION
				"The desired state of the vgw. When a managed system initializes, all 
				vgws start with vgwAdminStatus in the down(0)state.  As a result of either  
				explicit management action or per configuration information retained by 
				the managed system, vgwAdminStatus is then changed to up(1)states (or remains in 
				the down(0) state). 
				"
			DEFVAL { down }
			::= { sheVoipVgwEntry 3 }

		
		sheVoipVgwOperStatus OBJECT-TYPE
			SYNTAX SheVoipVgwStatusType
			MAX-ACCESS read-only
			STATUS current
			DESCRIPTION
				"Current status of this vgw, can be set to either up or down.
				down(0), up(1)"
			DEFVAL { down }
			::= { sheVoipVgwEntry 4 }

		
		sheVoipVgwMemberList OBJECT-TYPE
			SYNTAX OCTET STRING (SIZE (256))
			MAX-ACCESS read-only
			STATUS current
			DESCRIPTION
				"Member list contained in this vgw. This is a bitmap of the slot or ports that are the members
				of the vgw, depending on the signaling protocol. For example, if the SignalingProtocol
				is set to H248, each bit in this attribute indicates a slot by his entPhysicalIndex.
				For SIP, each bit indicates a port by his ifIndex.
				The least significant bit (LSB) of byte 0 indicates the card/port 1.
				The LSB of byte 1 indicates the card/port 9,
				and so on.
				
				Be aware that first valid port index is now 101 - first valid IU ifIndex.
				Be aware that first valid slot index is now 3 - first valid slot entPhysicalIndex. 
				 
				Different to R2.0M Maintenance release!!  
				"
			::= { sheVoipVgwEntry 5 }

		
		sheVoipVgwDmList OBJECT-TYPE
			SYNTAX OCTET STRING (SIZE (64))
			MAX-ACCESS read-only
			STATUS current
			DESCRIPTION
				"The digit map that is configured in this vgw.  The octet 
				string contains the profile index of sheVoipDigitMapProfileTable. Each index 
				has 16 bits (2 octects). DigitMapNames referred by indices added in this list 
				should be different to each other, which means within one VGW, digitMapName should 
				be unique. A maximum number of 1 digitmap index can be set to the DmList for each vgw. 
				Each index should be set to its fixed position in this octet string. For example, 
				there is a sheVoipDigitMapProfileTable that contains a entry with the index - 
				index6. When this index need to be set into sheVoipVgwDmList, 
				it should be set according to the following draft:  
				 
				[0] [1] [2] [3]	... ...	[6]	[7] ... ...[10][11] 
				---+---+---+---+---+---+---+---+---+---+---+---+--- 
								       |index 6| 
				---+---+---+---+---+---+---+---+---+---+---+---+---	 	 
				"
			::= { sheVoipVgwEntry 6 }

		
		sheVoipVgwIpAddr OBJECT-TYPE
			SYNTAX IpAddress
			MAX-ACCESS read-only
			STATUS current
			DESCRIPTION
				"The IP address that the Media Gateway Controller will  
				use to communicate with the Media Gateway. The value  
				0.0.0.0. is returned if the entry is invalid. 
				Def: CXU IP ADDRESS"
			::= { sheVoipVgwEntry 7 }

		
		sheVoipVgwPortNumber OBJECT-TYPE
			SYNTAX Unsigned32
			MAX-ACCESS read-only
			STATUS current
			DESCRIPTION
				"TCP/UDP port number that the Media Gateway Controller  
				will use to communicate with the Media Gateway. The value 0  
				is returned if the entry is invalid."
			::= { sheVoipVgwEntry 8 }

		
		sheVoipVgwSignalingProtocol OBJECT-TYPE
			SYNTAX SheVoipVgwSignalingProtocolType
			MAX-ACCESS read-only
			STATUS current
			DESCRIPTION
				"This attribute identifies the type of VoIP signaling  
				protocol used. 
				Valid values are:  
				0 - none 
				1 - sip 
				2 - h248 
				3 - mgcp"
			DEFVAL { h248 }
			::= { sheVoipVgwEntry 9 }

		
		sheVoipVgwMgConfigProfileIndex OBJECT-TYPE
			SYNTAX Unsigned32
			MAX-ACCESS read-only
			STATUS current
			DESCRIPTION
				"When signaling protocol is set to H.248, this index 
				equals to sheVoipH248MgConfigProfileIndex."
			DEFVAL { 1 }
			::= { sheVoipVgwEntry 10 }

		
		sheVoipVgwMgcConfigProfileIndex OBJECT-TYPE
			SYNTAX Unsigned32
			MAX-ACCESS read-only
			STATUS current
			DESCRIPTION
				"When signaling protocol is set to Mgcp, this index equals to sheVoipMgcConfigProfileIndex.
				This attribute associates Vgw with MGC configuration."
			DEFVAL { 0 }
			::= { sheVoipVgwEntry 11 }

		
		sheVoipVgwAlarmSeverityIndex OBJECT-TYPE
			SYNTAX SheAlarmSevProfileIndex
			MAX-ACCESS read-only
			STATUS current
			DESCRIPTION
				"Equals to sheAlarmSevProfileIndex in sheAlarmSeverityProfileTable, sheAlarmingMib."
			DEFVAL { 1 }
			::= { sheVoipVgwEntry 12 }

		
		sheVoipVgwPrioProfileIndex OBJECT-TYPE
			SYNTAX INTEGER (0..65535)
			MAX-ACCESS read-only
			STATUS current
			DESCRIPTION
				"Equals to sheVoipCallPriorityProfileIndex in sheVoipCallPriorityProfileTable.
				0 measns not configured"
			DEFVAL { 0 }
			::= { sheVoipVgwEntry 13 }

		
-- cn2zj090 on 2007-06-27 in BeiJing
		sheVoipVgwSipUAConfigProfileIndex OBJECT-TYPE
			SYNTAX Unsigned32
			MAX-ACCESS read-only
			STATUS current
			DESCRIPTION
				"Equals to sheVoipSipUAConfigProfileIndex in sheVoipSipUserAgentConfigProfileTable."
			::= { sheVoipVgwEntry 14 }

		
		sheVoipVgwSipServerConfigProfileIndex OBJECT-TYPE
			SYNTAX Unsigned32
			MAX-ACCESS read-only
			STATUS current
			DESCRIPTION
				"Equals to sheVoipSipServerConfigProfileIndex in sheVoipSipServerConfigProfileTable."
			::= { sheVoipVgwEntry 15 }

		
		sheVoipVgwControl OBJECT IDENTIFIER ::= { sheVoipVgwGroup 2 }

		
		sheVoipVgwControlRequest OBJECT-TYPE
			SYNTAX SheVoipControlRequestType
			MAX-ACCESS read-write
			STATUS current
			DESCRIPTION
				"The request of a user command: 
				createVoipVgw					(10) 
					Must: 	 sheVoipVgwControlSignalingProtocol 
					Optional:sheVoipVgwControlName 
							 sheVoipVgwControlMemberList 
							 sheVoipVgwControlDmList 
							 sheVoipVgwControlIpAddr  
							 sheVoipVgwControlPortNumber 
							 sheVoipVgwControlMgConfigProfileIndex 
							 sheVoipVgwControlMgcConfigProfileIndex
							 sheVoipVgwControlAlarmSeverityIndex   
							 sheVoipVgwControlPrioProfileIndex 
				         deleteVoipVgw					(11), 
				             Must: 	 sheVoipVgwControlIndex 
				              
				modifyVoipVgwConfig				(12), 
					Must: 	 sheVoipVgwControlIndex				 
					Optional:sheVoipVgwControlName 
							 sheVoipVgwControlIpAddr 						  
							 sheVoipVgwControlMemberList 
							 sheVoipVgwControlDmList 
							 sheVoipVgwControlPortNumber 
							 sheVoipVgwControlSignalingProtocol 
							 sheVoipVgwControlMgConfigProfileIndex 
							 sheVoipVgwControlMgcConfigProfileIndex 
							 sheVoipVgwControlAlarmSeverityIndex
							 sheVoipVgwControlPrioProfileIndex
				setVoipVgwAdminStatus			(13) 
					Must: 	 sheVoipVgwControlIndex 
						 sheVoipVgwControlAdminStatus							     
				"
			::= { sheVoipVgwControl 1 }

		
		sheVoipVgwControlIndex OBJECT-TYPE
			SYNTAX Unsigned32
			MAX-ACCESS read-write
			STATUS current
			DESCRIPTION
				"sheVoipVgwIndex - each index uniquely identifies  
				one VGW entry."
			::= { sheVoipVgwControl 2 }

		
		sheVoipVgwControlName OBJECT-TYPE
			SYNTAX DisplayString (SIZE (0..31))
			MAX-ACCESS read-write
			STATUS current
			DESCRIPTION
				"A describable name that uniquely identifies a profile entry  
				of this table.It should be user specified."
			::= { sheVoipVgwControl 3 }

		
		sheVoipVgwControlAdminStatus OBJECT-TYPE
			SYNTAX SheVoipVgwStatusType
			MAX-ACCESS read-write
			STATUS current
			DESCRIPTION
				"The desired state of the vgw. When a managed system initializes, all 
				vgws start with vgwAdminStatus in the down(0)state.  As a result of either  
				explicit management action or per configuration information retained by 
				the managed system, vgwAdminStatus is then changed to up(1)states (or remains in 
				the down(0) state).  
				"
			::= { sheVoipVgwControl 4 }

		
		sheVoipVgwControlMemberList OBJECT-TYPE
			SYNTAX OCTET STRING (SIZE (256))
			MAX-ACCESS read-write
			STATUS current
			DESCRIPTION
				"Member list contained in this vgw. This is a bitmap of the slot or ports that are the members
				of the vgw, depending on the signaling protocol. For example, if the SignalingProtocol
				is set to H248, each bit in this attribute indicates a slot by his entPhysicalIndex.
				For SIP, each bit indicates a port by his ifIndex.
				The least significant bit (LSB) of byte 0 indicates the card/port 1.
				The LSB of byte 1 indicates the card/port 9,
				and so on.
				
				Be aware that first valid port index is now 101 - first valid IU ifIndex.
				Be aware that first valid slot index is now 3 - first valid slot entPhysicalIndex. 
				
				Different to R2.0M maintenance release!!
				"
			::= { sheVoipVgwControl 5 }

		
		sheVoipVgwControlDmList OBJECT-TYPE
			SYNTAX OCTET STRING (SIZE (64))
			MAX-ACCESS read-write
			STATUS current
			DESCRIPTION
				"The digit map that is configured in this vgw.  The octet 
				string contains the profile index of sheVoipDigitMapProfileTable. Each index 
				has 16 bits (2 octects). DigitMapNames referred by indices added in this list 
				should be different to each other, which means within one VGW, digitMapName should 
				be unique. A maximum number of 1 digitmap index can be set to the DmList for each vgw. 
				Each index should be set to its fixed position in this octet string. For example, 
				there is a sheVoipDigitMapProfileTable that contains a entry with the index - 
				index6. When this index need to be set into sheVoipVgwDmList, 
				it should be set according to the following draft:  
				 
				[0] [1] [2] [3]	... ...	[6]	[7] ... ...[10][11] 
				---+---+---+---+---+---+---+---+---+---+---+---+--- 
								       |index 6| 
				---+---+---+---+---+---+---+---+---+---+---+---+--- 
				"
			::= { sheVoipVgwControl 6 }

		
		sheVoipVgwControlIpAddr OBJECT-TYPE
			SYNTAX IpAddress
			MAX-ACCESS read-write
			STATUS current
			DESCRIPTION
				"The IP address that the Media Gateway Controller will  
				use to communicate with the Media Gateway.CXU IP ADDRESS 
				is used as the default value."
			::= { sheVoipVgwControl 7 }

		
		sheVoipVgwControlPortNumber OBJECT-TYPE
			SYNTAX Unsigned32
			MAX-ACCESS read-write
			STATUS current
			DESCRIPTION
				"TCP/UDP port number that the Media Gateway Controller  
				will use to communicate with the Media Gateway.Default  
				value is created by system automatically."
			::= { sheVoipVgwControl 8 }

		
		sheVoipVgwControlSignalingProtocol OBJECT-TYPE
			SYNTAX SheVoipVgwSignalingProtocolType
			MAX-ACCESS read-write
			STATUS current
			DESCRIPTION
				"This attribute identifies the type of VoIP signaling  
				protocol used. Only one type of protocol is allowed. 
				Valid values are:  
				0 - none 
				1 - sip 
				2 - h248 
				3 - mgcp"
			::= { sheVoipVgwControl 9 }

		
		sheVoipVgwControlMgConfigProfileIndex OBJECT-TYPE
			SYNTAX Unsigned32
			MAX-ACCESS read-write
			STATUS current
			DESCRIPTION
				"This attribute associates Vgw with MG configuration."
			::= { sheVoipVgwControl 10 }

		
		sheVoipVgwControlMgcConfigProfileIndex OBJECT-TYPE
			SYNTAX Unsigned32
			MAX-ACCESS read-write
			STATUS current
			DESCRIPTION
				"This attribute associates Vgw with MGC configuration."
			::= { sheVoipVgwControl 11 }

		
		sheVoipVgwControlAlarmSeverityIndex OBJECT-TYPE
			SYNTAX SheAlarmSevProfileIndex
			MAX-ACCESS read-write
			STATUS current
			DESCRIPTION
				"AlarmSeverityIndex"
			::= { sheVoipVgwControl 12 }

		
		sheVoipVgwControlPrioProfileIndex OBJECT-TYPE
			SYNTAX INTEGER (0..65535)
			MAX-ACCESS read-write
			STATUS current
			DESCRIPTION
				"Equals to sheVoipCallPriorityProfileIndex."
			::= { sheVoipVgwControl 13 }

		
		sheVoipVgwControlStatus OBJECT-TYPE
			SYNTAX SheControlStatusType
			MAX-ACCESS read-only
			STATUS current
			DESCRIPTION
				"The status of a user command."
			::= { sheVoipVgwControl 14 }

		
		sheVoipVgwControlTimer OBJECT-TYPE
			SYNTAX Gauge32
			MAX-ACCESS read-only
			STATUS current
			DESCRIPTION
				"The maximum wait time for the manager for a  
				long running user command."
			::= { sheVoipVgwControl 15 }

		
		sheVoipVgwControlTimeStamp OBJECT-TYPE
			SYNTAX TimeTicks
			MAX-ACCESS read-only
			STATUS current
			DESCRIPTION
				"The time stamp of the last command (end of command)."
			::= { sheVoipVgwControl 16 }

		
		sheVoipVgwControlReqResult OBJECT-TYPE
			SYNTAX SheVoipControlRequestResultType
			MAX-ACCESS read-only
			STATUS current
			DESCRIPTION
				"The result of the last user command."
			::= { sheVoipVgwControl 17 }

		
-- cn2zj090 on 2007-06-27 in BeiJing
		sheVoipVgwControlSipUAConfigProfileIndex OBJECT-TYPE
			SYNTAX Unsigned32
			MAX-ACCESS read-write
			STATUS current
			DESCRIPTION
				"Equals to sheVoipSipUAConfigProfileIndex in sheVoipSipUAConfigProfileTable."
			::= { sheVoipVgwControl 18 }

		
		sheVoipVgwControlSipServerConfigProfileIndex OBJECT-TYPE
			SYNTAX Unsigned32
			MAX-ACCESS read-write
			STATUS current
			DESCRIPTION
				"Equals to sheVoipSipServerConfigProfileIndex in sheVoipSipServerConfigProfileTable."
			::= { sheVoipVgwControl 19 }

		
		sheVoipCallPriorityProfileTable OBJECT-TYPE
			SYNTAX SEQUENCE OF SheVoipCallPriorityProfileEntry
			MAX-ACCESS not-accessible
			STATUS current
			DESCRIPTION
				"This table contains attributes for each PriorityProfile entry."
			::= { sheVoipVgwGroup 3 }

		
		sheVoipCallPriorityProfileEntry OBJECT-TYPE
			SYNTAX SheVoipCallPriorityProfileEntry
			MAX-ACCESS not-accessible
			STATUS current
			DESCRIPTION
				"An entry in sheVoipCallPriorityProfileTable.                      
				"
			INDEX { sheVoipCallPriorityProfileIndex }
			::= { sheVoipCallPriorityProfileTable 1 }

		
		SheVoipCallPriorityProfileEntry ::=
			SEQUENCE { 
				sheVoipCallPriorityProfileIndex
					INTEGER,
				sheVoipCallPriorityProfileName
					DisplayString,
				sheVoipCallPriorityProfileLevel1
					INTEGER,
				sheVoipCallPriorityProfileLevel2
					INTEGER,
				sheVoipCallPriorityProfileLevel3
					INTEGER
			 }

		sheVoipCallPriorityProfileIndex OBJECT-TYPE
			SYNTAX INTEGER (1..65535)
			MAX-ACCESS read-only
			STATUS current
			DESCRIPTION
				"Table index. Each index uniquely identifies one 
				vgw priority profile.
				"
			::= { sheVoipCallPriorityProfileEntry 1 }

		
		sheVoipCallPriorityProfileName OBJECT-TYPE
			SYNTAX DisplayString (SIZE (0..31))
			MAX-ACCESS read-only
			STATUS current
			DESCRIPTION
				"A describable name that uniquely identifies a profile entry 
				of this table.The profile name is user specified. 
				"
			::= { sheVoipCallPriorityProfileEntry 2 }

		
		sheVoipCallPriorityProfileLevel1 OBJECT-TYPE
			SYNTAX INTEGER (0..100)
			MAX-ACCESS read-only
			STATUS current
			DESCRIPTION
				"Level1 of Priority Service (default:75)."
			DEFVAL { 75 }
			::= { sheVoipCallPriorityProfileEntry 3 }

		
		sheVoipCallPriorityProfileLevel2 OBJECT-TYPE
			SYNTAX INTEGER (0..100)
			MAX-ACCESS read-only
			STATUS current
			DESCRIPTION
				"Level2 of Priority Service (default:50)."
			DEFVAL { 50 }
			::= { sheVoipCallPriorityProfileEntry 4 }

		
		sheVoipCallPriorityProfileLevel3 OBJECT-TYPE
			SYNTAX INTEGER (0..100)
			MAX-ACCESS read-only
			STATUS current
			DESCRIPTION
				"Level3 of Priority Service (default:25)."
			DEFVAL { 25 }
			::= { sheVoipCallPriorityProfileEntry 5 }

		
		sheVoipCallPriorityProfileControl OBJECT IDENTIFIER ::= { sheVoipVgwGroup 4 }

		
		sheVoipCallPriorityProfileControlRequest OBJECT-TYPE
			SYNTAX SheVoipControlRequestType
			MAX-ACCESS read-write
			STATUS current
			DESCRIPTION
				"The request of a user command.
				createVoipVgwPriorityProfile    (23),
				    Must: sheVoipCallPriorityProfileControlName
				    Optional:sheVoipCallPriorityProfileControlLevel1
				             sheVoipCallPriorityProfileControlLevel2
				             sheVoipCallPriorityProfileControlLevel3
				                      
				modifyVoipVgwPriorityProfile    (24),
				    Must: sheVoipCallPriorityProfileControlIndex
				    Optional:sheVoipCallPriorityProfileControlName
				             sheVoipCallPriorityProfileControlLevel1
				             sheVoipCallPriorityProfileControlLevel2
				             sheVoipCallPriorityProfileControlLevel3
				                      
				deleteVoipVgwPriorityProfile    (25),
				     Must: sheVoipCallPriorityProfileControlIndex
				"
			::= { sheVoipCallPriorityProfileControl 1 }

		
		sheVoipCallPriorityProfileControlIndex OBJECT-TYPE
			SYNTAX INTEGER (1..65535)
			MAX-ACCESS read-write
			STATUS current
			DESCRIPTION
				"Equals to sheVoipMgcConfigIndex."
			::= { sheVoipCallPriorityProfileControl 2 }

		
		sheVoipCallPriorityProfileControlName OBJECT-TYPE
			SYNTAX DisplayString (SIZE (0..31))
			MAX-ACCESS read-write
			STATUS current
			DESCRIPTION
				"A describable name that uniquely identifies a profile entry 
				of this table.The profile name is user specified. "
			::= { sheVoipCallPriorityProfileControl 3 }

		
		sheVoipCallPriorityProfileControlLevel1 OBJECT-TYPE
			SYNTAX INTEGER (0..100)
			MAX-ACCESS read-write
			STATUS current
			DESCRIPTION
				"Level1 of Priority Service (default:75)."
			::= { sheVoipCallPriorityProfileControl 4 }

		
		sheVoipCallPriorityProfileControlLevel2 OBJECT-TYPE
			SYNTAX INTEGER (0..100)
			MAX-ACCESS read-write
			STATUS current
			DESCRIPTION
				"Level2 of Priority Service (default:50)."
			::= { sheVoipCallPriorityProfileControl 5 }

		
		sheVoipCallPriorityProfileControlLevel3 OBJECT-TYPE
			SYNTAX INTEGER (0..100)
			MAX-ACCESS read-write
			STATUS current
			DESCRIPTION
				"Level3 of Priority Service (default:25)."
			::= { sheVoipCallPriorityProfileControl 6 }

		
		sheVoipCallPriorityProfileControlStatus OBJECT-TYPE
			SYNTAX SheControlStatusType
			MAX-ACCESS read-only
			STATUS current
			DESCRIPTION
				"The status of a user command."
			::= { sheVoipCallPriorityProfileControl 7 }

		
		sheVoipCallPriorityProfileControlTimer OBJECT-TYPE
			SYNTAX Gauge32
			MAX-ACCESS read-only
			STATUS current
			DESCRIPTION
				"The maximum wait time for the manager for a 
				long running user command."
			::= { sheVoipCallPriorityProfileControl 8 }

		
		sheVoipCallPriorityProfileControlTimeStamp OBJECT-TYPE
			SYNTAX TimeTicks
			MAX-ACCESS read-only
			STATUS current
			DESCRIPTION
				"The time stamp of the last command (end of command)."
			::= { sheVoipCallPriorityProfileControl 9 }

		
		sheVoipCallPriorityProfileControlReqResult OBJECT-TYPE
			SYNTAX SheVoipControlRequestResultType
			MAX-ACCESS read-only
			STATUS current
			DESCRIPTION
				"The result of the last user command."
			::= { sheVoipCallPriorityProfileControl 10 }

		
		sheVoipH248DataGroup OBJECT IDENTIFIER ::= { sheVoipMibModule 2 }

		
		sheVoipMgcConfigProfileTable OBJECT-TYPE
			SYNTAX SEQUENCE OF SheVoipMgcConfigProfileEntry
			MAX-ACCESS not-accessible
			STATUS current
			DESCRIPTION
				"This table contains attributes for each Mgc config profile."
			::= { sheVoipH248DataGroup 1 }

		
		sheVoipMgcConfigProfileEntry OBJECT-TYPE
			SYNTAX SheVoipMgcConfigProfileEntry
			MAX-ACCESS not-accessible
			STATUS current
			DESCRIPTION
				"An entry represents a set of profile configurations 
				in sheVoipMgcConfigProfileTable. 
				"
			INDEX { sheVoipMgcConfigProfileIndex }
			::= { sheVoipMgcConfigProfileTable 1 }

		
		SheVoipMgcConfigProfileEntry ::=
			SEQUENCE { 
				sheVoipMgcConfigProfileIndex
					Unsigned32,
				sheVoipMgcConfigProfileName
					DisplayString,
				sheVoipMgcConfigProfileIPAddress1
					IpAddress,
				sheVoipMgcConfigProfileIPAddress2
					IpAddress,
				sheVoipMgcConfigProfileIPAddress3
					IpAddress,
				sheVoipMgcConfigProfileIPAddress4
					IpAddress,
				sheVoipMgcConfigProfileIPAddress5
					IpAddress,
				sheVoipMgcConfigProfilePort1
					Unsigned32,
				sheVoipMgcConfigProfilePort2
					Unsigned32,
				sheVoipMgcConfigProfilePort3
					Unsigned32,
				sheVoipMgcConfigProfilePort4
					Unsigned32,
				sheVoipMgcConfigProfilePort5
					Unsigned32,
				sheVoipMgcConfigProfileSoftswitch1
					SheVoipMgcConfigProfileSoftswitchType,
				sheVoipMgcConfigProfileSoftswitch2
					SheVoipMgcConfigProfileSoftswitchType,
				sheVoipMgcConfigProfileSoftswitch3
					SheVoipMgcConfigProfileSoftswitchType,
				sheVoipMgcConfigProfileSoftswitch4
					SheVoipMgcConfigProfileSoftswitchType,
				sheVoipMgcConfigProfileSoftswitch5
					SheVoipMgcConfigProfileSoftswitchType
			 }

		sheVoipMgcConfigProfileIndex OBJECT-TYPE
			SYNTAX Unsigned32 (1..16)
			MAX-ACCESS read-only
			STATUS current
			DESCRIPTION
				"Table index. Each index uniquely identifies one mgc config profile."
			::= { sheVoipMgcConfigProfileEntry 1 }

		
		sheVoipMgcConfigProfileName OBJECT-TYPE
			SYNTAX DisplayString (SIZE (0..31))
			MAX-ACCESS read-only
			STATUS current
			DESCRIPTION
				"A describable name that uniquely identifies a profile entry  
				of this table."
			::= { sheVoipMgcConfigProfileEntry 2 }

		
		sheVoipMgcConfigProfileIPAddress1 OBJECT-TYPE
			SYNTAX IpAddress
			MAX-ACCESS read-only
			STATUS current
			DESCRIPTION
				"The IP address of the Media Gateway Controller 1.  
				The value 0.0.0.0 is returned if the entry is invalid."
			::= { sheVoipMgcConfigProfileEntry 3 }

		
		sheVoipMgcConfigProfileIPAddress2 OBJECT-TYPE
			SYNTAX IpAddress
			MAX-ACCESS read-only
			STATUS current
			DESCRIPTION
				"The IP address of the Media Gateway Controller 2.  
				The value 0.0.0.0 is returned if the entry is invalid."
			::= { sheVoipMgcConfigProfileEntry 4 }

		
		sheVoipMgcConfigProfileIPAddress3 OBJECT-TYPE
			SYNTAX IpAddress
			MAX-ACCESS read-only
			STATUS current
			DESCRIPTION
				"The IP address of the Media Gateway Controller 3.  
				The value 0.0.0.0 is returned if the entry is invalid."
			::= { sheVoipMgcConfigProfileEntry 5 }

		
		sheVoipMgcConfigProfileIPAddress4 OBJECT-TYPE
			SYNTAX IpAddress
			MAX-ACCESS read-only
			STATUS current
			DESCRIPTION
				"The IP address of the Media Gateway Controller 4.  
				The value 0.0.0.0 is returned if the entry is invalid."
			::= { sheVoipMgcConfigProfileEntry 6 }

		
		sheVoipMgcConfigProfileIPAddress5 OBJECT-TYPE
			SYNTAX IpAddress
			MAX-ACCESS read-only
			STATUS current
			DESCRIPTION
				"The IP address of the Media Gateway Controller 5.  
				The value 0.0.0.0 is returned if the entry is invalid."
			::= { sheVoipMgcConfigProfileEntry 7 }

		
		sheVoipMgcConfigProfilePort1 OBJECT-TYPE
			SYNTAX Unsigned32
			MAX-ACCESS read-only
			STATUS current
			DESCRIPTION
				"TCP/UDP port of the Media Gateway Controller 1.  
				The value 0 is returned if the entry is invalid."
			::= { sheVoipMgcConfigProfileEntry 8 }

		
		sheVoipMgcConfigProfilePort2 OBJECT-TYPE
			SYNTAX Unsigned32
			MAX-ACCESS read-only
			STATUS current
			DESCRIPTION
				"TCP/UDP port of the Media Gateway Controller 2.  
				The value 0 is returned if the entry is invalid."
			::= { sheVoipMgcConfigProfileEntry 9 }

		
		sheVoipMgcConfigProfilePort3 OBJECT-TYPE
			SYNTAX Unsigned32
			MAX-ACCESS read-only
			STATUS current
			DESCRIPTION
				"TCP/UDP port of the Media Gateway Controller 3.  
				The value 0 is returned if the entry is invalid."
			::= { sheVoipMgcConfigProfileEntry 10 }

		
		sheVoipMgcConfigProfilePort4 OBJECT-TYPE
			SYNTAX Unsigned32
			MAX-ACCESS read-only
			STATUS current
			DESCRIPTION
				"TCP/UDP port of the Media Gateway Controller 4.  
				The value 0 is returned if the entry is invalid."
			::= { sheVoipMgcConfigProfileEntry 11 }

		
		sheVoipMgcConfigProfilePort5 OBJECT-TYPE
			SYNTAX Unsigned32
			MAX-ACCESS read-only
			STATUS current
			DESCRIPTION
				"TCP/UDP port of the Media Gateway Controller 5.  
				The value 0 is returned if the entry is invalid."
			::= { sheVoipMgcConfigProfileEntry 12 }

		
		sheVoipMgcConfigProfileSoftswitch1 OBJECT-TYPE
			SYNTAX SheVoipMgcConfigProfileSoftswitchType
			MAX-ACCESS read-only
			STATUS current
			DESCRIPTION
				"type of softswitch1
				
				common(0),
				siemensHie9200(1),
				alcatelA5020(2),
				huaweiSoftX3000(3),
				nortelCs2000(4),
				ericssionTesTSS(5),
				zxss10(6)"
			DEFVAL { common }
			::= { sheVoipMgcConfigProfileEntry 13 }

		
		sheVoipMgcConfigProfileSoftswitch2 OBJECT-TYPE
			SYNTAX SheVoipMgcConfigProfileSoftswitchType
			MAX-ACCESS read-only
			STATUS current
			DESCRIPTION
				"type of softswitch2
				
				common(0),
				siemensHie9200(1),
				alcatelA5020(2),
				huaweiSoftX3000(3),
				nortelCs2000(4),
				ericssionTesTSS(5),
				zxss10(6)"
			DEFVAL { common }
			::= { sheVoipMgcConfigProfileEntry 14 }

		
		sheVoipMgcConfigProfileSoftswitch3 OBJECT-TYPE
			SYNTAX SheVoipMgcConfigProfileSoftswitchType
			MAX-ACCESS read-only
			STATUS current
			DESCRIPTION
				"type of softswitch3
				
				common(0),
				siemensHie9200(1),
				alcatelA5020(2),
				huaweiSoftX3000(3),
				nortelCs2000(4),
				ericssionTesTSS(5),
				zxss10(6)"
			DEFVAL { common }
			::= { sheVoipMgcConfigProfileEntry 15 }

		
		sheVoipMgcConfigProfileSoftswitch4 OBJECT-TYPE
			SYNTAX SheVoipMgcConfigProfileSoftswitchType
			MAX-ACCESS read-only
			STATUS current
			DESCRIPTION
				"type of softswitch4
				
				common(0),
				siemensHie9200(1),
				alcatelA5020(2),
				huaweiSoftX3000(3),
				nortelCs2000(4),
				ericssionTesTSS(5),
				zxss10(6)"
			DEFVAL { common }
			::= { sheVoipMgcConfigProfileEntry 16 }

		
		sheVoipMgcConfigProfileSoftswitch5 OBJECT-TYPE
			SYNTAX SheVoipMgcConfigProfileSoftswitchType
			MAX-ACCESS read-only
			STATUS current
			DESCRIPTION
				"type of softswitch5
				
				common(0),
				siemensHie9200(1),
				alcatelA5020(2),
				huaweiSoftX3000(3),
				nortelCs2000(4),
				ericssionTesTSS(5),
				zxss10(6)"
			DEFVAL { common }
			::= { sheVoipMgcConfigProfileEntry 17 }

		
		sheVoipMgcConfigProfileControl OBJECT IDENTIFIER ::= { sheVoipH248DataGroup 2 }

		
		sheVoipMgcConfigProfileControlRequest OBJECT-TYPE
			SYNTAX SheVoipControlRequestType
			MAX-ACCESS read-write
			STATUS current
			DESCRIPTION
				"The request of a user command. 
				createVoipMgcConfigProfile   (20), 
					Must: 	sheVoipMgcConfigProfileControlName 
					Optional:   sheVoipMgcConfigProfileControlIPAddress1 
					            sheVoipMgcConfigProfileControlIPAddress2 
					            sheVoipMgcConfigProfileControlIPAddress3 
					            sheVoipMgcConfigProfileControlIPAddress4 
					            sheVoipMgcConfigProfileControlIPAddress5 
					            sheVoipMgcConfigProfileControlPort1 
					            sheVoipMgcConfigProfileControlPort2 
					            sheVoipMgcConfigProfileControlPort3 
					            sheVoipMgcConfigProfileControlPort4 
					            sheVoipMgcConfigProfileControlPort5
					            sheVoipMgcConfigProfileControlSoftswitch1
				        	    sheVoipMgcConfigProfileControlSoftswitch2
				        	    sheVoipMgcConfigProfileControlSoftswitch3
				        	    sheVoipMgcConfigProfileControlSoftswitch4
				        	    sheVoipMgcConfigProfileControlSoftswitch5
				
					             
				modifyVoipMgcConfigProfile   (21), 
					Must:	sheVoipMgcConfigProfileControlIndex 
					Optional:   sheVoipMgcConfigProfileControlName 
						    sheVoipMgcConfigProfileControlIPAddress1 
					            sheVoipMgcConfigProfileControlIPAddress2 
					            sheVoipMgcConfigProfileControlIPAddress3 
					            sheVoipMgcConfigProfileControlIPAddress4 
					            sheVoipMgcConfigProfileControlIPAddress5 
					            sheVoipMgcConfigProfileControlPort1 
					            sheVoipMgcConfigProfileControlPort2 
					            sheVoipMgcConfigProfileControlPort3 
					            sheVoipMgcConfigProfileControlPort4 
					            sheVoipMgcConfigProfileControlPort5
					            sheVoipMgcConfigProfileControlSoftswitch1
				        	    sheVoipMgcConfigProfileControlSoftswitch2
				        	    sheVoipMgcConfigProfileControlSoftswitch3
				        	    sheVoipMgcConfigProfileControlSoftswitch4
				        	    sheVoipMgcConfigProfileControlSoftswitch5
					             
				deleteVoipMgcConfigProfile   (22),  
					Must:	sheVoipMgcConfigProfileControlIndex"
			::= { sheVoipMgcConfigProfileControl 1 }

		
		sheVoipMgcConfigProfileControlIndex OBJECT-TYPE
			SYNTAX Unsigned32 (1..16)
			MAX-ACCESS read-write
			STATUS current
			DESCRIPTION
				"Equals to sheVoipMgcConfigIndex."
			::= { sheVoipMgcConfigProfileControl 2 }

		
		sheVoipMgcConfigProfileControlName OBJECT-TYPE
			SYNTAX DisplayString (SIZE (0..31))
			MAX-ACCESS read-write
			STATUS current
			DESCRIPTION
				"A describable name that uniquely identifies a  
				profile entry of this table."
			::= { sheVoipMgcConfigProfileControl 3 }

		
		sheVoipMgcConfigProfileControlIPAddress1 OBJECT-TYPE
			SYNTAX IpAddress
			MAX-ACCESS read-write
			STATUS current
			DESCRIPTION
				"The IP address of the Media Gateway Controller 1.  
				The value 0.0.0.0 is returned if the entry is invalid."
			::= { sheVoipMgcConfigProfileControl 4 }

		
		sheVoipMgcConfigProfileControlIPAddress2 OBJECT-TYPE
			SYNTAX IpAddress
			MAX-ACCESS read-write
			STATUS current
			DESCRIPTION
				"The IP address of the Media Gateway Controller 2.  
				The value 0.0.0.0 is returned if the entry is invalid."
			::= { sheVoipMgcConfigProfileControl 5 }

		
		sheVoipMgcConfigProfileControlIPAddress3 OBJECT-TYPE
			SYNTAX IpAddress
			MAX-ACCESS read-write
			STATUS current
			DESCRIPTION
				"The IP address of the Media Gateway Controller 3.  
				The value 0.0.0.0 is returned if the entry is invalid."
			::= { sheVoipMgcConfigProfileControl 6 }

		
		sheVoipMgcConfigProfileControlIPAddress4 OBJECT-TYPE
			SYNTAX IpAddress
			MAX-ACCESS read-write
			STATUS current
			DESCRIPTION
				"The IP address of the Media Gateway Controller 4.  
				The value 0.0.0.0 is returned if the entry is invalid."
			::= { sheVoipMgcConfigProfileControl 7 }

		
		sheVoipMgcConfigProfileControlIPAddress5 OBJECT-TYPE
			SYNTAX IpAddress
			MAX-ACCESS read-write
			STATUS current
			DESCRIPTION
				"The IP address of the Media Gateway Controller 5.  
				The value 0.0.0.0 is returned if the entry is invalid."
			::= { sheVoipMgcConfigProfileControl 8 }

		
		sheVoipMgcConfigProfileControlPort1 OBJECT-TYPE
			SYNTAX Unsigned32
			MAX-ACCESS read-write
			STATUS current
			DESCRIPTION
				"TCP/UDP port of the Media Gateway Controller 1.  
				The value 0 is returned if the entry is invalid."
			::= { sheVoipMgcConfigProfileControl 9 }

		
		sheVoipMgcConfigProfileControlPort2 OBJECT-TYPE
			SYNTAX Unsigned32
			MAX-ACCESS read-write
			STATUS current
			DESCRIPTION
				"TCP/UDP port of the Media Gateway Controller 2.  
				The value 0 is returned if the entry is invalid."
			::= { sheVoipMgcConfigProfileControl 10 }

		
		sheVoipMgcConfigProfileControlPort3 OBJECT-TYPE
			SYNTAX Unsigned32
			MAX-ACCESS read-write
			STATUS current
			DESCRIPTION
				"TCP/UDP port of the Media Gateway Controller 3.  
				The value 0 is returned if the entry is invalid."
			::= { sheVoipMgcConfigProfileControl 11 }

		
		sheVoipMgcConfigProfileControlPort4 OBJECT-TYPE
			SYNTAX Unsigned32
			MAX-ACCESS read-write
			STATUS current
			DESCRIPTION
				"TCP/UDP port of the Media Gateway Controller 4.  
				The value 0 is returned if the entry is invalid."
			::= { sheVoipMgcConfigProfileControl 12 }

		
		sheVoipMgcConfigProfileControlPort5 OBJECT-TYPE
			SYNTAX Unsigned32
			MAX-ACCESS read-write
			STATUS current
			DESCRIPTION
				"TCP/UDP port of the Media Gateway Controller 5.  
				The value 0 is returned if the entry is invalid."
			::= { sheVoipMgcConfigProfileControl 13 }

		
		sheVoipMgcConfigProfileControlStatus OBJECT-TYPE
			SYNTAX SheControlStatusType
			MAX-ACCESS read-only
			STATUS current
			DESCRIPTION
				"The status of a user command."
			::= { sheVoipMgcConfigProfileControl 14 }

		
		sheVoipMgcConfigProfileControlTimer OBJECT-TYPE
			SYNTAX Gauge32
			MAX-ACCESS read-only
			STATUS current
			DESCRIPTION
				"The maximum wait time for the manager for a  
				long running user command."
			::= { sheVoipMgcConfigProfileControl 15 }

		
		sheVoipMgcConfigProfileControlTimeStamp OBJECT-TYPE
			SYNTAX TimeTicks
			MAX-ACCESS read-only
			STATUS current
			DESCRIPTION
				"The time stamp of the last command (end of command)."
			::= { sheVoipMgcConfigProfileControl 16 }

		
		sheVoipMgcConfigProfileControlReqResult OBJECT-TYPE
			SYNTAX SheVoipControlRequestResultType
			MAX-ACCESS read-only
			STATUS current
			DESCRIPTION
				"The result of the last user command."
			::= { sheVoipMgcConfigProfileControl 17 }

		
		sheVoipMgcConfigProfileControlSoftswitch1 OBJECT-TYPE
			SYNTAX SheVoipMgcConfigProfileSoftswitchType
			MAX-ACCESS read-write
			STATUS current
			DESCRIPTION
				"type of softswitch1"
			::= { sheVoipMgcConfigProfileControl 18 }

		
		sheVoipMgcConfigProfileControlSoftswitch2 OBJECT-TYPE
			SYNTAX SheVoipMgcConfigProfileSoftswitchType
			MAX-ACCESS read-write
			STATUS current
			DESCRIPTION
				"type of softswitch2"
			::= { sheVoipMgcConfigProfileControl 19 }

		
		sheVoipMgcConfigProfileControlSoftswitch3 OBJECT-TYPE
			SYNTAX SheVoipMgcConfigProfileSoftswitchType
			MAX-ACCESS read-write
			STATUS current
			DESCRIPTION
				"type of softswitch3"
			::= { sheVoipMgcConfigProfileControl 20 }

		
		sheVoipMgcConfigProfileControlSoftswitch4 OBJECT-TYPE
			SYNTAX SheVoipMgcConfigProfileSoftswitchType
			MAX-ACCESS read-write
			STATUS current
			DESCRIPTION
				"type of softswitch4"
			::= { sheVoipMgcConfigProfileControl 21 }

		
		sheVoipMgcConfigProfileControlSoftswitch5 OBJECT-TYPE
			SYNTAX SheVoipMgcConfigProfileSoftswitchType
			MAX-ACCESS read-write
			STATUS current
			DESCRIPTION
				"type of softswitch5"
			::= { sheVoipMgcConfigProfileControl 22 }

		
		sheVoipH248MgConfigProfileTable OBJECT-TYPE
			SYNTAX SEQUENCE OF SheVoipH248MgConfigProfileEntry
			MAX-ACCESS not-accessible
			STATUS current
			DESCRIPTION
				"This table contains attributes for each H248Mg config profile."
			::= { sheVoipH248DataGroup 3 }

		
		sheVoipH248MgConfigProfileEntry OBJECT-TYPE
			SYNTAX SheVoipH248MgConfigProfileEntry
			MAX-ACCESS not-accessible
			STATUS current
			DESCRIPTION
				"An entry represents a set of profile configurations 
				in sheVoipH248MgConfigProfileTable.  
				"
			INDEX { sheVoipH248MgConfigProfileIndex }
			::= { sheVoipH248MgConfigProfileTable 1 }

		
		SheVoipH248MgConfigProfileEntry ::=
			SEQUENCE { 
				sheVoipH248MgConfigProfileIndex
					Unsigned32,
				sheVoipH248MgConfigProfileName
					DisplayString,
				sheVoipH248MgConfigProfileEncodingScheme
					SheVoipH248MgConfigProfileEncodingSchemeType,
				sheVoipH248MgConfigProfileProtocolVersion
					SheVoipH248MgConfigProfileProtocolVersionType,
				sheVoipH248MgConfigProfileUseTimestamp
					SheVoipH248MgConfigProfileUseTimestampType,
				sheVoipH248MgConfigProfileNamingPhyTerm
					OCTET STRING,
				sheVoipH248MgConfigProfileNamingRtpTerm
					OCTET STRING,
				sheVoipH248MgConfigProfilePkgList
					OCTET STRING,
				sheVoipH248MgConfigProfileHeartBeatTime
					Unsigned32,
				sheVoipH248MgConfigProfileRetransTime
					Unsigned32,
				sheVoipH248MgConfigProfileMaxRetransCount
					Unsigned32,
				sheVoipH248MgConfigProfileStartupType
					SheVoipH248MgConfigProfileStartupType,
				sheVoipH248MgConfigProfileMWD
					Unsigned32,
				sheVoipH248MgConfigProfileTermQuitMode
					SheVoipH248MgConfigProfileTermQuitModeType,
				sheVoipH248MgConfigProfileTcpUdpCfgProtocol
					SheVoipH248MgConfigProfileTcpUdpCfgProtocolType,
				sheVoipH248MgConfigProfileMarkTos
					Unsigned32
			 }

		sheVoipH248MgConfigProfileIndex OBJECT-TYPE
			SYNTAX Unsigned32 (1..16)
			MAX-ACCESS read-only
			STATUS current
			DESCRIPTION
				"Table index. Each index uniquely identifies one mg config profile."
			::= { sheVoipH248MgConfigProfileEntry 1 }

		
		sheVoipH248MgConfigProfileName OBJECT-TYPE
			SYNTAX DisplayString (SIZE (0..31))
			MAX-ACCESS read-only
			STATUS current
			DESCRIPTION
				"A describable name that uniquely identifies a profile entry  
				of this table.The profile name is user specified.  
				"
			::= { sheVoipH248MgConfigProfileEntry 2 }

		
		sheVoipH248MgConfigProfileEncodingScheme OBJECT-TYPE
			SYNTAX SheVoipH248MgConfigProfileEncodingSchemeType
			MAX-ACCESS read-only
			STATUS current
			DESCRIPTION
				"The encoding scheme that would be used to encode the Megaco  
				messages that are sent/received to/from the gateway controller. 
				mgTextShort (0),
				mgTextLong  (1),
				mgBinary    (2) "
			DEFVAL { mgTextLong }
			::= { sheVoipH248MgConfigProfileEntry 3 }

		
		sheVoipH248MgConfigProfileProtocolVersion OBJECT-TYPE
			SYNTAX SheVoipH248MgConfigProfileProtocolVersionType
			MAX-ACCESS read-only
			STATUS current
			DESCRIPTION
				"Type of the control protocol in use. 
				megacoV1 (1)
				megacoV2 (2)
				"
			DEFVAL { megacoV1 }
			::= { sheVoipH248MgConfigProfileEntry 4 }

		
		sheVoipH248MgConfigProfileUseTimestamp OBJECT-TYPE
			SYNTAX SheVoipH248MgConfigProfileUseTimestampType
			MAX-ACCESS read-only
			STATUS current
			DESCRIPTION
				"When a message is sended, it is decided to include the current  
				time (Timestamp)in the message. 
				(0) TimeStampNoUse  
				(1) TimeStampUse "
			DEFVAL { timeStampUse }
			::= { sheVoipH248MgConfigProfileEntry 5 }

		
		sheVoipH248MgConfigProfileNamingPhyTerm OBJECT-TYPE
			SYNTAX OCTET STRING (SIZE (0..60))
			MAX-ACCESS read-only
			STATUS current
			DESCRIPTION
				"Naming rule of physical termination in h248 message."
			::= { sheVoipH248MgConfigProfileEntry 6 }

		
		sheVoipH248MgConfigProfileNamingRtpTerm OBJECT-TYPE
			SYNTAX OCTET STRING (SIZE (0..60))
			MAX-ACCESS read-only
			STATUS current
			DESCRIPTION
				"The format of RTP termination in h248 message."
			::= { sheVoipH248MgConfigProfileEntry 7 }

		
		sheVoipH248MgConfigProfilePkgList OBJECT-TYPE
			SYNTAX OCTET STRING (SIZE (0..256))
			MAX-ACCESS read-only
			STATUS current
			DESCRIPTION
				"H.248 Package list."
			::= { sheVoipH248MgConfigProfileEntry 8 }

		
		sheVoipH248MgConfigProfileHeartBeatTime OBJECT-TYPE
			SYNTAX Unsigned32
			UNITS "sec"
			MAX-ACCESS read-only
			STATUS current
			DESCRIPTION
				"H.248 VGW HeartBeatTime(sec).  
				"
			DEFVAL { 40 }
			::= { sheVoipH248MgConfigProfileEntry 9 }

		
		sheVoipH248MgConfigProfileRetransTime OBJECT-TYPE
			SYNTAX Unsigned32
			UNITS "sec"
			MAX-ACCESS read-only
			STATUS current
			DESCRIPTION
				"H.248 VGW RetransmissionTime(sec).  
				"
			DEFVAL { 3 }
			::= { sheVoipH248MgConfigProfileEntry 10 }

		
		sheVoipH248MgConfigProfileMaxRetransCount OBJECT-TYPE
			SYNTAX Unsigned32
			MAX-ACCESS read-only
			STATUS current
			DESCRIPTION
				"H.248 VGW MaxRetransmissionCount 
				"
			DEFVAL { 3 }
			::= { sheVoipH248MgConfigProfileEntry 11 }

		
		sheVoipH248MgConfigProfileStartupType OBJECT-TYPE
			SYNTAX SheVoipH248MgConfigProfileStartupType
			MAX-ACCESS read-only
			STATUS current
			DESCRIPTION
				"Startup type of MG: 
				(1)normal : MG joins into only a MGC. 
				(2)expedited : MG joins into two MGCs. 
				(3)local   
				"
			DEFVAL { normal }
			::= { sheVoipH248MgConfigProfileEntry 12 }

		
		sheVoipH248MgConfigProfileMWD OBJECT-TYPE
			SYNTAX Unsigned32
			MAX-ACCESS read-only
			STATUS current
			DESCRIPTION
				"MWD(Max Waiting Delay)   
				"
			DEFVAL { 0 }
			::= { sheVoipH248MgConfigProfileEntry 13 }

		
		sheVoipH248MgConfigProfileTermQuitMode OBJECT-TYPE
			SYNTAX SheVoipH248MgConfigProfileTermQuitModeType
			MAX-ACCESS read-only
			STATUS current
			DESCRIPTION
				"Termination quitting mode, configured to either graceful or forced."
			DEFVAL { forced }
			::= { sheVoipH248MgConfigProfileEntry 14 }

		
		sheVoipH248MgConfigProfileTcpUdpCfgProtocol OBJECT-TYPE
			SYNTAX SheVoipH248MgConfigProfileTcpUdpCfgProtocolType
			MAX-ACCESS read-only
			STATUS current
			DESCRIPTION
				"This attribute defines the protocol types available  
				as defined by IANA. Default value is UDP (1) 
				UDP(1):default, TCP(2):not support,SCTP(3):not support.   
				"
			DEFVAL { udp }
			::= { sheVoipH248MgConfigProfileEntry 15 }

		
		sheVoipH248MgConfigProfileMarkTos OBJECT-TYPE
			SYNTAX Unsigned32 (0..255)
			MAX-ACCESS read-only
			STATUS current
			DESCRIPTION
				"Mark TOS"
			DEFVAL { 1 }
			::= { sheVoipH248MgConfigProfileEntry 16 }

		
		sheVoipH248MgConfigProfileControl OBJECT IDENTIFIER ::= { sheVoipH248DataGroup 4 }

		
		sheVoipH248MgConfigProfileControlRequest OBJECT-TYPE
			SYNTAX SheVoipControlRequestType
			MAX-ACCESS read-write
			STATUS current
			DESCRIPTION
				"The request of a user command. 
				createVoipH248MgConfigProfile    (23), 
				    Must: sheVoipH248MgConfigProfileControlName 
				    Optional:
				            sheVoipH248MgConfigProfileControlEncodingScheme 
				            sheVoipH248MgConfigProfileControlProtocolVersion  
				            sheVoipH248MgConfigProfileControlUseTimestamp 
				            sheVoipH248MgConfigProfileControlNamingPhyTerm 
				            sheVoipH248MgConfigProfileControlNamingRtpTerm  
				            sheVoipH248MgConfigProfileControlPkgList  
				            sheVoipH248MgConfigProfileControlHeartBeatTime 
				            sheVoipH248MgConfigProfileControlRetransTime 
				            sheVoipH248MgConfigProfileControlMaxRetransCount 
				            sheVoipH248MgConfigProfileControlStartupType 
				            sheVoipH248MgConfigProfileControlMWD 
				            sheVoipH248MgConfigProfileControlTermQuitMode 
				            sheVoipH248MgConfigProfileControlTcpUdpCfgProtocol 
				            sheVoipH248MgConfigProfileControlMarkTos 
				modifyVoipH248MgConfigProfile    (24), 
				    Must: sheVoipH248MgConfigProfileControlIndex 
				    Optional:sheVoipH248MgConfigProfileControlName 
				            sheVoipH248MgConfigProfileControlEncodingScheme
				    		sheVoipH248MgConfigProfileControlProtocolVersion  
				            sheVoipH248MgConfigProfileControlUseTimestamp 
				            sheVoipH248MgConfigProfileControlNamingPhyTerm 
				            sheVoipH248MgConfigProfileControlNamingRtpTerm  
				            sheVoipH248MgConfigProfileControlPkgList  
				            sheVoipH248MgConfigProfileControlHeartBeatTime 
				            sheVoipH248MgConfigProfileControlRetransTime 
				            sheVoipH248MgConfigProfileControlMaxRetransCount 
				            sheVoipH248MgConfigProfileControlStartupType 
				            sheVoipH248MgConfigProfileControlMWD 
				            sheVoipH248MgConfigProfileControlTermQuitMode 
				            sheVoipH248MgConfigProfileControlTcpUdpCfgProtocol 
				            sheVoipH248MgConfigProfileControlMarkTos 
				             
				deleteVoipH248MgConfigProfile    (25), 
				     Must: sheVoipH248MgConfigProfileControlIndex 
				"
			::= { sheVoipH248MgConfigProfileControl 1 }

		
		sheVoipH248MgConfigProfileControlIndex OBJECT-TYPE
			SYNTAX Unsigned32 (1..16)
			MAX-ACCESS read-write
			STATUS current
			DESCRIPTION
				"Table index"
			::= { sheVoipH248MgConfigProfileControl 2 }

		
		sheVoipH248MgConfigProfileControlName OBJECT-TYPE
			SYNTAX DisplayString (SIZE (0..31))
			MAX-ACCESS read-write
			STATUS current
			DESCRIPTION
				"A describable name that uniquely identifies  
				a profile entry of this table.The profile name  
				is user specified. 
				"
			::= { sheVoipH248MgConfigProfileControl 3 }

		
		sheVoipH248MgConfigProfileControlEncodingScheme OBJECT-TYPE
			SYNTAX SheVoipH248MgConfigProfileEncodingSchemeType
			MAX-ACCESS read-write
			STATUS current
			DESCRIPTION
				"The encoding scheme that would be used to encode the  
				Megaco messages that are sent/received to/from the  
				gateway controller. 
				mgTextShort (0),
				   mgTextLong  (1),
				   mgBinary	(2) "
			::= { sheVoipH248MgConfigProfileControl 4 }

		
		sheVoipH248MgConfigProfileControlProtocolVersion OBJECT-TYPE
			SYNTAX SheVoipH248MgConfigProfileProtocolVersionType
			MAX-ACCESS read-write
			STATUS current
			DESCRIPTION
				"Type of the control protocol in use. 
				megacoV1 (1) 
				megacoV2 (2) 
				"
			::= { sheVoipH248MgConfigProfileControl 5 }

		
		sheVoipH248MgConfigProfileControlUseTimestamp OBJECT-TYPE
			SYNTAX SheVoipH248MgConfigProfileUseTimestampType
			MAX-ACCESS read-write
			STATUS current
			DESCRIPTION
				"When a message is sended, it is decided to include the current  
				time (Timestamp)in the message. 
				(0) timeStampNoUse  
				(1) timeStampUse  
				"
			::= { sheVoipH248MgConfigProfileControl 6 }

		
		sheVoipH248MgConfigProfileControlNamingPhyTerm OBJECT-TYPE
			SYNTAX OCTET STRING (SIZE (0..60))
			MAX-ACCESS read-write
			STATUS current
			DESCRIPTION
				"Naming rule of physical termination in h248 message.  
				"
			::= { sheVoipH248MgConfigProfileControl 7 }

		
		sheVoipH248MgConfigProfileControlNamingRtpTerm OBJECT-TYPE
			SYNTAX OCTET STRING (SIZE (0..60))
			MAX-ACCESS read-write
			STATUS current
			DESCRIPTION
				"The format of RTP termination in h248 message.  
				"
			::= { sheVoipH248MgConfigProfileControl 8 }

		
		sheVoipH248MgConfigProfileControlPkgList OBJECT-TYPE
			SYNTAX OCTET STRING (SIZE (0..256))
			MAX-ACCESS read-write
			STATUS current
			DESCRIPTION
				"H.248 Package list.  
				"
			::= { sheVoipH248MgConfigProfileControl 9 }

		
		sheVoipH248MgConfigProfileControlHeartBeatTime OBJECT-TYPE
			SYNTAX Unsigned32
			UNITS "sec"
			MAX-ACCESS read-write
			STATUS current
			DESCRIPTION
				"H.248 VGW HeartBeatTime(sec).   
				"
			::= { sheVoipH248MgConfigProfileControl 10 }

		
		sheVoipH248MgConfigProfileControlRetransTime OBJECT-TYPE
			SYNTAX Unsigned32
			UNITS "sec"
			MAX-ACCESS read-write
			STATUS current
			DESCRIPTION
				"H.248 VGW RetransmissionTime(sec).  
				"
			::= { sheVoipH248MgConfigProfileControl 11 }

		
		sheVoipH248MgConfigProfileControlMaxRetransCount OBJECT-TYPE
			SYNTAX Unsigned32
			MAX-ACCESS read-write
			STATUS current
			DESCRIPTION
				"H.248 VGW MaxRetransmissionCount  
				"
			::= { sheVoipH248MgConfigProfileControl 12 }

		
		sheVoipH248MgConfigProfileControlStartupType OBJECT-TYPE
			SYNTAX SheVoipH248MgConfigProfileStartupType
			MAX-ACCESS read-write
			STATUS current
			DESCRIPTION
				"Startup type of MG: 
				normal : MG joins into only a MGC. 
				expedited : MG joins into two MGCs.   
				"
			::= { sheVoipH248MgConfigProfileControl 13 }

		
		sheVoipH248MgConfigProfileControlMWD OBJECT-TYPE
			SYNTAX Unsigned32
			MAX-ACCESS read-write
			STATUS current
			DESCRIPTION
				"MWD(Max Waiting Delay)    
				"
			::= { sheVoipH248MgConfigProfileControl 14 }

		
		sheVoipH248MgConfigProfileControlTermQuitMode OBJECT-TYPE
			SYNTAX SheVoipH248MgConfigProfileTermQuitModeType
			MAX-ACCESS read-write
			STATUS current
			DESCRIPTION
				"Termination quitting mode, configured to either graceful or forced."
			::= { sheVoipH248MgConfigProfileControl 15 }

		
		sheVoipH248MgConfigProfileControlTcpUdpCfgProtocol OBJECT-TYPE
			SYNTAX SheVoipH248MgConfigProfileTcpUdpCfgProtocolType
			MAX-ACCESS read-write
			STATUS current
			DESCRIPTION
				"This attribute defines the protocol types available  
				as defined by IANA. Default value is UDP (1) 
				UDP(1):default, TCP(2):not support,SCTP(3):not support.    
				"
			::= { sheVoipH248MgConfigProfileControl 16 }

		
		sheVoipH248MgConfigProfileControlMarkTos OBJECT-TYPE
			SYNTAX Unsigned32 (0..255)
			MAX-ACCESS read-write
			STATUS current
			DESCRIPTION
				"Mark TOS     
				"
			::= { sheVoipH248MgConfigProfileControl 17 }

		
		sheVoipH248MgConfigProfileControlStatus OBJECT-TYPE
			SYNTAX SheControlStatusType
			MAX-ACCESS read-only
			STATUS current
			DESCRIPTION
				"The status of a user command."
			::= { sheVoipH248MgConfigProfileControl 18 }

		
		sheVoipH248MgConfigProfileControlTimer OBJECT-TYPE
			SYNTAX Gauge32
			MAX-ACCESS read-only
			STATUS current
			DESCRIPTION
				"The maximum wait time for the manager for a  
				long running user command."
			::= { sheVoipH248MgConfigProfileControl 19 }

		
		sheVoipH248MgConfigProfileControlTimeStamp OBJECT-TYPE
			SYNTAX TimeTicks
			MAX-ACCESS read-only
			STATUS current
			DESCRIPTION
				"The time stamp of the last command (end of command)."
			::= { sheVoipH248MgConfigProfileControl 20 }

		
		sheVoipH248MgConfigProfileControlReqResult OBJECT-TYPE
			SYNTAX SheVoipControlRequestResultType
			MAX-ACCESS read-only
			STATUS current
			DESCRIPTION
				"The result of the last user command."
			::= { sheVoipH248MgConfigProfileControl 21 }

		
		sheVoipVoipDataGroup OBJECT IDENTIFIER ::= { sheVoipMibModule 3 }

		
		sheVoipMediaProfiles OBJECT IDENTIFIER ::= { sheVoipVoipDataGroup 1 }

		
		sheVoipMediaCodecProfileTable OBJECT-TYPE
			SYNTAX SEQUENCE OF SheVoipMediaCodecProfileEntry
			MAX-ACCESS not-accessible
			STATUS current
			DESCRIPTION
				"This table contains attributes for each media codec profile."
			::= { sheVoipMediaProfiles 1 }

		
		sheVoipMediaCodecProfileEntry OBJECT-TYPE
			SYNTAX SheVoipMediaCodecProfileEntry
			MAX-ACCESS not-accessible
			STATUS current
			DESCRIPTION
				"An entry represents a set of profile configurations 
				in sheVoipMediaCodecProfileTable. A default	 
				profile will always exist. This profile's name will be set to  
				`DEFVAL' and its parameters will be set to vendor specific values. 
				"
			INDEX { sheVoipMediaCodecProfileIndex }
			::= { sheVoipMediaCodecProfileTable 1 }

		
		SheVoipMediaCodecProfileEntry ::=
			SEQUENCE { 
				sheVoipMediaCodecProfileIndex
					Unsigned32,
				sheVoipMediaCodecProfileName
					DisplayString,
				sheVoipMediaCodecProfileCodecCapability
					OCTET STRING,
				sheVoipMediaCodecProfileG726PayloadType
					Unsigned32,
				sheVoipMediaCodecProfileG723Bitrate
					SheVoipMediaCodecProfileG723BitrateType,
				sheVoipMediaCodecProfileG726Bitrate
					SheVoipMediaCodecProfileG726BitrateType,
				sheVoipMediaCodecProfileCodecPTimeG711
					SheVoipMediaCodecProfileCodecPTimeG711Type,
				sheVoipMediaCodecProfileCodecPTimeG723
					SheVoipMediaCodecProfileCodecPTimeG723Type,
				sheVoipMediaCodecProfileCodecPTimeG726
					SheVoipMediaCodecProfileCodecPTimeG726Type,
				sheVoipMediaCodecProfileCodecPTimeG729
					SheVoipMediaCodecProfileCodecPTimeG711Type,
				sheVoipMediaCodecProfileEC
					INTEGER,
				sheVoipMediaCodecProfileVad
					SheVoipMediaCodecProfileVadType,
				sheVoipMediaCodecProfilePLC
					SheVoipMediaCodecProfilePLCType,
				sheVoipMediaCodecProfileCng
					SheVoipMediaCodecProfileCngType,
				sheVoipMediaCodecProfileAutoSwitchCodec
					SheVoipMediaCodecProfileAutoSwitchCodecType,
				sheVoipMediaCodecProfileG711passThruCodec
					SheVoipMediaCodecProfileG711passThruCodecType,
				sheVoipMediaCodecProfileG711passThruPayloadType
					INTEGER
			 }

		sheVoipMediaCodecProfileIndex OBJECT-TYPE
			SYNTAX Unsigned32
			MAX-ACCESS read-only
			STATUS current
			DESCRIPTION
				"Table index. Each index uniquely identifies one Media Codec Profile."
			::= { sheVoipMediaCodecProfileEntry 1 }

		
		sheVoipMediaCodecProfileName OBJECT-TYPE
			SYNTAX DisplayString (SIZE (0..31))
			MAX-ACCESS read-only
			STATUS current
			DESCRIPTION
				"A describable name that uniquely identifies a profile entry  
				of this table.The profile name is user specified. A default	 
				     profile will always exist. This profile's name will be set to  
				     `DEFVAL'."
			::= { sheVoipMediaCodecProfileEntry 2 }

		
		sheVoipMediaCodecProfileCodecCapability OBJECT-TYPE
			SYNTAX OCTET STRING (SIZE (0..5))
			MAX-ACCESS read-only
			STATUS current
			DESCRIPTION
				"Codec list to be used, ordered by priority. [value index] 
				-pcmu(0) = Use G.711U voice codec (default:2) 
				-g7231(4)=Use G.723.1 6.3kbps voice codec (default:4) 
				-pcma(8) = Use G.711A voice codec (default:1) 
				-g729(18) = Use G.729 voice codec  (default:3)  
				-g726(255) = Use G.711U voice codec (default:5) 
				"
			DEFVAL { "" }
			::= { sheVoipMediaCodecProfileEntry 3 }

		
		sheVoipMediaCodecProfileG726PayloadType OBJECT-TYPE
			SYNTAX Unsigned32 (0..255)
			MAX-ACCESS read-only
			STATUS current
			DESCRIPTION
				"sheVoipMediaProftG726PayloadType for slot[AGLU] 
				[value range] Value = <0..255> Default:2"
			DEFVAL { 2 }
			::= { sheVoipMediaCodecProfileEntry 4 }

		
		sheVoipMediaCodecProfileG723Bitrate OBJECT-TYPE
			SYNTAX SheVoipMediaCodecProfileG723BitrateType
			MAX-ACCESS read-only
			STATUS current
			DESCRIPTION
				"sheVoipMediaProfG723Bitrate for slot[AGLU] 
				[value index]					 
				bps6300(0):6.3 kbps(default) 
				bps5300(1):5.3 kbps"
			DEFVAL { bps6300 }
			::= { sheVoipMediaCodecProfileEntry 5 }

		
		sheVoipMediaCodecProfileG726Bitrate OBJECT-TYPE
			SYNTAX SheVoipMediaCodecProfileG726BitrateType
			MAX-ACCESS read-only
			STATUS current
			DESCRIPTION
				"sheVoipMediaProftG726Bitrate for slot[AGLU] 
				[value index]		 
				  gbt16kbps 		(0),                         
				  gbt24kbps 		(1), 
				  gbt32kbps		(2), 
				  gbt40kbps		(3) "
			DEFVAL { gbt32kbps }
			::= { sheVoipMediaCodecProfileEntry 6 }

		
		sheVoipMediaCodecProfileCodecPTimeG711 OBJECT-TYPE
			SYNTAX SheVoipMediaCodecProfileCodecPTimeG711Type
			MAX-ACCESS read-only
			STATUS current
			DESCRIPTION
				"Packet generation cycle of G.711 codec, also refers
				to the duration of each packet in milliseconds:   
				[value index] 
				g711pgc10msec		(0), 
				g711pgc20msec		(1), 
				g711pgc30msec		(2), 
				g711pgc40msec		(3), 
				g711pgc50msec		(4), 
				g711pgc60msec		(5)			 
				"
			DEFVAL { g711pgc10msec }
			::= { sheVoipMediaCodecProfileEntry 7 }

		
		sheVoipMediaCodecProfileCodecPTimeG723 OBJECT-TYPE
			SYNTAX SheVoipMediaCodecProfileCodecPTimeG723Type
			MAX-ACCESS read-only
			STATUS current
			DESCRIPTION
				"Packet generation cycle of G.723 codec : 
				[value index] 
				  g723pgc30msec		(0), 
				  g723pgc60msec		(1) "
			DEFVAL { g723pgc30msec }
			::= { sheVoipMediaCodecProfileEntry 8 }

		
		sheVoipMediaCodecProfileCodecPTimeG726 OBJECT-TYPE
			SYNTAX SheVoipMediaCodecProfileCodecPTimeG726Type
			MAX-ACCESS read-only
			STATUS current
			DESCRIPTION
				"Packet generation cycle of G.726 codec : 
				[value index] 
				  g726pgc10msec		(0), 
				  g726pgc20msec		(1), 
				  g726pgc30msec		(2) "
			DEFVAL { g726pgc20msec }
			::= { sheVoipMediaCodecProfileEntry 9 }

		
		sheVoipMediaCodecProfileCodecPTimeG729 OBJECT-TYPE
			SYNTAX SheVoipMediaCodecProfileCodecPTimeG711Type
			MAX-ACCESS read-only
			STATUS current
			DESCRIPTION
				"Packet generation cycle of G.729 codec : 
				[value index] 
				  g711pgc10msec		(0), 
				  g711pgc20msec		(1), 
				  g711pgc30msec		(2), 
				  g711pgc40msec		(3), 
				  g711pgc50msec		(4), 
				  g711pgc60msec		(5) "
			DEFVAL { g711pgc20msec }
			::= { sheVoipMediaCodecProfileEntry 10 }

		
		sheVoipMediaCodecProfileEC OBJECT-TYPE
			SYNTAX INTEGER (0..15)
			UNITS "8 msec"
			MAX-ACCESS read-only
			STATUS current
			DESCRIPTION
				"Use of Echo Canceler and level, for modem/fax call, this attribute
				must be set to 0.
				[value index ]     		 
				-off(0) : Echo Canceler is turned off.  
				-on(1..15) : Echo Canceler is turned on when the 
				echo cancellation is requested. 
				(step: 8 msec, default:8) "
			DEFVAL { 8 }
			::= { sheVoipMediaCodecProfileEntry 11 }

		
		sheVoipMediaCodecProfileVad OBJECT-TYPE
			SYNTAX SheVoipMediaCodecProfileVadType
			MAX-ACCESS read-only
			STATUS current
			DESCRIPTION
				"Use of Voice Activation Detection.
				The purpose of the detector is to detect silence periods in 
				the voice signal and temporarily discontinue transmission of 
				the signal during the silence period.  
				[value index] 
				off: VAD Disabled (0), 
				defaultMethod:VAD Enabled using the coding scheme's default method (1), 
				appendixIIScheme:VAD Enabled using PT13/G.711 Appendix II scheme (2) 
				"
			DEFVAL { off }
			::= { sheVoipMediaCodecProfileEntry 12 }

		
		sheVoipMediaCodecProfilePLC OBJECT-TYPE
			SYNTAX SheVoipMediaCodecProfilePLCType
			MAX-ACCESS read-only
			STATUS current
			DESCRIPTION
				"PLC(Packet Loss Concealment)for slot[AGLU], a technique used to 
				mask the effects of lost or discarded packets. PLC is generally 
				effective only for small numbers of consecutive lost packets, 
				for example a total of 20-30 milliseconds of speech, and for 
				low packet loss rates.
				
				[value index] 
				On(1)= use PLC (default) 
				Off(0)= unuse PLC 
				"
			DEFVAL { on }
			::= { sheVoipMediaCodecProfileEntry 13 }

		
		sheVoipMediaCodecProfileCng OBJECT-TYPE
			SYNTAX SheVoipMediaCodecProfileCngType
			MAX-ACCESS read-only
			STATUS current
			DESCRIPTION
				"Use of  CNG(Comfor Noise Gerneration) 
				[value index] 
				-off (0)= Unuse CNG (default) 
				-on(1) = Use CNG 
				"
			DEFVAL { off }
			::= { sheVoipMediaCodecProfileEntry 14 }

		
		sheVoipMediaCodecProfileAutoSwitchCodec OBJECT-TYPE
			SYNTAX SheVoipMediaCodecProfileAutoSwitchCodecType
			MAX-ACCESS read-only
			STATUS current
			DESCRIPTION
				"AutoSwitch may happen autonomously when an RTP frame with an unexpected 
				payload type is encountered.An unexpected payload type is defined as a payload 
				type that does not fit into one of the following categories:
				Current Voice payload type – these packets are decoded as voice.
				RTP Comfort Noise payload type – these packets generate the appropriate comfort
				noise to the TDM inerface.
				DTMF in RTP packets – these packets either are decoded as DTMF digits and generated
				to the TDM interface, or signaled to the host via the NTERCVD function code.
				Dynamic payload type packets – when the payload type is in the dynamic range
				(values 96 and above), the device cannot know whether the packet is valid or not, 
				and so they are silently discarded.  
				AutoSwitchCodec
				[value index] 
				off(0), 
				pcma(1),  
				pcmu(2) 
				"
			DEFVAL { off }
			::= { sheVoipMediaCodecProfileEntry 15 }

		
		sheVoipMediaCodecProfileG711passThruCodec OBJECT-TYPE
			SYNTAX SheVoipMediaCodecProfileG711passThruCodecType
			MAX-ACCESS read-only
			STATUS current
			DESCRIPTION
				"used only when sheVoipMediaFaxProfileFaxTypeUsed is set to t30auto or
				sheVoipMediaFaxProfileModemDetect is set to modemAuto.
				[value index]
				-pcma(1) = Use G.711A voice codec
				-pcmu(2) = Use G.711U voice codec
				"
			DEFVAL { pcma }
			::= { sheVoipMediaCodecProfileEntry 16 }

		
		sheVoipMediaCodecProfileG711passThruPayloadType OBJECT-TYPE
			SYNTAX INTEGER (1..255)
			MAX-ACCESS read-only
			STATUS current
			DESCRIPTION
				"G.711 pass through payload type."
			DEFVAL { 8 }
			::= { sheVoipMediaCodecProfileEntry 17 }

		
		sheVoipMediaCodecProfileControl OBJECT IDENTIFIER ::= { sheVoipMediaProfiles 2 }

		
		sheVoipMediaCodecProfileControlRequest OBJECT-TYPE
			SYNTAX SheVoipControlRequestType
			MAX-ACCESS read-write
			STATUS current
			DESCRIPTION
				"The request of a user command. 
				createVoipMediaCodecProfile  (30),            
				         	Must:		sheVoipMediaCodecProfileControlName 				 
				         	Optional:	sheVoipMediaCodecProfileControlCodecCapability			 
				         			sheVoipMediaCodecProfileControlG726PayloadType  	       	            
				         			sheVoipMediaCodecProfileControlG723Bitrate			        	 
				         			sheVoipMediaCodecProfileControlG726Bitrate  		             
				         			sheVoipMediaCodecProfileControlCodecPTimeG711 		    
				     				sheVoipMediaCodecProfileControlCodecPTimeG723  	    
				     				sheVoipMediaCodecProfileControlCodecPTimeG726 	 
				     				sheVoipMediaCodecProfileControlCodecPTimeG729 		 
				     				sheVoipMediaCodecProfileControlEC 					 
				     				sheVoipMediaCodecProfileControlVad 				  
				     				sheVoipMediaCodecProfileControlPLC					 
				     				sheVoipMediaCodecProfileControlCng					 
				     				sheVoipMediaCodecProfileControlAutoSwitchCodec
				     				sheVoipMediaCodecProfileControlG711passThruCodec
				     				sheVoipMediaCodecProfileControlG711passThruPayloadType       	 
				     	 	 
				modifyVoipMediaCodecProfile  (31), 
				         	Must:	 sheVoipMediaCodecProfileControlIndex	 				 
				         	Optional:sheVoipMediaCodecProfileControlName	 
				         			sheVoipMediaCodecProfileControlCodecCapability			 
				         			sheVoipMediaCodecProfileControlG726PayloadType  	       	            
				         			sheVoipMediaCodecProfileControlG723Bitrate			        	 
				         			sheVoipMediaCodecProfileControlG726Bitrate  		             
				         			sheVoipMediaCodecProfileControlCodecPTimeG711 		    
				     				sheVoipMediaCodecProfileControlCodecPTimeG723  	    
				     				sheVoipMediaCodecProfileControlCodecPTimeG726 	 
				     				sheVoipMediaCodecProfileControlCodecPTimeG729 		 
				     				sheVoipMediaCodecProfileControlEC 					 
				     				sheVoipMediaCodecProfileControlVad 				  
				     				sheVoipMediaCodecProfileControlPLC					 
				     				sheVoipMediaCodecProfileControlCng					 
				     				sheVoipMediaCodecProfileControlAutoSwitchCodec
				     				sheVoipMediaCodecProfileControlG711passThruCodec
				     				sheVoipMediaCodecProfileControlG711passThruPayloadType 			 
				 
				deleteVoipMediaCodecProfile  (32), 
				        		Must:	 sheVoipMediaCodecProfileControlIndex						 
				"
			::= { sheVoipMediaCodecProfileControl 1 }

		
		sheVoipMediaCodecProfileControlIndex OBJECT-TYPE
			SYNTAX Unsigned32
			MAX-ACCESS read-write
			STATUS current
			DESCRIPTION
				"Table index"
			::= { sheVoipMediaCodecProfileControl 2 }

		
		sheVoipMediaCodecProfileControlName OBJECT-TYPE
			SYNTAX DisplayString (SIZE (0..31))
			MAX-ACCESS read-write
			STATUS current
			DESCRIPTION
				"A describable name that uniquely identifies a  
				profile entry of this table.The profile name is  
				user specified.A default profile will always exist.  
				This profile's name will be set to `DEFVAL'."
			::= { sheVoipMediaCodecProfileControl 3 }

		
		sheVoipMediaCodecProfileControlCodecCapability OBJECT-TYPE
			SYNTAX OCTET STRING (SIZE (0..5))
			MAX-ACCESS read-write
			STATUS current
			DESCRIPTION
				"Codec list to be used, ordered by priority. [value index] 
				-pcmu(0) = Use G.711U voice codec (default:2) 
				-g7231(4)=Use G.723.1 6.3kbps voice codec (default:4) 
				-pcma(8) = Use G.711A voice codec (default:1) 
				-g729(18) = Use G.729 voice codec  (default:3)  
				-g726(255) = Use G.711U voice codec (default:5) 
				"
			::= { sheVoipMediaCodecProfileControl 4 }

		
		sheVoipMediaCodecProfileControlG726PayloadType OBJECT-TYPE
			SYNTAX Unsigned32
			MAX-ACCESS read-write
			STATUS current
			DESCRIPTION
				"sheVoipMediaProftG726PayloadType for slot[AGLU] 
				[value range] Value = <0..255> Default:2 
				"
			::= { sheVoipMediaCodecProfileControl 5 }

		
		sheVoipMediaCodecProfileControlG723Bitrate OBJECT-TYPE
			SYNTAX SheVoipMediaCodecProfileG723BitrateType
			MAX-ACCESS read-write
			STATUS current
			DESCRIPTION
				"sheVoipMediaProfG723Bitrate for slot[AGLU] 
				[value index]					 
				bps6300(0):6.3 kbps(default) 
				bps5300(1):5.3 kbps 
				"
			::= { sheVoipMediaCodecProfileControl 6 }

		
		sheVoipMediaCodecProfileControlG726Bitrate OBJECT-TYPE
			SYNTAX SheVoipMediaCodecProfileG726BitrateType
			MAX-ACCESS read-write
			STATUS current
			DESCRIPTION
				"sheVoipMediaProftG726Bitrate for slot[AGLU] 
				[value index]		 
				  gbt16kbps 	(0),                         
				  gbt24kbps 	(1), 
				  gbt32kbps	(2), 
				  gbt40kbps	(3) 
				"
			::= { sheVoipMediaCodecProfileControl 7 }

		
		sheVoipMediaCodecProfileControlCodecPTimeG711 OBJECT-TYPE
			SYNTAX SheVoipMediaCodecProfileCodecPTimeG711Type
			MAX-ACCESS read-write
			STATUS current
			DESCRIPTION
				"Packet generation cycle of G.711 codec.:   
				[value index] 
				  g711pgc10msec		(0), 
				  g711pgc20msec		(1), 
				  g711pgc30msec		(2), 
				  g711pgc40msec		(3), 
				  g711pgc50msec		(4), 
				  g711pgc60msec		(5) 
				"
			::= { sheVoipMediaCodecProfileControl 8 }

		
		sheVoipMediaCodecProfileControlCodecPTimeG723 OBJECT-TYPE
			SYNTAX SheVoipMediaCodecProfileCodecPTimeG723Type
			MAX-ACCESS read-write
			STATUS current
			DESCRIPTION
				"Packet generation cycle of G.723 codec : 
				[value index] 
				  g723pgc30msec		(0), 
				  g723pgc60msec		(1) 
				"
			::= { sheVoipMediaCodecProfileControl 9 }

		
		sheVoipMediaCodecProfileControlCodecPTimeG726 OBJECT-TYPE
			SYNTAX SheVoipMediaCodecProfileCodecPTimeG726Type
			MAX-ACCESS read-write
			STATUS current
			DESCRIPTION
				"Packet generation cycle of G.726 codec : 
				[value index] 
				  g726pgc10msec		(0), 
				  g726pgc20msec		(1), 
				  g726pgc30msec		(2) 
				"
			::= { sheVoipMediaCodecProfileControl 10 }

		
		sheVoipMediaCodecProfileControlCodecPTimeG729 OBJECT-TYPE
			SYNTAX SheVoipMediaCodecProfileCodecPTimeG711Type
			MAX-ACCESS read-write
			STATUS current
			DESCRIPTION
				"Packet generation cycle of G.729 codec : 
				[value index] 
					-10 = Time in msec  
					-20 = Time in msec (default)  		 
					-30 = Time in msec 
					-40 = Time in msec  
					-50 = Time in msec   		 
					-60 = Time in msec 
				"
			::= { sheVoipMediaCodecProfileControl 11 }

		
		sheVoipMediaCodecProfileControlEC OBJECT-TYPE
			SYNTAX INTEGER (0..15)
			UNITS "8 msec"
			MAX-ACCESS read-write
			STATUS current
			DESCRIPTION
				"Use of Echo Canceler and level 
				[value index ]     		 
				-off(0) : disable  
				-on(1..15) : On Echo Canceler  
				(step: 8 msec, default:8) 
				"
			::= { sheVoipMediaCodecProfileControl 12 }

		
		sheVoipMediaCodecProfileControlVad OBJECT-TYPE
			SYNTAX SheVoipMediaCodecProfileVadType
			MAX-ACCESS read-write
			STATUS current
			DESCRIPTION
				"Use of Voice Activation Detection.  
				[value index] 
				off 		    (0), 
				defaultMethod	    (1), 
				appendixIIScheme    (2)  
				"
			::= { sheVoipMediaCodecProfileControl 13 }

		
		sheVoipMediaCodecProfileControlPLC OBJECT-TYPE
			SYNTAX SheVoipMediaCodecProfilePLCType
			MAX-ACCESS read-write
			STATUS current
			DESCRIPTION
				"PLC(Packet Loss Concealment)for slot[AGLU] 
				[value index] 
				On(1)= use PLC (default) 
				Off(0)= unuse PLC 
				"
			::= { sheVoipMediaCodecProfileControl 14 }

		
		sheVoipMediaCodecProfileControlCng OBJECT-TYPE
			SYNTAX SheVoipMediaCodecProfileCngType
			MAX-ACCESS read-write
			STATUS current
			DESCRIPTION
				"Use of  CNG(Comfor Noise Gerneration) 
				[value index] 
				-off (0)= Unuse CNG (default) 
				-on(1) = Use CNG 
				"
			::= { sheVoipMediaCodecProfileControl 15 }

		
		sheVoipMediaCodecProfileControlAutoSwitchCodec OBJECT-TYPE
			SYNTAX SheVoipMediaCodecProfileAutoSwitchCodecType
			MAX-ACCESS read-write
			STATUS current
			DESCRIPTION
				"AutoSwitchCodec  
				[value index] 
				off(0), 
				pcma(1),  
				pcmu(2) 
				"
			::= { sheVoipMediaCodecProfileControl 16 }

		
		sheVoipMediaCodecProfileControlG711passThruCodec OBJECT-TYPE
			SYNTAX SheVoipMediaCodecProfileG711passThruCodecType
			MAX-ACCESS read-write
			STATUS current
			DESCRIPTION
				"[value index]
				-pcma(1) = Use G.711A voice codec
				-pcmu(2) = Use G.711U voice codec
				"
			::= { sheVoipMediaCodecProfileControl 17 }

		
		sheVoipMediaCodecProfileControlG711passThruPayloadType OBJECT-TYPE
			SYNTAX INTEGER (1..255)
			MAX-ACCESS read-write
			STATUS current
			DESCRIPTION
				"G.711 pass through payload type
				"
			::= { sheVoipMediaCodecProfileControl 18 }

		
		sheVoipMediaCodecProfileControlStatus OBJECT-TYPE
			SYNTAX SheControlStatusType
			MAX-ACCESS read-only
			STATUS current
			DESCRIPTION
				"The status of a user command."
			::= { sheVoipMediaCodecProfileControl 19 }

		
		sheVoipMediaCodecProfileControlTimer OBJECT-TYPE
			SYNTAX Gauge32
			MAX-ACCESS read-only
			STATUS current
			DESCRIPTION
				"The maximum wait time for the manager for a  
				long running user command."
			::= { sheVoipMediaCodecProfileControl 20 }

		
		sheVoipMediaCodecProfileControlTimeStamp OBJECT-TYPE
			SYNTAX TimeTicks
			MAX-ACCESS read-only
			STATUS current
			DESCRIPTION
				"The time stamp of the last command (end of command)."
			::= { sheVoipMediaCodecProfileControl 21 }

		
		sheVoipMediaCodecProfileControlReqResult OBJECT-TYPE
			SYNTAX SheVoipControlRequestResultType
			MAX-ACCESS read-only
			STATUS current
			DESCRIPTION
				"The result of the last user command."
			::= { sheVoipMediaCodecProfileControl 22 }

		
		sheVoipMediaJitterBufProfileTable OBJECT-TYPE
			SYNTAX SEQUENCE OF SheVoipMediaJitterBufProfileEntry
			MAX-ACCESS not-accessible
			STATUS current
			DESCRIPTION
				"This table contains attributes for each jitter buffer profile."
			::= { sheVoipMediaProfiles 3 }

		
		sheVoipMediaJitterBufProfileEntry OBJECT-TYPE
			SYNTAX SheVoipMediaJitterBufProfileEntry
			MAX-ACCESS not-accessible
			STATUS current
			DESCRIPTION
				"An entry represents a set of profile configurations 
				in sheVoipMediaJitterBufProfileTable. A default	 
				profile will always exist. This profile's name will be set to  
				`DEFVAL' and its parameters will be set to vendor specific values. 
				"
			INDEX { sheVoipMediaJitterBufProfileIndex }
			::= { sheVoipMediaJitterBufProfileTable 1 }

		
		SheVoipMediaJitterBufProfileEntry ::=
			SEQUENCE { 
				sheVoipMediaJitterBufProfileIndex
					Unsigned32,
				sheVoipMediaJitterBufProfileName
					DisplayString,
				sheVoipMediaJitterBufProfileJitterMode
					SheVoipMediaJitterBufProfileJitterModeType,
				sheVoipMediaJitterBufProfileJitterMin
					Unsigned32,
				sheVoipMediaJitterBufProfileJitterMax
					Unsigned32,
				sheVoipMediaJitterBufProfileJitterInit
					Unsigned32,
				sheVoipMediaJitterBufProfileJitterUpdatePeriod
					Unsigned32,
				sheVoipMediaJitterBufProfileJitterDelThreshold
					Unsigned32,
				sheVoipMediaJitterBufProfileJitterFaxModem
					Unsigned32
			 }

		sheVoipMediaJitterBufProfileIndex OBJECT-TYPE
			SYNTAX Unsigned32
			MAX-ACCESS read-only
			STATUS current
			DESCRIPTION
				"Table index. Each index uniquely identifies one jitter buffer Profile."
			::= { sheVoipMediaJitterBufProfileEntry 1 }

		
		sheVoipMediaJitterBufProfileName OBJECT-TYPE
			SYNTAX DisplayString (SIZE (0..31))
			MAX-ACCESS read-only
			STATUS current
			DESCRIPTION
				"A describable name that uniquely identifies a profile entry  
				of this table.The profile name is user specified. A default	 
				profile will always exist. This profile's name will be set to  
				`DEFVAL'."
			::= { sheVoipMediaJitterBufProfileEntry 2 }

		
		sheVoipMediaJitterBufProfileJitterMode OBJECT-TYPE
			SYNTAX SheVoipMediaJitterBufProfileJitterModeType
			MAX-ACCESS read-only
			STATUS current
			DESCRIPTION
				"dynamic(0): (default) the size of the adaptive jitter buffer changes dynamically 
				with the network jitter. 
				static(1) : the size of the jitter buffer is fixed. This configuration 
				is recommended for modem/fax over G711. 
				"
			DEFVAL { dynamic }
			::= { sheVoipMediaJitterBufProfileEntry 3 }

		
		sheVoipMediaJitterBufProfileJitterMin OBJECT-TYPE
			SYNTAX Unsigned32 (0..200)
			MAX-ACCESS read-only
			STATUS current
			DESCRIPTION
				"The JitterMin and JitterMax control the minimum and maximum jitter buffer size, 
				even when the measured jitter would allow a smaller or larger jitter buffer.
				Jitter Min Size : 
				
				[value range] 
				value = <0..200> 
				default(0) 
				"
			DEFVAL { 0 }
			::= { sheVoipMediaJitterBufProfileEntry 4 }

		
		sheVoipMediaJitterBufProfileJitterMax OBJECT-TYPE
			SYNTAX Unsigned32 (0..200)
			MAX-ACCESS read-only
			STATUS current
			DESCRIPTION
				"MGC sends max size on jitter buffer to hiX if the jittermode is static, then 
				jitter min and jitter init will be the same as jitter max,
				Jitter Max Size :
				[value range] 
				value = <0..200>  
				default(200) 
				"
			DEFVAL { 200 }
			::= { sheVoipMediaJitterBufProfileEntry 5 }

		
		sheVoipMediaJitterBufProfileJitterInit OBJECT-TYPE
			SYNTAX Unsigned32 (0..200)
			MAX-ACCESS read-only
			STATUS current
			DESCRIPTION
				"Controls the initial delay of the jitter buffer.
				Jitter Init Size : 
				
				[value range] 
				value = <0..200> 
				default(0) 
				"
			DEFVAL { 0 }
			::= { sheVoipMediaJitterBufProfileEntry 6 }

		
		sheVoipMediaJitterBufProfileJitterUpdatePeriod OBJECT-TYPE
			SYNTAX Unsigned32 (1000..65535)
			UNITS "msec"
			MAX-ACCESS read-only
			STATUS current
			DESCRIPTION
				"Jitter Update Period :  
				[value range] 
				value = <1000..65535> msec 
				default(10000) 
				"
			DEFVAL { 10000 }
			::= { sheVoipMediaJitterBufProfileEntry 7 }

		
		sheVoipMediaJitterBufProfileJitterDelThreshold OBJECT-TYPE
			SYNTAX Unsigned32 (0..500)
			UNITS "msec"
			MAX-ACCESS read-only
			STATUS current
			DESCRIPTION
				"When the jitter buffer grows past the Deletion Threshold, frames exceeding 
				the deletion threshold are deleted immediately. Audio quality may be 
				negatively affected.
				JitterDelThreshold : 
				
				[value range] 
				value = <0..500> msec 
				default(500)  
				"
			DEFVAL { 500 }
			::= { sheVoipMediaJitterBufProfileEntry 8 }

		
		sheVoipMediaJitterBufProfileJitterFaxModem OBJECT-TYPE
			SYNTAX Unsigned32 (0..200)
			UNITS "msec"
			MAX-ACCESS read-only
			STATUS current
			DESCRIPTION
				"Jitter buffer size used on hiX, applied only to fax. 
				[value range] 
				value = <0..200> msec 
				default(100)  
				"
			DEFVAL { 100 }
			::= { sheVoipMediaJitterBufProfileEntry 9 }

		
		sheVoipMediaJitterBufProfileControl OBJECT IDENTIFIER ::= { sheVoipMediaProfiles 4 }

		
		sheVoipMediaJitterBufProfileControlRequest OBJECT-TYPE
			SYNTAX SheVoipControlRequestType
			MAX-ACCESS read-write
			STATUS current
			DESCRIPTION
				"The request of a user command. 
				createVoipMediaJitterBufProfile    (33), 
				             Must: sheVoipMediaJitterBufProfileControlName 
				    Optional: sheVoipMediaJitterBufProfileControlJitterMode			 
				         			  sheVoipMediaJitterBufProfileControlJitterMin  			       	            
				         			  sheVoipMediaJitterBufProfileControlJitterMax			       	 
				         			  sheVoipMediaJitterBufProfileControlJitterInit  		             
				         			  sheVoipMediaJitterBufProfileControlJitterUpdatePeriod 	    
				     				  sheVoipMediaJitterBufProfileControlJitterDelThreshold
				     				  sheVoipMediaJitterBufProfileControlJitterFaxModem 
				        	 
				     	modifyVoipMediaJitterBufProfile    (34), 
				     		Must: sheVoipMediaJitterBufProfileControlIndex 
					Optional: sheVoipMediaJitterBufProfileControlName 				 
				         			  sheVoipMediaJitterBufProfileControlJitterMode			 
				         			  sheVoipMediaJitterBufProfileControlJitterMin  			       	            
				         			  sheVoipMediaJitterBufProfileControlJitterMax			       	 
				         			  sheVoipMediaJitterBufProfileControlJitterInit  		             
				         			  sheVoipMediaJitterBufProfileControlJitterUpdatePeriod 	    
				     				  sheVoipMediaJitterBufProfileControlJitterDelThreshold
				     				  sheVoipMediaJitterBufProfileControlJitterFaxModem 
				     				   
				deleteVoipMediaJitterBufProfile    (35) 
				    Must: sheVoipMediaJitterBufProfileControlIndex 
				"
			::= { sheVoipMediaJitterBufProfileControl 1 }

		
		sheVoipMediaJitterBufProfileControlIndex OBJECT-TYPE
			SYNTAX Unsigned32
			MAX-ACCESS read-write
			STATUS current
			DESCRIPTION
				"Table index"
			::= { sheVoipMediaJitterBufProfileControl 2 }

		
		sheVoipMediaJitterBufProfileControlName OBJECT-TYPE
			SYNTAX DisplayString (SIZE (0..31))
			MAX-ACCESS read-write
			STATUS current
			DESCRIPTION
				"A describable name that uniquely identifies a  
				profile entry of this table.The profile name is  
				user specified. A default profile will always exist.  
				This profile's name will be set to `DEFVAL'."
			::= { sheVoipMediaJitterBufProfileControl 3 }

		
		sheVoipMediaJitterBufProfileControlJitterMode OBJECT-TYPE
			SYNTAX SheVoipMediaJitterBufProfileJitterModeType
			MAX-ACCESS read-write
			STATUS current
			DESCRIPTION
				"[value index] 
				dynamic(0): (default)the size of the adaptive jitter buffer changes dynamically 
				   with the network jitter. 
				   static(1) : the size of the jitter buffer is fixed. This configuration 
				   is recommended for modem/fax over G711. 
				"
			::= { sheVoipMediaJitterBufProfileControl 4 }

		
		sheVoipMediaJitterBufProfileControlJitterMin OBJECT-TYPE
			SYNTAX Unsigned32 (0..200)
			MAX-ACCESS read-write
			STATUS current
			DESCRIPTION
				"The JitterMin and JitterMax control the minimum and maximum jitter buffer size, 
				even when the measured jitter would allow a smaller or larger jitter buffer.
				Jitter Min Size : 
				[value range] 
				value = <0..200> 
				default(0) 
				"
			::= { sheVoipMediaJitterBufProfileControl 5 }

		
		sheVoipMediaJitterBufProfileControlJitterMax OBJECT-TYPE
			SYNTAX Unsigned32 (0..200)
			MAX-ACCESS read-write
			STATUS current
			DESCRIPTION
				"MGC sends max size on jitter buffer to hiX if the jittermode is static, then 
				jitter min and jitter init will be the same as jitter max,
				Jitter Max Size : 
				
				[value range] 
				value = <0..200>  
				default(200) 
				"
			::= { sheVoipMediaJitterBufProfileControl 6 }

		
		sheVoipMediaJitterBufProfileControlJitterInit OBJECT-TYPE
			SYNTAX Unsigned32 (0..200)
			MAX-ACCESS read-write
			STATUS current
			DESCRIPTION
				"Controls the initial delay of the jitter buffer.
				Jitter Init Size : 
				[value range] 
				value = <0..200> 
				default(0) 
				"
			::= { sheVoipMediaJitterBufProfileControl 7 }

		
		sheVoipMediaJitterBufProfileControlJitterUpdatePeriod OBJECT-TYPE
			SYNTAX Unsigned32 (1000..65535)
			UNITS "msec"
			MAX-ACCESS read-write
			STATUS current
			DESCRIPTION
				"Jitter Update Period :  
				[value range] 
				value = <1000..65535> msec 
				default(10000) 
				"
			::= { sheVoipMediaJitterBufProfileControl 8 }

		
		sheVoipMediaJitterBufProfileControlJitterDelThreshold OBJECT-TYPE
			SYNTAX Unsigned32 (0..500)
			UNITS "msec"
			MAX-ACCESS read-write
			STATUS current
			DESCRIPTION
				"When the jitter buffer grows past the Deletion Threshold, frames exceeding 
				the deletion threshold are deleted immediately. Audio quality may be 
				negatively affected.
				     JitterDelThreshold : 
				[value range] 
				value = <0..500> msec 
				default(500)  
				"
			::= { sheVoipMediaJitterBufProfileControl 9 }

		
		sheVoipMediaJitterBufProfileControlJitterFaxModem OBJECT-TYPE
			SYNTAX Unsigned32 (0..200)
			UNITS "msec"
			MAX-ACCESS read-write
			STATUS current
			DESCRIPTION
				"Jitter buffer size used on hiX, applied only to fax. 
				[value range] 
				value = <0..200> msec 
				default(100)  
				"
			::= { sheVoipMediaJitterBufProfileControl 10 }

		
		sheVoipMediaJitterBufProfileControlStatus OBJECT-TYPE
			SYNTAX SheControlStatusType
			MAX-ACCESS read-only
			STATUS current
			DESCRIPTION
				"The status of a user command."
			::= { sheVoipMediaJitterBufProfileControl 11 }

		
		sheVoipMediaJitterBufProfileControlTimer OBJECT-TYPE
			SYNTAX Gauge32
			MAX-ACCESS read-only
			STATUS current
			DESCRIPTION
				"The maximum wait time for the manager for a  
				long running user command."
			::= { sheVoipMediaJitterBufProfileControl 12 }

		
		sheVoipMediaJitterBufProfileControlTimeStamp OBJECT-TYPE
			SYNTAX TimeTicks
			MAX-ACCESS read-only
			STATUS current
			DESCRIPTION
				"The time stamp of the last command (end of command)."
			::= { sheVoipMediaJitterBufProfileControl 13 }

		
		sheVoipMediaJitterBufProfileControlReqResult OBJECT-TYPE
			SYNTAX SheVoipControlRequestResultType
			MAX-ACCESS read-only
			STATUS current
			DESCRIPTION
				"The result of the last user command."
			::= { sheVoipMediaJitterBufProfileControl 14 }

		
		sheVoipMediaFaxProfileTable OBJECT-TYPE
			SYNTAX SEQUENCE OF SheVoipMediaFaxProfileEntry
			MAX-ACCESS not-accessible
			STATUS current
			DESCRIPTION
				"This table contains attributes for each fax profile."
			::= { sheVoipMediaProfiles 5 }

		
		sheVoipMediaFaxProfileEntry OBJECT-TYPE
			SYNTAX SheVoipMediaFaxProfileEntry
			MAX-ACCESS not-accessible
			STATUS current
			DESCRIPTION
				"An entry represents a set of profile configurations 
				in sheVoipMediaFaxProfileTable.A default	 
				profile will always exist. This profile's name will be set to  
				`DEFVAL' and its parameters will be set to vendor specific values. 
				"
			INDEX { sheVoipMediaFaxProfileIndex }
			::= { sheVoipMediaFaxProfileTable 1 }

		
		SheVoipMediaFaxProfileEntry ::=
			SEQUENCE { 
				sheVoipMediaFaxProfileIndex
					Unsigned32,
				sheVoipMediaFaxProfileName
					DisplayString,
				sheVoipMediaFaxProfileModemDetect
					SheVoipMediaFaxProfileModemDetectType,
				sheVoipMediaFaxProfileFaxTypeUsed
					SheVoipMediaFaxProfileFaxTypeUsedType,
				sheVoipMediaFaxProfileFaxMaxBaudrate
					SheVoipMediaFaxProfileFaxMaxBaudrateType,
				sheVoipMediaFaxProfileT38FaxEcm
					SheVoipMediaFaxProfileT38FaxEcmType,
				sheVoipMediaFaxProfileT38FaxTcfmode
					SheVoipMediaFaxProfileT38FaxTcfmodeType,
				sheVoipMediaFaxProfileT38FaxNumFec
					Unsigned32,
				sheVoipMediaFaxProfileT38FaxNumIfp
					Unsigned32,
				sheVoipMediaFaxProfileT38FaxBytemode
					SheVoipMediaFaxProfileT38FaxBytemodeType
			 }

		sheVoipMediaFaxProfileIndex OBJECT-TYPE
			SYNTAX Unsigned32
			MAX-ACCESS read-only
			STATUS current
			DESCRIPTION
				"Table index. Each index uniquely identifies one  
				Fax Profile."
			::= { sheVoipMediaFaxProfileEntry 1 }

		
		sheVoipMediaFaxProfileName OBJECT-TYPE
			SYNTAX DisplayString (SIZE (0..31))
			MAX-ACCESS read-only
			STATUS current
			DESCRIPTION
				"A describable name that uniquely identifies a profile entry  
				of this table.The profile name is user specified. A default	 
				profile will always exist. This profile's name will be set to  
				`DEFVAL'."
			::= { sheVoipMediaFaxProfileEntry 2 }

		
		sheVoipMediaFaxProfileModemDetect OBJECT-TYPE
			SYNTAX SheVoipMediaFaxProfileModemDetectType
			MAX-ACCESS read-only
			STATUS current
			DESCRIPTION
				"Control the way of modem call setup.
				Modem Detection 
				[value index] 
				modemOff 	(0), 
				modemAuto 	(1),
				modemMgc	(2)  --default
				"
			DEFVAL { modemMgc }
			::= { sheVoipMediaFaxProfileEntry 3 }

		
		sheVoipMediaFaxProfileFaxTypeUsed OBJECT-TYPE
			SYNTAX SheVoipMediaFaxProfileFaxTypeUsedType
			MAX-ACCESS read-only
			STATUS current
			DESCRIPTION
				"Control the way and type of fax call setup. When setting to t30/t38auto,
				MG will NOT report the fax events to MGC and automatically change to T.30/T.38 
				fax mode from voice mode when receiving related events from TDM or RTP side.
				When setting to t30/t38mgc, MG will report the fax events to MGC when receiving 
				related events from TDM or RTP side. MGC should support T.38 negociation, sending 
				modified msg to MG and changing to T.38 fax mode.
				[value index]     		 
				faxOff	(0),
				t30auto (1), 
				t30mgc	(2), 
				t38auto (3), 
				t38mgc	(4)
				"
			DEFVAL { t30mgc }
			::= { sheVoipMediaFaxProfileEntry 4 }

		
		sheVoipMediaFaxProfileFaxMaxBaudrate OBJECT-TYPE
			SYNTAX SheVoipMediaFaxProfileFaxMaxBaudrateType
			MAX-ACCESS read-only
			STATUS current
			DESCRIPTION
				"Use of  Fax Max Baudrate: 
				[value index] 
				no-speed(0): no speed limit
				2400bps(1): 
				4800bps(2): 
				7200bps(3): 
				9600bps(4): 
				12000bps(5): 
				14400bps(6): 
				"
			::= { sheVoipMediaFaxProfileEntry 5 }

		
		sheVoipMediaFaxProfileT38FaxEcm OBJECT-TYPE
			SYNTAX SheVoipMediaFaxProfileT38FaxEcmType
			MAX-ACCESS read-only
			STATUS current
			DESCRIPTION
				"T38 Fax Error Correction Mode :
				[value index]	 
				off(0): Fax Error Correction Mode 
				on(1) : (default) Allow ECM faxes in T.38"
			DEFVAL { on }
			::= { sheVoipMediaFaxProfileEntry 6 }

		
		sheVoipMediaFaxProfileT38FaxTcfmode OBJECT-TYPE
			SYNTAX SheVoipMediaFaxProfileT38FaxTcfmodeType
			MAX-ACCESS read-only
			STATUS current
			DESCRIPTION
				"This parameter selects the TCF(training confirmation fax) procedure to be used in fax mode. 
				For TCF procedure 1, the TCF data is not passed across the IP network. 
				Each gateway independently generates or checks the TCF and only the 
				result of the training is passed over the network. For TCF procedure 2, 
				the TCF data is passed across the IP network in the same way as any 
				other page data.
				[value index] 
				Procedure2(0):  
				Procedure1(1) : Default 
				"
			DEFVAL { procedure1 }
			::= { sheVoipMediaFaxProfileEntry 7 }

		
		sheVoipMediaFaxProfileT38FaxNumFec OBJECT-TYPE
			SYNTAX Unsigned32 (0..3)
			MAX-ACCESS read-only
			STATUS current
			DESCRIPTION
				"Fax Forward Error Correction 
				[value range] 
				<0..3> 
				Default(0) "
			DEFVAL { 0 }
			::= { sheVoipMediaFaxProfileEntry 8 }

		
		sheVoipMediaFaxProfileT38FaxNumIfp OBJECT-TYPE
			SYNTAX Unsigned32 (0..4)
			MAX-ACCESS read-only
			STATUS current
			DESCRIPTION
				"Internet Fax Protocol 
				[value range]<0..4> 
				Default(0)"
			DEFVAL { 0 }
			::= { sheVoipMediaFaxProfileEntry 9 }

		
		sheVoipMediaFaxProfileT38FaxBytemode OBJECT-TYPE
			SYNTAX SheVoipMediaFaxProfileT38FaxBytemodeType
			MAX-ACCESS read-only
			STATUS current
			DESCRIPTION
				"T38 Byte or Frame Mode			 
				[value index] 
				Bytemode(0): (default)  
				Framemode(1):  
				"
			DEFVAL { bytemode }
			::= { sheVoipMediaFaxProfileEntry 10 }

		
		sheVoipMediaFaxProfileControl OBJECT IDENTIFIER ::= { sheVoipMediaProfiles 6 }

		
		sheVoipMediaFaxProfileControlRequest OBJECT-TYPE
			SYNTAX SheVoipControlRequestType
			MAX-ACCESS read-write
			STATUS current
			DESCRIPTION
				"The request of a user command.  
				createVoipMediaFaxProfile    (36), 
				    Must:  sheVoipMediaFaxProfileControlName 
				    Optional:   sheVoipMediaFaxProfileControlModemDetect		 
				         	sheVoipMediaFaxProfileControlFaxTypeUsed   			       	            
				         	sheVoipMediaFaxProfileControlFaxMaxBaudrate	        	 
				         	sheVoipMediaFaxProfileControlT38FaxEcm  		             
				         	sheVoipMediaFaxProfileControlT38FaxTcfmode 	    
				     		sheVoipMediaFaxProfileControlT38FaxNumFec  	 
				     		sheVoipMediaFaxProfileControlT38FaxNumIfp  	 
				     		sheVoipMediaFaxProfileControlT38FaxBytemode 
				 
				modifyVoipMediaFaxProfile    (37), 
					Must:  sheVoipMediaFaxProfileControlIndex 
					Optional: sheVoipMediaFaxProfileControlName 				 
				         	  sheVoipMediaFaxProfileControlModemDetect		 
				         	  sheVoipMediaFaxProfileControlFaxTypeUsed   			       	            
				         	  sheVoipMediaFaxProfileControlFaxMaxBaudrate	        	 
				         	  sheVoipMediaFaxProfileControlT38FaxEcm  		             
				         	  sheVoipMediaFaxProfileControlT38FaxTcfmode 	    
				     		  sheVoipMediaFaxProfileControlT38FaxNumFec  	 
				     		  sheVoipMediaFaxProfileControlT38FaxNumIfp  	 
				     		  sheVoipMediaFaxProfileControlT38FaxBytemode 
				 
				deleteVoipMediaFaxProfile    (38), 
				    Must: sheVoipMediaFaxProfileControlIndex 
				"
			::= { sheVoipMediaFaxProfileControl 1 }

		
		sheVoipMediaFaxProfileControlIndex OBJECT-TYPE
			SYNTAX Unsigned32
			MAX-ACCESS read-write
			STATUS current
			DESCRIPTION
				"Table index"
			::= { sheVoipMediaFaxProfileControl 2 }

		
		sheVoipMediaFaxProfileControlName OBJECT-TYPE
			SYNTAX DisplayString (SIZE (0..31))
			MAX-ACCESS read-write
			STATUS current
			DESCRIPTION
				"A describable name that uniquely identifies a  
				profile entry of this table.The profile name is  
				user specified.A default profile will always exist.  
				This profile's name will be set to `DEFVAL'."
			::= { sheVoipMediaFaxProfileControl 3 }

		
		sheVoipMediaFaxProfileControlModemDetect OBJECT-TYPE
			SYNTAX SheVoipMediaFaxProfileModemDetectType
			MAX-ACCESS read-write
			STATUS current
			DESCRIPTION
				"Modem Detection 
				[value index] 
				modemOff 	(0), 
				modemAuto 	(1),
				modemMgc	(2)  --default 
				"
			::= { sheVoipMediaFaxProfileControl 4 }

		
		sheVoipMediaFaxProfileControlFaxTypeUsed OBJECT-TYPE
			SYNTAX SheVoipMediaFaxProfileFaxTypeUsedType
			MAX-ACCESS read-write
			STATUS current
			DESCRIPTION
				"Use of Fax 
				[value index]     		 
				 faxOff	(0),
				 t30auto	(1), 
				 t30mgc	(2), 
				 t38auto	(3), 
				 t38mgc	(4) 
				"
			::= { sheVoipMediaFaxProfileControl 5 }

		
		sheVoipMediaFaxProfileControlFaxMaxBaudrate OBJECT-TYPE
			SYNTAX SheVoipMediaFaxProfileFaxMaxBaudrateType
			MAX-ACCESS read-write
			STATUS current
			DESCRIPTION
				"Use of  Fax Max Baudrate: 
				[value index] 
				no-speed(0): 
				2400bps(1): 
				4800bps(2): 
				7200bps(3): 
				9600bps(4): 
				12000bps(5): 
				14400bps(6): 
				"
			::= { sheVoipMediaFaxProfileControl 6 }

		
		sheVoipMediaFaxProfileControlT38FaxEcm OBJECT-TYPE
			SYNTAX SheVoipMediaFaxProfileT38FaxEcmType
			MAX-ACCESS read-write
			STATUS current
			DESCRIPTION
				"T38 Fax Error Correction Mode : 
				[value index]	 
				off(0):  
				on(1) : (default) 
				"
			::= { sheVoipMediaFaxProfileControl 7 }

		
		sheVoipMediaFaxProfileControlT38FaxTcfmode OBJECT-TYPE
			SYNTAX SheVoipMediaFaxProfileT38FaxTcfmodeType
			MAX-ACCESS read-write
			STATUS current
			DESCRIPTION
				"T38 FaxTcfmode 
				[value index] 
				Procedure2(0):  
				Procedure1(1) : Default 
				"
			::= { sheVoipMediaFaxProfileControl 8 }

		
		sheVoipMediaFaxProfileControlT38FaxNumFec OBJECT-TYPE
			SYNTAX Unsigned32 (0..3)
			MAX-ACCESS read-write
			STATUS current
			DESCRIPTION
				"Fax Forward Error Correction 
				[value range] 
				<0..3> 
				Default(0) 
				"
			::= { sheVoipMediaFaxProfileControl 9 }

		
		sheVoipMediaFaxProfileControlT38FaxNumIfp OBJECT-TYPE
			SYNTAX Unsigned32 (0..4)
			MAX-ACCESS read-write
			STATUS current
			DESCRIPTION
				"Internet Fax Protocol 
				[value range]<0..4> 
				Default(0) 
				"
			::= { sheVoipMediaFaxProfileControl 10 }

		
		sheVoipMediaFaxProfileControlT38FaxBytemode OBJECT-TYPE
			SYNTAX SheVoipMediaFaxProfileT38FaxBytemodeType
			MAX-ACCESS read-write
			STATUS current
			DESCRIPTION
				"T38 Byte or Frame Mode			 
				[value index] 
				Bytemode(0): (default)  
				Framemode(1):  
				"
			::= { sheVoipMediaFaxProfileControl 11 }

		
		sheVoipMediaFaxProfileControlStatus OBJECT-TYPE
			SYNTAX SheControlStatusType
			MAX-ACCESS read-only
			STATUS current
			DESCRIPTION
				"The status of a user command."
			::= { sheVoipMediaFaxProfileControl 12 }

		
		sheVoipMediaFaxProfileControlTimer OBJECT-TYPE
			SYNTAX Gauge32
			MAX-ACCESS read-only
			STATUS current
			DESCRIPTION
				"The maximum wait time for the manager for a  
				long running user command."
			::= { sheVoipMediaFaxProfileControl 13 }

		
		sheVoipMediaFaxProfileControlTimeStamp OBJECT-TYPE
			SYNTAX TimeTicks
			MAX-ACCESS read-only
			STATUS current
			DESCRIPTION
				"The time stamp of the last command (end of command)."
			::= { sheVoipMediaFaxProfileControl 14 }

		
		sheVoipMediaFaxProfileControlReqResult OBJECT-TYPE
			SYNTAX SheVoipControlRequestResultType
			MAX-ACCESS read-only
			STATUS current
			DESCRIPTION
				"The result of the last user command."
			::= { sheVoipMediaFaxProfileControl 15 }

		
		sheVoipRtcpProfileTable OBJECT-TYPE
			SYNTAX SEQUENCE OF SheVoipRtcpProfileEntry
			MAX-ACCESS not-accessible
			STATUS current
			DESCRIPTION
				"This table contains attributes for each RtpRtcp profile."
			::= { sheVoipVoipDataGroup 2 }

		
		sheVoipRtcpProfileEntry OBJECT-TYPE
			SYNTAX SheVoipRtcpProfileEntry
			MAX-ACCESS not-accessible
			STATUS current
			DESCRIPTION
				"An entry represents a set of profile configurations 
				in sheVoipRtcpProfileTable.A default profile will always exist.  
				This profile's name will be set to `DEFVAL' and its parameters will  
				be set to vendor specific values. 
				"
			INDEX { sheVoipRtcpProfileIndex }
			::= { sheVoipRtcpProfileTable 1 }

		
		SheVoipRtcpProfileEntry ::=
			SEQUENCE { 
				sheVoipRtcpProfileIndex
					Unsigned32,
				sheVoipRtcpProfileName
					DisplayString,
				sheVoipRtcpProfileDtmf
					SheVoipRtcpProfileDtmfType,
				sheVoipRtcpProfileT38FaxRedPktCount
					Unsigned32,
				sheVoipRtcpProfileT30FaxRedPktCount
					Unsigned32,
				sheVoipRtcpProfileDtmfRfc2833PktType
					Unsigned32,
				sheVoipRtcpProfileDtmfRfc2833RedPktType
					Unsigned32,
				sheVoipRtcpProfileRTPRedPktCount
					Unsigned32,
				sheVoipRtcpProfileRtcpGen
					SheVoipRtcpProfileRtcpGenType,
				sheVoipRtcpProfileRtcpInterval
					Unsigned32,
				sheVoipRtcpProfileFecPayLoadType
					Unsigned32
			 }

		sheVoipRtcpProfileIndex OBJECT-TYPE
			SYNTAX Unsigned32
			MAX-ACCESS read-only
			STATUS current
			DESCRIPTION
				"Table index. Each index uniquely identifies one  
				RtpRctp Profile."
			::= { sheVoipRtcpProfileEntry 1 }

		
		sheVoipRtcpProfileName OBJECT-TYPE
			SYNTAX DisplayString (SIZE (0..31))
			MAX-ACCESS read-only
			STATUS current
			DESCRIPTION
				"A describable name that uniquely identifies a profile entry  
				of this table.The profile name is user specified. A default	 
				profile will always exist. This profile's name will be set to  
				`DEFVAL'."
			::= { sheVoipRtcpProfileEntry 2 }

		
		sheVoipRtcpProfileDtmf OBJECT-TYPE
			SYNTAX SheVoipRtcpProfileDtmfType
			MAX-ACCESS read-only
			STATUS current
			DESCRIPTION
				"Use of Out-of-Band DTMF 
				[value index] 
				-inBandDTMF(0):default
				When receiving DTMF from terminal, MG always pack DTMF into voice inband and 
				send it out directely.
				-rfc2833(1) = Use RFC2833 DTMF
				When receiving DTMF from terminal, MG pack DTMF into RTP inband using RFC2833 standard. 
				"
			DEFVAL { inBandDTMF }
			::= { sheVoipRtcpProfileEntry 3 }

		
		sheVoipRtcpProfileT38FaxRedPktCount OBJECT-TYPE
			SYNTAX Unsigned32 (0..3)
			MAX-ACCESS read-only
			STATUS current
			DESCRIPTION
				"This parameter controls the UDPTL redundancy count for fax page data. 
				The redundant message format is defined in section 9.4.1 of Recommendation T.38. 
				Range: 0 (default) to 3.  Choose a low level of redundancy for page data, to keep
				bandwidth requirements to a minimum level.
				[value range]<0-3> 
				"
			DEFVAL { 0 }
			::= { sheVoipRtcpProfileEntry 4 }

		
		sheVoipRtcpProfileT30FaxRedPktCount OBJECT-TYPE
			SYNTAX Unsigned32 (0..7)
			MAX-ACCESS read-only
			STATUS current
			DESCRIPTION
				"This parameter controls the UDPTL redundancy count for T.30 messages. 
				The redundant message format is defined in section 9.4.1 of Recommendation T.38. 
				
				Range: 0 to 7, default 3(chipset). Increasing this value ensures that the fax 
				negotiation is as reliable as possible.
				"
			DEFVAL { 3 }
			::= { sheVoipRtcpProfileEntry 5 }

		
		sheVoipRtcpProfileDtmfRfc2833PktType OBJECT-TYPE
			SYNTAX Unsigned32 (96..127)
			MAX-ACCESS read-only
			STATUS current
			DESCRIPTION
				"The pay load type of RFC2833 in RTP packages. Normal this value will depends 
				on the negociation between two peers under the control of MGC. 
				Dtmf Rfc2833 Packet Type
				[value range]Value = <96-127> 
				"
			DEFVAL { 97 }
			::= { sheVoipRtcpProfileEntry 6 }

		
		sheVoipRtcpProfileDtmfRfc2833RedPktType OBJECT-TYPE
			SYNTAX Unsigned32 (96..127)
			MAX-ACCESS read-only
			STATUS current
			DESCRIPTION
				"Redundant Scheme for DTMF, Redundant payload type value.
				Dtmf Rfc2833 Red Packet Type
				[value range]<96..127> 
				"
			DEFVAL { 96 }
			::= { sheVoipRtcpProfileEntry 7 }

		
		sheVoipRtcpProfileRTPRedPktCount OBJECT-TYPE
			SYNTAX Unsigned32 (0..2)
			MAX-ACCESS read-only
			STATUS current
			DESCRIPTION
				"Redundancy Selection. This parameter allows a given number of redundant 
				audio payloads to be send in RTP packets, usually used in T.38.
				Redundancy for RTP Packet 
				[value range]Value = <0-2> 
				"
			DEFVAL { 0 }
			::= { sheVoipRtcpProfileEntry 8 }

		
		sheVoipRtcpProfileRtcpGen OBJECT-TYPE
			SYNTAX SheVoipRtcpProfileRtcpGenType
			MAX-ACCESS read-only
			STATUS current
			DESCRIPTION
				"RTCP Generation,enable  RTCP protocol.
				[value index] 
				Off(0):  
				On(1) : default(1)  
				"
			DEFVAL { on }
			::= { sheVoipRtcpProfileEntry 9 }

		
		sheVoipRtcpProfileRtcpInterval OBJECT-TYPE
			SYNTAX Unsigned32 (5..180)
			UNITS "sec"
			MAX-ACCESS read-only
			STATUS current
			DESCRIPTION
				"Configure the transmission granularity of RTCP packets.
				RTCP Interval 
				[value range]<5..180>   [second] 
				default(5)  
				"
			DEFVAL { 5 }
			::= { sheVoipRtcpProfileEntry 10 }

		
		sheVoipRtcpProfileFecPayLoadType OBJECT-TYPE
			SYNTAX Unsigned32 (96..254)
			MAX-ACCESS read-only
			STATUS current
			DESCRIPTION
				"Forward Error Correction (FEC) recovers lost packet data at the receiver by 
				using encoding rules defined in accordance with the sender. RFC2733 describes 
				how to use FEC with data packets made of voice stream and fax/modem signals in 
				the voice stream.Note: Default value of FEC payload type is 0x64, so if MGC ask 
				this value for other use, like rfc2833, we should modified the FEC payload type 
				with other value(other than 0x64).
				 [value range]<96..254> 
				"
			DEFVAL { 100 }
			::= { sheVoipRtcpProfileEntry 11 }

		
		sheVoipRtcpProfileControl OBJECT IDENTIFIER ::= { sheVoipVoipDataGroup 3 }

		
		sheVoipRtcpProfileControlRequest OBJECT-TYPE
			SYNTAX SheVoipControlRequestType
			MAX-ACCESS read-write
			STATUS current
			DESCRIPTION
				"The request of a user command. 
				createsheVoipRtcpProfile  (40), 
				    Must: sheVoipRtcpProfileControlName 
				    Optional: sheVoipRtcpProfileControlDtmf
				       	   sheVoipRtcpProfileControlT38FaxRedPktCount  		             
				       	   sheVoipRtcpProfileControlT30FaxRedPktCount 			    
					   sheVoipRtcpProfileControlDtmfRfc2833PktType  		 
					   sheVoipRtcpProfileControlDtmfRfc2833RedPktType  	 
					   sheVoipRtcpProfileControlRTPRedPktCount   			 
					   sheVoipRtcpProfileControlRtcpGen	  	 			 
					   sheVoipRtcpProfileControlRtcpInterval         					              
					   sheVoipRtcpProfileControlFecPayLoadType	 
				  		 	   
				modifysheVoipRtcpProfile  (41),                  
				             Must:  sheVoipRtcpProfileControlIndex 
				    Optional: sheVoipRtcpProfileControlName			       	            
				       	   sheVoipRtcpProfileControlDtmf
				       	   sheVoipRtcpProfileControlT38FaxRedPktCount  		             
				       	   sheVoipRtcpProfileControlT30FaxRedPktCount 			    
					   sheVoipRtcpProfileControlDtmfRfc2833PktType  		 
					   sheVoipRtcpProfileControlDtmfRfc2833RedPktType  	 
					   sheVoipRtcpProfileControlRTPRedPktCount   			 
					   sheVoipRtcpProfileControlRtcpGen	  	 			 
					   sheVoipRtcpProfileControlRtcpInterval 
					   sheVoipRtcpProfileControlFecPayLoadType	 
				    				    
				deletesheVoipRtcpProfile  (42), 
				   Must:  sheVoipRtcpProfileControlIndex 
				"
			::= { sheVoipRtcpProfileControl 1 }

		
		sheVoipRtcpProfileControlIndex OBJECT-TYPE
			SYNTAX Unsigned32
			MAX-ACCESS read-write
			STATUS current
			DESCRIPTION
				"Table index"
			::= { sheVoipRtcpProfileControl 2 }

		
		sheVoipRtcpProfileControlName OBJECT-TYPE
			SYNTAX DisplayString (SIZE (0..31))
			MAX-ACCESS read-write
			STATUS current
			DESCRIPTION
				"A describable name that uniquely identifies a  
				profile entry of this table.The profile name is  
				user specified.A default profile will always exist.  
				This profile's name will be set to `DEFVAL'."
			::= { sheVoipRtcpProfileControl 3 }

		
		sheVoipRtcpProfileControlDtmf OBJECT-TYPE
			SYNTAX SheVoipRtcpProfileDtmfType
			MAX-ACCESS read-write
			STATUS current
			DESCRIPTION
				"inBandDTMF(0):default
				When receiving DTMF from terminal, MG always pack DTMF into voice inband and 
				send it out directely.
				-rfc2833(1) = Use RFC2833 DTMF
				When receiving DTMF from terminal, MG pack DTMF into RTP inband using RFC2833 standard. 
				"
			::= { sheVoipRtcpProfileControl 4 }

		
		sheVoipRtcpProfileControlT38FaxRedPktCount OBJECT-TYPE
			SYNTAX Unsigned32 (0..3)
			MAX-ACCESS read-write
			STATUS current
			DESCRIPTION
				"This parameter controls the UDPTL redundancy count for fax page data. 
				The redundant message format is defined in section 9.4.1 of Recommendation T.38. 
				Range: 0 (default) to 3.  Choose a low level of redundancy for page data, to keep
				bandwidth requirements to a minimum level.
				T38 Fax Redundancy Packet CountT38 Fax Redundancy Packet Count 
				[value range]<0-3> 
				Default:0 
				"
			::= { sheVoipRtcpProfileControl 5 }

		
		sheVoipRtcpProfileControlT30FaxRedPktCount OBJECT-TYPE
			SYNTAX Unsigned32 (0..7)
			MAX-ACCESS read-write
			STATUS current
			DESCRIPTION
				"This parameter controls the UDPTL redundancy count for T.30 messages. 
				The redundant message format is defined in section 9.4.1 of Recommendation T.38. 
				Range: 0 to 7, default 3(chipset). Increasing this value ensures that the fax 
				negotiation is as reliable as possible.
				T30 Fax Redundancy Red Packet Count 
				[value range]<0..7> 
				Default:7 
				"
			::= { sheVoipRtcpProfileControl 6 }

		
		sheVoipRtcpProfileControlDtmfRfc2833PktType OBJECT-TYPE
			SYNTAX Unsigned32 (96..127)
			MAX-ACCESS read-write
			STATUS current
			DESCRIPTION
				"The pay load type of RFC2833 in RTP packages. Normal this value will depends 
				on the negociation between two peers under the control of MGC. 
				Dtmf Rfc2833 Packet Type 
				[value range]Value = <96-127> 
				default(97) 
				"
			::= { sheVoipRtcpProfileControl 7 }

		
		sheVoipRtcpProfileControlDtmfRfc2833RedPktType OBJECT-TYPE
			SYNTAX Unsigned32 (96..127)
			MAX-ACCESS read-write
			STATUS current
			DESCRIPTION
				"Redundant Scheme for DTMF, Redundant payload type value.
				Dtmf Rfc2833 Red Packet Type 
				[value range]<96..127> 
				default(96) 
				"
			::= { sheVoipRtcpProfileControl 8 }

		
		sheVoipRtcpProfileControlRTPRedPktCount OBJECT-TYPE
			SYNTAX Unsigned32 (0..2)
			MAX-ACCESS read-write
			STATUS current
			DESCRIPTION
				"Redundancy Selection. This parameter allows a given number of redundant 
				audio payloads to be send in RTP packets.
				Redundancy for RTP Packet
				[value range]Value = <0-2> 
				default(0)  
				"
			::= { sheVoipRtcpProfileControl 9 }

		
		sheVoipRtcpProfileControlRtcpGen OBJECT-TYPE
			SYNTAX SheVoipRtcpProfileRtcpGenType
			MAX-ACCESS read-write
			STATUS current
			DESCRIPTION
				"RTCP Generation,enable  RTCP protocol.    		  
				[value index] 
				Off(0):  
				On(1) : default(1)  
				"
			::= { sheVoipRtcpProfileControl 10 }

		
		sheVoipRtcpProfileControlRtcpInterval OBJECT-TYPE
			SYNTAX Unsigned32 (5..180)
			UNITS "sec"
			MAX-ACCESS read-write
			STATUS current
			DESCRIPTION
				"Configure the transmission granularity of RTCP packets.
				RTCP Interval  
				[value range]<5..180>   [second] 
				default(5)  
				"
			::= { sheVoipRtcpProfileControl 11 }

		
		sheVoipRtcpProfileControlStatus OBJECT-TYPE
			SYNTAX SheControlStatusType
			MAX-ACCESS read-only
			STATUS current
			DESCRIPTION
				"The status of a user command."
			::= { sheVoipRtcpProfileControl 12 }

		
		sheVoipRtcpProfileControlTimer OBJECT-TYPE
			SYNTAX Gauge32
			MAX-ACCESS read-only
			STATUS current
			DESCRIPTION
				"The maximum wait time for the manager for a  
				long running user command."
			::= { sheVoipRtcpProfileControl 13 }

		
		sheVoipRtcpProfileControlReqResult OBJECT-TYPE
			SYNTAX SheVoipControlRequestResultType
			MAX-ACCESS read-only
			STATUS current
			DESCRIPTION
				"The result of the last user command."
			::= { sheVoipRtcpProfileControl 14 }

		
		sheVoipRtcpProfileControlTimeStamp OBJECT-TYPE
			SYNTAX TimeTicks
			MAX-ACCESS read-only
			STATUS current
			DESCRIPTION
				"The time stamp of the last command (end of command)."
			::= { sheVoipRtcpProfileControl 15 }

		
		sheVoipRtcpProfileControlFecPayLoadType OBJECT-TYPE
			SYNTAX Unsigned32
			MAX-ACCESS read-write
			STATUS current
			DESCRIPTION
				"Forward Error Correction (FEC) recovers lost packet data at the receiver by 
				using encoding rules defined in accordance with the sender. RFC2733 describes 
				how to use FEC with data packets made of voice stream and fax/modem signals in 
				the voice stream.Note: Default value of FEC payload type is 0x64, so if MGC ask 
				this value for other use, like rfc2833, we should modified the FEC payload type 
				with other value(other than 0x64).
					[value range]<96..254> 
				default(100)"
			::= { sheVoipRtcpProfileControl 16 }

		
		sheVoipVoipVoiceCtpTable OBJECT-TYPE
			SYNTAX SEQUENCE OF SheVoipVoipVoiceCtpEntry
			MAX-ACCESS not-accessible
			STATUS current
			DESCRIPTION
				"This table contains attributes for each voice connection  
				termination point table profile."
			::= { sheVoipVoipDataGroup 4 }

		
		sheVoipVoipVoiceCtpEntry OBJECT-TYPE
			SYNTAX SheVoipVoipVoiceCtpEntry
			MAX-ACCESS not-accessible
			STATUS current
			DESCRIPTION
				"An entry in sheVoipVoipVoiceCtpTable."
			INDEX { ifIndex }
			::= { sheVoipVoipVoiceCtpTable 1 }

		
		SheVoipVoipVoiceCtpEntry ::=
			SEQUENCE { 
				sheVoipVoipVoiceCtpVgwIndex
					Unsigned32,
				sheVoipVoipVoiceCtpIpHostProfileIndex
					Unsigned32,
				sheVoipVoipVoiceCtpCodecProfileIndex
					Unsigned32,
				sheVoipVoipVoiceCtpJitterBufProfileIndex
					Unsigned32,
				sheVoipVoipVoiceCtpFaxProfileIndex
					Unsigned32,
				sheVoipVoipVoiceCtpRtcpProfileIndex
					Unsigned32,
				sheVoipVoipVoiceCtpRtpUdpPortBase
					Unsigned32,
				sheVoipVoipVoiceCtpRtpStreamTos
					Unsigned32
			 }

		sheVoipVoipVoiceCtpVgwIndex OBJECT-TYPE
			SYNTAX Unsigned32
			MAX-ACCESS read-only
			STATUS current
			DESCRIPTION
				"This read-only attribute represents a pointer to vgw profile. 
				sheVoipVoipVoiceCtpVgwIndex = sheVoipVgwIndex"
			::= { sheVoipVoipVoiceCtpEntry 1 }

		
		sheVoipVoipVoiceCtpIpHostProfileIndex OBJECT-TYPE
			SYNTAX Unsigned32
			MAX-ACCESS read-only
			STATUS current
			DESCRIPTION
				"sheVoipVoipVoiceCtpIpHostProfileIndex= sheVoipIpHostProfileIndex"
			DEFVAL { 1 }
			::= { sheVoipVoipVoiceCtpEntry 2 }

		
		sheVoipVoipVoiceCtpCodecProfileIndex OBJECT-TYPE
			SYNTAX Unsigned32
			MAX-ACCESS read-only
			STATUS current
			DESCRIPTION
				"sheVoipVoipVoiceCtpCodecProfileIndex  
				= sheVoipMediaCodecProfileIndex"
			DEFVAL { 1 }
			::= { sheVoipVoipVoiceCtpEntry 3 }

		
		sheVoipVoipVoiceCtpJitterBufProfileIndex OBJECT-TYPE
			SYNTAX Unsigned32
			MAX-ACCESS read-only
			STATUS current
			DESCRIPTION
				"sheVoipMediaJitterBufProfileIndex  
				= sheVoipVoipVoiceCtpJitterBufProfileIndex"
			DEFVAL { 0 }
			::= { sheVoipVoipVoiceCtpEntry 4 }

		
		sheVoipVoipVoiceCtpFaxProfileIndex OBJECT-TYPE
			SYNTAX Unsigned32
			MAX-ACCESS read-only
			STATUS current
			DESCRIPTION
				"sheVoipVoipVoiceCtpFaxProfileIndex = sheVoipMediaFaxProfileIndex"
			DEFVAL { 1 }
			::= { sheVoipVoipVoiceCtpEntry 5 }

		
		sheVoipVoipVoiceCtpRtcpProfileIndex OBJECT-TYPE
			SYNTAX Unsigned32
			MAX-ACCESS read-only
			STATUS current
			DESCRIPTION
				"Pointer to sheVoipRtcpProfileTable,equal to sheVoipRtcpProfileIndex."
			DEFVAL { 1 }
			::= { sheVoipVoipVoiceCtpEntry 6 }

		
		sheVoipVoipVoiceCtpRtpUdpPortBase OBJECT-TYPE
			SYNTAX Unsigned32 (20000..40000)
			MAX-ACCESS read-only
			STATUS current
			DESCRIPTION
				"The user needs to configure the UDP ports for RTP traffic on AGLU interfaces.  
				Only when signaling protocol is set to H.248, can ifIndex represent the first  
				interface of each AGLU card. The portBase specifies the starting UDP port that can 
				be set to a value larger than 20000.  
				"
			::= { sheVoipVoipVoiceCtpEntry 7 }

		
		sheVoipVoipVoiceCtpRtpStreamTos OBJECT-TYPE
			SYNTAX Unsigned32 (0..255)
			MAX-ACCESS read-only
			STATUS current
			DESCRIPTION
				" rtp stream type of service. "
			DEFVAL { 0 }
			::= { sheVoipVoipVoiceCtpEntry 8 }

		
		sheVoipVoipVoiceCtpControl OBJECT IDENTIFIER ::= { sheVoipVoipDataGroup 5 }

		
		sheVoipVoipVoiceCtpControlRequest OBJECT-TYPE
			SYNTAX SheVoipControlRequestType
			MAX-ACCESS read-write
			STATUS current
			DESCRIPTION
				"The request of a user command.  
				modifySheVoipVoipVoiceCtpConfig (43),   
				Must: sheVoipVoipVoiceCtpControlIfIndexBitMask 					              
				Optional: sheVoipVoipVoiceCtpControlIpHostProfileIndex 			 
					  sheVoipVoipVoiceCtpControlCodecProfileIndex			 
					  sheVoipVoipVoiceCtpControlJitterBufProfileIndex   	       	            
					  sheVoipVoipVoiceCtpControlFaxProfileIndex			        	 
					  sheVoipVoipVoiceCtpControlRtcpProfileIndex 
					  sheVoipVoipVoiceCtpControlRtpUdpPortBase
					  sheVoipVoipVoiceCtpControlRtpStreamTos "
			::= { sheVoipVoipVoiceCtpControl 1 }

		
		sheVoipVoipVoiceCtpControlIfIndexBitMask OBJECT-TYPE
			SYNTAX OCTET STRING (SIZE (256))
			MAX-ACCESS read-write
			STATUS current
			DESCRIPTION
				"IfIndex list, represented by 256 bytes. Each bit  
				stands for an ifIndex of a port.When sheVoipMgConfigDataProtocolVersion  
				is set to H.248, ifIndex should be set from 101 to 1772. The  
				slot number this ifIndex associates can be found through  
				shePhysPortId in shePhysPortTable. 					 
				"
			::= { sheVoipVoipVoiceCtpControl 2 }

		
		sheVoipVoipVoiceCtpControlIpHostProfileIndex OBJECT-TYPE
			SYNTAX Unsigned32
			MAX-ACCESS read-write
			STATUS current
			DESCRIPTION
				"sheVoipVoipVoiceCtpIpHostProfileIndex= sheVoipIpHostProfileIndex"
			::= { sheVoipVoipVoiceCtpControl 3 }

		
		sheVoipVoipVoiceCtpControlCodecProfileIndex OBJECT-TYPE
			SYNTAX Unsigned32
			MAX-ACCESS read-write
			STATUS current
			DESCRIPTION
				"sheVoipVoipVoiceCtpCodecProfileIndex  
				= sheVoipMediaCodecProfileIndex"
			::= { sheVoipVoipVoiceCtpControl 4 }

		
		sheVoipVoipVoiceCtpControlJitterBufProfileIndex OBJECT-TYPE
			SYNTAX Unsigned32
			MAX-ACCESS read-write
			STATUS current
			DESCRIPTION
				"sheVoipVoipVoiceCtpJitterBufProfileIndex =  
				sheVoipMediaJitterBufProfileIndex"
			::= { sheVoipVoipVoiceCtpControl 5 }

		
		sheVoipVoipVoiceCtpControlFaxProfileIndex OBJECT-TYPE
			SYNTAX Unsigned32
			MAX-ACCESS read-write
			STATUS current
			DESCRIPTION
				"sheVoipVoipVoiceCtpFaxProfileIndex = sheVoipMediaFaxProfileIndex"
			::= { sheVoipVoipVoiceCtpControl 6 }

		
		sheVoipVoipVoiceCtpControlRtcpProfileIndex OBJECT-TYPE
			SYNTAX Unsigned32
			MAX-ACCESS read-write
			STATUS current
			DESCRIPTION
				"Pointer to sheVoipRtcpProfileTable, equal to sheVoipRtcpProfileIndex."
			::= { sheVoipVoipVoiceCtpControl 7 }

		
		sheVoipVoipVoiceCtpControlRtpUdpPortBase OBJECT-TYPE
			SYNTAX Unsigned32 (20000..40000)
			MAX-ACCESS read-write
			STATUS current
			DESCRIPTION
				"The user needs to configure the UDP ports for RTP traffic on AGLU interfaces.  
				Only when signaling protocol is set to H.248, can ifIndex represent the first  
				interface of each AGLU card.The portBase specifies the starting UDP port that can 
				be set to a value larger than 20000.  
				"
			::= { sheVoipVoipVoiceCtpControl 8 }

		
		sheVoipVoipVoiceCtpControlStatus OBJECT-TYPE
			SYNTAX SheControlStatusType
			MAX-ACCESS read-only
			STATUS current
			DESCRIPTION
				"The status of a user command."
			::= { sheVoipVoipVoiceCtpControl 9 }

		
		sheVoipVoipVoiceCtpControlTimer OBJECT-TYPE
			SYNTAX Gauge32
			MAX-ACCESS read-only
			STATUS current
			DESCRIPTION
				"The maximum wait time for the manager for a  
				long running user command."
			::= { sheVoipVoipVoiceCtpControl 10 }

		
		sheVoipVoipVoiceCtpControlReqResult OBJECT-TYPE
			SYNTAX SheVoipControlRequestResultType
			MAX-ACCESS read-only
			STATUS current
			DESCRIPTION
				"The result of the last user command."
			::= { sheVoipVoipVoiceCtpControl 11 }

		
		sheVoipVoipVoiceCtpControlTimeStamp OBJECT-TYPE
			SYNTAX TimeTicks
			MAX-ACCESS read-only
			STATUS current
			DESCRIPTION
				"The time stamp of the last command (end of command)."
			::= { sheVoipVoipVoiceCtpControl 12 }

		
		sheVoipVoipVoiceCtpControlRtpStreamTos OBJECT-TYPE
			SYNTAX Unsigned32 (0..255)
			MAX-ACCESS read-write
			STATUS current
			DESCRIPTION
				" rtp stream type of service. "
			::= { sheVoipVoipVoiceCtpControl 13 }

		
		sheVoipIpHostDataGroup OBJECT IDENTIFIER ::= { sheVoipMibModule 4 }

		
		sheVoipIpHostProfileTable OBJECT-TYPE
			SYNTAX SEQUENCE OF SheVoipIpHostProfileEntry
			MAX-ACCESS not-accessible
			STATUS current
			DESCRIPTION
				"This table contains attributes for each voip IP 
				host profile table."
			::= { sheVoipIpHostDataGroup 1 }

		
		sheVoipIpHostProfileEntry OBJECT-TYPE
			SYNTAX SheVoipIpHostProfileEntry
			MAX-ACCESS not-accessible
			STATUS current
			DESCRIPTION
				"An entry represents a set of profile configurations 
				in sheVoipIpHostProfileTable. 
				"
			INDEX { sheVoipIpHostProfileIndex }
			::= { sheVoipIpHostProfileTable 1 }

		
		SheVoipIpHostProfileEntry ::=
			SEQUENCE { 
				sheVoipIpHostProfileIndex
					Unsigned32,
				sheVoipIpHostProfileName
					DisplayString,
				sheVoipIpHostProfileUseDhcp
					SheVoipIpHostProfileUseDhcpType,
				sheVoipIpHostProfileIpAddress
					IpAddress,
				sheVoipIpHostProfileSubnetMask
					IpAddress,
				sheVoipIpHostProfileDefaultGateway
					IpAddress
			 }

		sheVoipIpHostProfileIndex OBJECT-TYPE
			SYNTAX Unsigned32
			MAX-ACCESS read-only
			STATUS current
			DESCRIPTION
				"Table index. Each index uniquely identifies one  
				Ip host Profile table entry."
			::= { sheVoipIpHostProfileEntry 1 }

		
		sheVoipIpHostProfileName OBJECT-TYPE
			SYNTAX DisplayString (SIZE (0..31))
			MAX-ACCESS read-only
			STATUS current
			DESCRIPTION
				"A describable name that uniquely identifies a profile entry  
				of this table. The profile name is user specified.  
				"
			::= { sheVoipIpHostProfileEntry 2 }

		
		sheVoipIpHostProfileUseDhcp OBJECT-TYPE
			SYNTAX SheVoipIpHostProfileUseDhcpType
			MAX-ACCESS read-only
			STATUS current
			DESCRIPTION
				"Wether to use slot Dhcp 
				(0)	noUseDhcp (default) 
				(1)	useDhcp 
				     	"
			DEFVAL { noUseDhcp }
			::= { sheVoipIpHostProfileEntry 3 }

		
		sheVoipIpHostProfileIpAddress OBJECT-TYPE
			SYNTAX IpAddress
			MAX-ACCESS read-only
			STATUS current
			DESCRIPTION
				"SlotIpaddress 
				"
			::= { sheVoipIpHostProfileEntry 4 }

		
		sheVoipIpHostProfileSubnetMask OBJECT-TYPE
			SYNTAX IpAddress
			MAX-ACCESS read-only
			STATUS current
			DESCRIPTION
				"Slot subnet mask 
				"
			::= { sheVoipIpHostProfileEntry 5 }

		
		sheVoipIpHostProfileDefaultGateway OBJECT-TYPE
			SYNTAX IpAddress
			MAX-ACCESS read-only
			STATUS current
			DESCRIPTION
				"Default gateway 
				"
			::= { sheVoipIpHostProfileEntry 6 }

		
		sheVoipIpHostProfileControl OBJECT IDENTIFIER ::= { sheVoipIpHostDataGroup 2 }

		
		sheVoipIpHostProfileControlRequest OBJECT-TYPE
			SYNTAX SheVoipControlRequestType
			MAX-ACCESS read-write
			STATUS current
			DESCRIPTION
				"The request of a user command.  
				createVoipIpHostProfile    (50), 
					Must: sheVoipIpHostProfileControlName 
					Optional: sheVoipIpHostProfileControlUseDhcp				 
				         	  sheVoipIpHostProfileControlIpAddress  			       	            
				         	  sheVoipIpHostProfileControlSubnetMask 			        	 
				         	  sheVoipIpHostProfileControlDefaultGateway 
				         			   
				deleteVoipIpHostProfile    (51), 
					Must: sheVoipIpHostProfileControlIndex 
					 
				modifyVoipIpHostProfile    (52), 
					Must: sheVoipIpHostProfileControlIndex 				              
					Optional: sheVoipIpHostProfileControlName 				  
				         	sheVoipIpHostProfileControlUseDhcp				 
				         	sheVoipIpHostProfileControlIpAddress  			       	            
				         	sheVoipIpHostProfileControlSubnetMask 			        	 
				         	sheVoipIpHostProfileControlDefaultGateway  	 
				"
			::= { sheVoipIpHostProfileControl 1 }

		
		sheVoipIpHostProfileControlIndex OBJECT-TYPE
			SYNTAX Unsigned32
			MAX-ACCESS read-write
			STATUS current
			DESCRIPTION
				"Table index"
			::= { sheVoipIpHostProfileControl 2 }

		
		sheVoipIpHostProfileControlName OBJECT-TYPE
			SYNTAX DisplayString (SIZE (0..31))
			MAX-ACCESS read-write
			STATUS current
			DESCRIPTION
				"A describable name that uniquely identifies a profile entry  
				of this table.The profile name is user specified. 
				"
			::= { sheVoipIpHostProfileControl 3 }

		
		sheVoipIpHostProfileControlUseDhcp OBJECT-TYPE
			SYNTAX SheVoipIpHostProfileUseDhcpType
			MAX-ACCESS read-write
			STATUS current
			DESCRIPTION
				"Wether to use slot Dhcp 
				noUseDhcp (0), 
				useDhcp   (1) 
				"
			::= { sheVoipIpHostProfileControl 4 }

		
		sheVoipIpHostProfileControlIpAddress OBJECT-TYPE
			SYNTAX IpAddress
			MAX-ACCESS read-write
			STATUS current
			DESCRIPTION
				"SlotIpaddress 
				"
			::= { sheVoipIpHostProfileControl 5 }

		
		sheVoipIpHostProfileControlSubnetMask OBJECT-TYPE
			SYNTAX IpAddress
			MAX-ACCESS read-write
			STATUS current
			DESCRIPTION
				"Slot subnet mask 
				"
			::= { sheVoipIpHostProfileControl 6 }

		
		sheVoipIpHostProfileControlDefaultGateway OBJECT-TYPE
			SYNTAX IpAddress
			MAX-ACCESS read-write
			STATUS current
			DESCRIPTION
				"Default gateway 
				"
			::= { sheVoipIpHostProfileControl 7 }

		
		sheVoipIpHostProfileControlStatus OBJECT-TYPE
			SYNTAX SheControlStatusType
			MAX-ACCESS read-only
			STATUS current
			DESCRIPTION
				"The status of a user command."
			::= { sheVoipIpHostProfileControl 8 }

		
		sheVoipIpHostProfileControlTimer OBJECT-TYPE
			SYNTAX Gauge32
			MAX-ACCESS read-only
			STATUS current
			DESCRIPTION
				"The maximum wait time for the manager for a  
				long running user command."
			::= { sheVoipIpHostProfileControl 9 }

		
		sheVoipIpHostProfileControlReqResult OBJECT-TYPE
			SYNTAX SheVoipControlRequestResultType
			MAX-ACCESS read-only
			STATUS current
			DESCRIPTION
				"The result of the last user command."
			::= { sheVoipIpHostProfileControl 10 }

		
		sheVoipIpHostProfileControlTimeStamp OBJECT-TYPE
			SYNTAX TimeTicks
			MAX-ACCESS read-only
			STATUS current
			DESCRIPTION
				"The time stamp of the last command (end of command)."
			::= { sheVoipIpHostProfileControl 11 }

		
		sheVoipDigitMapGroup OBJECT IDENTIFIER ::= { sheVoipMibModule 5 }

		
		sheVoipDigitMapProfileTable OBJECT-TYPE
			SYNTAX SEQUENCE OF SheVoipDigitMapProfileEntry
			MAX-ACCESS not-accessible
			STATUS current
			DESCRIPTION
				"This table contains attributes for each VoipDigitMapProfile table."
			::= { sheVoipDigitMapGroup 1 }

		
		sheVoipDigitMapProfileEntry OBJECT-TYPE
			SYNTAX SheVoipDigitMapProfileEntry
			MAX-ACCESS not-accessible
			STATUS current
			DESCRIPTION
				"An entry in sheVoipDigitMapProfileTable. A default	 
				profile will always exist. This profile's name will be set to  
				`DEFVAL' and its parameters will be set to vendor specific values."
			INDEX { sheVoipDigitMapProfileIndex }
			::= { sheVoipDigitMapProfileTable 1 }

		
		SheVoipDigitMapProfileEntry ::=
			SEQUENCE { 
				sheVoipDigitMapProfileIndex
					Unsigned32,
				sheVoipDigitMapProfileName
					OCTET STRING,
				sheVoipDigitMapProfileDigitMap
					OCTET STRING,
				sheVoipDigitMapProfileLongTime
					Unsigned32,
				sheVoipDigitMapProfileShortTime
					Unsigned32,
				sheVoipDigitMapProfileStartTime
					Unsigned32,
				sheVoipDigitMapProfileZTime
					Unsigned32
			 }

		sheVoipDigitMapProfileIndex OBJECT-TYPE
			SYNTAX Unsigned32
			MAX-ACCESS read-only
			STATUS current
			DESCRIPTION
				"Table index. Each index uniquely identifies one  
				DigitMap table entry."
			::= { sheVoipDigitMapProfileEntry 1 }

		
		sheVoipDigitMapProfileName OBJECT-TYPE
			SYNTAX OCTET STRING (SIZE (0..31))
			MAX-ACCESS read-only
			STATUS current
			DESCRIPTION
				"The digitmap name is user specified. A default	 
				profile will always exist. This profile's name will be set to  
				`DEFVAL' and its parameters will be set to vendor specific values."
			::= { sheVoipDigitMapProfileEntry 2 }

		
		sheVoipDigitMapProfileDigitMap OBJECT-TYPE
			SYNTAX OCTET STRING (SIZE (0..128))
			MAX-ACCESS read-only
			STATUS current
			DESCRIPTION
				"A DigitMap is a dialing plan resident in the Media Gateway used for   
				detecting and reporting digit events received on a Termination."
			DEFVAL { "9|11x|[5-8]xxxxxxx|0[1-9]xxx.|00xxx.|179xx.|13xxxxxxxxx|800xxxxxxx" }
			::= { sheVoipDigitMapProfileEntry 3 }

		
		sheVoipDigitMapProfileLongTime OBJECT-TYPE
			SYNTAX Unsigned32 (0..99)
			UNITS "sec"
			MAX-ACCESS read-only
			STATUS current
			DESCRIPTION
				"If the Media Gateway can determine that at least one more digit is 
				needed for a digit string to match any of the allowed patterns in
				the digit map, then the interdigit timer value should be set to a
				long (L) duration (e.g., 8 seconds).
				DigitmapLongTime : last-digit-time( 0~99s)"
			DEFVAL { 8 }
			::= { sheVoipDigitMapProfileEntry 4 }

		
		sheVoipDigitMapProfileShortTime OBJECT-TYPE
			SYNTAX Unsigned32 (0..99)
			UNITS "sec"
			MAX-ACCESS read-only
			STATUS current
			DESCRIPTION
				"If the digit string has matched one of the patterns in a digit map, but 
				it is possible that more digits could be received which would cause a match 
				with a different pattern, then instead of reporting the match immediately, 
				the MG must apply the short timer(S) and wait for more digits.
				DigitmapShortTime : inter-digit-time(0~99s)"
			DEFVAL { 4 }
			::= { sheVoipDigitMapProfileEntry 5 }

		
		sheVoipDigitMapProfileStartTime OBJECT-TYPE
			SYNTAX Unsigned32 (0..99)
			UNITS "sec"
			MAX-ACCESS read-only
			STATUS current
			DESCRIPTION
				"The start timer (T) is used prior to any digits having been dialed.
				This implies that the MG will wait for digits before time out.
				DigitmapStartTime : first-digit-time(0~99s)"
			DEFVAL { 10 }
			::= { sheVoipDigitMapProfileEntry 6 }

		
		sheVoipDigitMapProfileZTime OBJECT-TYPE
			SYNTAX Unsigned32 (0..99)
			UNITS "100 msec"
			MAX-ACCESS read-only
			STATUS current
			DESCRIPTION
				"A Z designates a long duration event: placed in front of the symbol(s) designating
				the event(s) which satisfy a given digit position, it indicates that that position 
				is satisfied only if the duration of the event exceeds the long-duration threshold.
				DigitmapZTime(0~99 100ms), default value is 5(100 milliseconds)"
			DEFVAL { 5 }
			::= { sheVoipDigitMapProfileEntry 7 }

		
		sheVoipDigitMapProfileControl OBJECT IDENTIFIER ::= { sheVoipDigitMapGroup 2 }

		
		sheVoipDigitMapProfileControlRequest OBJECT-TYPE
			SYNTAX SheVoipControlRequestType
			MAX-ACCESS read-write
			STATUS current
			DESCRIPTION
				"The request of a user command. 
				createVoipDigitMapProfile  	(60), 
					Must: sheVoipDigitMapProfileControlName 
					Optional: sheVoipDigitMapProfileControlDigitMap 			 
				         	  sheVoipDigitMapProfileControlLongTime				 
				         	  sheVoipDigitMapProfileControlShortTime    		       	            
				         	  sheVoipDigitMapProfileControlStartTime   			        	 
				         	  sheVoipDigitMapProfileControlZTime 
				         			   
					deleteVoipDigitMapProfile   (61), 
						Must: sheVoipDigitMapProfileControlIndex 
						 
				modifyVoipDigitMapProfile		(62) 
				             Must: sheVoipDigitMapProfileControlIndex 
					Optional: sheVoipDigitMapProfileControlName 
						  sheVoipDigitMapProfileControlDigitMap 			 
				         	  sheVoipDigitMapProfileControlLongTime				 
				         	  sheVoipDigitMapProfileControlShortTime    		       	            
				         	  sheVoipDigitMapProfileControlStartTime   			        	 
				         	  sheVoipDigitMapProfileControlZTime     			  
				"
			::= { sheVoipDigitMapProfileControl 1 }

		
		sheVoipDigitMapProfileControlIndex OBJECT-TYPE
			SYNTAX Unsigned32
			MAX-ACCESS read-write
			STATUS current
			DESCRIPTION
				"Table index"
			::= { sheVoipDigitMapProfileControl 2 }

		
		sheVoipDigitMapProfileControlName OBJECT-TYPE
			SYNTAX OCTET STRING (SIZE (0..31))
			MAX-ACCESS read-write
			STATUS current
			DESCRIPTION
				"The digitmap name is user specified.A default	 
				profile will always exist. This profile's name will be set to  
				`DEFVAL' and its parameters will be set to vendor specific values."
			::= { sheVoipDigitMapProfileControl 3 }

		
		sheVoipDigitMapProfileControlDigitMap OBJECT-TYPE
			SYNTAX OCTET STRING (SIZE (0..128))
			MAX-ACCESS read-write
			STATUS current
			DESCRIPTION
				"A DigitMap is a dialing plan resident in the Media Gateway used for   
				detecting and reporting digit events received on a Termination."
			::= { sheVoipDigitMapProfileControl 4 }

		
		sheVoipDigitMapProfileControlLongTime OBJECT-TYPE
			SYNTAX Unsigned32 (0..99)
			UNITS "sec"
			MAX-ACCESS read-write
			STATUS current
			DESCRIPTION
				"If the Media Gateway can determine that at least one more digit is 
				needed for a digit string to match any of the allowed patterns in
				the digit map, then the interdigit timer value should be set to a
				long (L) duration (e.g., 8 seconds).
				DigitmapLongTime : last-digit-time( 0~99s)"
			::= { sheVoipDigitMapProfileControl 5 }

		
		sheVoipDigitMapProfileControlShortTime OBJECT-TYPE
			SYNTAX Unsigned32 (0..99)
			UNITS "sec"
			MAX-ACCESS read-write
			STATUS current
			DESCRIPTION
				"If the digit string has matched one of the patterns in a digit map, but 
				it is possible that more digits could be received which would cause a match 
				with a different pattern, then instead of reporting the match immediately, 
				the MG must apply the short timer(S) and wait for more digits.
				DigitmapShortTime : inter-digit-time(0~99s)"
			::= { sheVoipDigitMapProfileControl 6 }

		
		sheVoipDigitMapProfileControlStartTime OBJECT-TYPE
			SYNTAX Unsigned32 (0..99)
			UNITS "sec"
			MAX-ACCESS read-write
			STATUS current
			DESCRIPTION
				"The start timer (T) is used prior to any digits having been dialed.
				This implies that the MG will wait for digits before time out.
				DigitmapStartTime : first-digit-time(0~99s)"
			::= { sheVoipDigitMapProfileControl 7 }

		
		sheVoipDigitMapProfileControlZTime OBJECT-TYPE
			SYNTAX Unsigned32 (0..99)
			UNITS "100 msec"
			MAX-ACCESS read-write
			STATUS current
			DESCRIPTION
				"A 'Z' designates a long duration event: placed in front of the symbol(s) designating
				the event(s) which satisfy a given digit position, it indicates that that position 
				is satisfied only if the duration of the event exceeds the long-duration threshold.
				DigitmapZTime(0~99 100ms), default value is 5(100 milliseconds)"
			::= { sheVoipDigitMapProfileControl 8 }

		
		sheVoipDigitMapProfileControlStatus OBJECT-TYPE
			SYNTAX SheControlStatusType
			MAX-ACCESS read-only
			STATUS current
			DESCRIPTION
				"The status of a user command."
			::= { sheVoipDigitMapProfileControl 9 }

		
		sheVoipDigitMapProfileControlTimer OBJECT-TYPE
			SYNTAX Gauge32
			MAX-ACCESS read-only
			STATUS current
			DESCRIPTION
				"The maximum wait time for the manager for a  
				long running user command."
			::= { sheVoipDigitMapProfileControl 10 }

		
		sheVoipDigitMapProfileControlReqResult OBJECT-TYPE
			SYNTAX SheVoipControlRequestResultType
			MAX-ACCESS read-only
			STATUS current
			DESCRIPTION
				"The result of the last user command."
			::= { sheVoipDigitMapProfileControl 11 }

		
		sheVoipDigitMapProfileControlTimeStamp OBJECT-TYPE
			SYNTAX TimeTicks
			MAX-ACCESS read-only
			STATUS current
			DESCRIPTION
				"The time stamp of the last command (end of command)."
			::= { sheVoipDigitMapProfileControl 12 }

		
		sheVoipPerformanceGroup OBJECT IDENTIFIER ::= { sheVoipMibModule 6 }

		
		sheVoipCallCtrlPmObjects OBJECT IDENTIFIER ::= { sheVoipPerformanceGroup 1 }

		
		sheVoipCallCtrlPmMonitorStartTime OBJECT-TYPE
			SYNTAX DateAndTime
			MAX-ACCESS read-only
			STATUS current
			DESCRIPTION
				"Time to start collecting statistics data.
				The counters will be cleared when the StartTime or StopTime is changed.  
				They start to be updated when the StartTime is reached."
			::= { sheVoipCallCtrlPmObjects 1 }

		
		sheVoipCallCtrlPmMonitorStopTime OBJECT-TYPE
			SYNTAX DateAndTime
			MAX-ACCESS read-only
			STATUS current
			DESCRIPTION
				"Time to stop collecting statistics data."
			::= { sheVoipCallCtrlPmObjects 2 }

		
		sheVoipCallCtrlPmTable OBJECT-TYPE
			SYNTAX SEQUENCE OF SheVoipCallCtrlPmEntry
			MAX-ACCESS not-accessible
			STATUS current
			DESCRIPTION
				"This table contains attributes for each sheVoipCallCtrlPmTable."
			::= { sheVoipCallCtrlPmObjects 3 }

		
		sheVoipCallCtrlPmEntry OBJECT-TYPE
			SYNTAX SheVoipCallCtrlPmEntry
			MAX-ACCESS not-accessible
			STATUS current
			DESCRIPTION
				"An entry in sheVoipCallCtrlPmTable."
			INDEX { ifIndex }
			::= { sheVoipCallCtrlPmTable 1 }

		
		SheVoipCallCtrlPmEntry ::=
			SEQUENCE { 
				sheVoipCallCtrlPmAverageCallDuration
					Unsigned32,
				sheVoipCallCtrlPmAtpOccuNum
					Unsigned32,
				sheVoipCallCtrlPmOccuNum
					Unsigned32
			 }

		sheVoipCallCtrlPmAverageCallDuration OBJECT-TYPE
			SYNTAX Unsigned32
			UNITS "second"
			MAX-ACCESS read-only
			STATUS current
			DESCRIPTION
				"Average call duration during the period between 
				sheVoipCallCtrlPmMonitorStartTime and sheVoipCallCtrlPmMonitorStopTime 
				on this port."
			::= { sheVoipCallCtrlPmEntry 1 }

		
		sheVoipCallCtrlPmAtpOccuNum OBJECT-TYPE
			SYNTAX Unsigned32
			MAX-ACCESS read-only
			STATUS current
			DESCRIPTION
				"Total number of attempted calls on this port."
			::= { sheVoipCallCtrlPmEntry 2 }

		
		sheVoipCallCtrlPmOccuNum OBJECT-TYPE
			SYNTAX Unsigned32
			MAX-ACCESS read-only
			STATUS current
			DESCRIPTION
				"Total number of occupations on this port."
			::= { sheVoipCallCtrlPmEntry 3 }

		
		sheVoipCallCtrlPmControl OBJECT IDENTIFIER ::= { sheVoipCallCtrlPmObjects 4 }

		
		sheVoipCallCtrlPmControlRequest OBJECT-TYPE
			SYNTAX SheVoipControlRequestType
			MAX-ACCESS read-write
			STATUS current
			DESCRIPTION
				"The request of a user command: 
				setCallCtrlPmMonitorTime     (70)
					Must: sheVoipCallCtrlPmControlMonitorStartTime 
					      sheVoipCallCtrlPmControlMonitorStopTime "
			::= { sheVoipCallCtrlPmControl 1 }

		
		sheVoipCallCtrlPmControlMonitorStartTime OBJECT-TYPE
			SYNTAX DateAndTime
			MAX-ACCESS read-write
			STATUS current
			DESCRIPTION
				"Time to start collecting statistics data, can't be set to a time
				value which is earlier than the current time or later than monitor stop time.
				The counters will be cleared when the StartTime or StopTime is changed.  
				They start to be updated when the StartTime is reached.
				Date and time should be desplayed as: 
				2d-1d-1d,1d:1d:1d.1d,1a1d:1d
				field  octets  contents                  range
				-----  ------  --------                  -----
				1      1-2   year                      0..65536
				2       3    month                     1..12
				3       4    day                       1..31
				4       5    hour                      0..23
				5       6    minutes                   0..59
				6       7    seconds                   0..60
				           (use 60 for leap-second)
				7       8    deci-seconds              0..9
				8       9    direction from UTC        '+' / '-'
				9      10    hours from UTC            0..11
				10      11    minutes from UTC          0..59
				
				For example, Tuesday May 26, 1992 at 1:30:15 PM EDT would be
				displayed as:
				
				            1992-5-26,13:30:15.0,-4:0
				
				Note that if only local time is known, then timezone
				information (fields 8-10) is not present.     		
				"
			::= { sheVoipCallCtrlPmControl 2 }

		
		sheVoipCallCtrlPmControlMonitorStopTime OBJECT-TYPE
			SYNTAX DateAndTime
			MAX-ACCESS read-write
			STATUS current
			DESCRIPTION
				"Time to stop collecting statistics data.     		
				The counters will be cleared when the StartTime or StopTime is changed. 
				Date and time should be desplayed as: 
				2d-1d-1d,1d:1d:1d.1d,1a1d:1d
				field  octets  contents                  range
				-----  ------  --------                  -----
				1      1-2   year                      0..65536
				2       3    month                     1..12
				3       4    day                       1..31
				4       5    hour                      0..23
				5       6    minutes                   0..59
				6       7    seconds                   0..60
				           (use 60 for leap-second)
				7       8    deci-seconds              0..9
				8       9    direction from UTC        '+' / '-'
				9      10    hours from UTC            0..11
				10      11    minutes from UTC          0..59
				
				For example, Tuesday May 26, 1992 at 1:30:15 PM EDT would be
				displayed as:
				
				            1992-5-26,13:30:15.0,-4:0
				
				Note that if only local time is known, then timezone
				information (fields 8-10) is not present.      		
				"
			::= { sheVoipCallCtrlPmControl 3 }

		
		sheVoipCallCtrlPmControlStatus OBJECT-TYPE
			SYNTAX SheControlStatusType
			MAX-ACCESS read-only
			STATUS current
			DESCRIPTION
				"The status of a user command."
			::= { sheVoipCallCtrlPmControl 4 }

		
		sheVoipCallCtrlPmControlTimer OBJECT-TYPE
			SYNTAX Gauge32
			MAX-ACCESS read-only
			STATUS current
			DESCRIPTION
				"The maximum wait time for the manager for a  
				long running user command."
			::= { sheVoipCallCtrlPmControl 5 }

		
		sheVoipCallCtrlPmControlTimeStamp OBJECT-TYPE
			SYNTAX TimeTicks
			MAX-ACCESS read-only
			STATUS current
			DESCRIPTION
				"The time stamp of the last command (end of command)."
			::= { sheVoipCallCtrlPmControl 6 }

		
		sheVoipCallCtrlPmControlReqResult OBJECT-TYPE
			SYNTAX SheVoipControlRequestResultType
			MAX-ACCESS read-only
			STATUS current
			DESCRIPTION
				"The result of the last user command."
			::= { sheVoipCallCtrlPmControl 7 }

		
		sheVoipRtpMonPmObjects OBJECT IDENTIFIER ::= { sheVoipPerformanceGroup 2 }

		
		sheVoipRtpMonPmMonitorStartTime OBJECT-TYPE
			SYNTAX DateAndTime
			MAX-ACCESS read-only
			STATUS current
			DESCRIPTION
				"Time to start collecting statistics data.
				The counters will be cleared when the StartTime or StopTime is changed.  
				They start to be updated when the StartTime is reached."
			::= { sheVoipRtpMonPmObjects 1 }

		
		sheVoipRtpMonPmMonitorStopTime OBJECT-TYPE
			SYNTAX DateAndTime
			MAX-ACCESS read-only
			STATUS current
			DESCRIPTION
				"Time to stop collecting statistics data."
			::= { sheVoipRtpMonPmObjects 2 }

		
		sheVoipRtpMonPmTable OBJECT-TYPE
			SYNTAX SEQUENCE OF SheVoipRtpMonPmEntry
			MAX-ACCESS not-accessible
			STATUS current
			DESCRIPTION
				"This table contains attributes for each sheVoipRtpMonPmTable."
			::= { sheVoipRtpMonPmObjects 3 }

		
		sheVoipRtpMonPmEntry OBJECT-TYPE
			SYNTAX SheVoipRtpMonPmEntry
			MAX-ACCESS not-accessible
			STATUS current
			DESCRIPTION
				"An entry in sheVoipRtpMonPmTable."
			INDEX { ifIndex }
			::= { sheVoipRtpMonPmTable 1 }

		
		SheVoipRtpMonPmEntry ::=
			SEQUENCE { 
				sheVoipRtpMonPmInOctetsNum
					Counter64,
				sheVoipRtpMonPmOutOctetsNum
					Counter64,
				sheVoipRtpMonPmInPacketsNum
					Counter64,
				sheVoipRtpMonPmOutPacketsNum
					Counter64,
				sheVoipRtpMonPmPacketLoss
					Unsigned32,
				sheVoipRtpMonPmAverageDelay
					Unsigned32,
				sheVoipRtpMonPmJitter
					Unsigned32
			 }

		sheVoipRtpMonPmInOctetsNum OBJECT-TYPE
			SYNTAX Counter64
			MAX-ACCESS read-only
			STATUS current
			DESCRIPTION
				"Number of octets received"
			::= { sheVoipRtpMonPmEntry 1 }

		
		sheVoipRtpMonPmOutOctetsNum OBJECT-TYPE
			SYNTAX Counter64
			MAX-ACCESS read-only
			STATUS current
			DESCRIPTION
				"Number of octets sent"
			::= { sheVoipRtpMonPmEntry 2 }

		
		sheVoipRtpMonPmInPacketsNum OBJECT-TYPE
			SYNTAX Counter64
			MAX-ACCESS read-only
			STATUS current
			DESCRIPTION
				"Number of Packets received"
			::= { sheVoipRtpMonPmEntry 3 }

		
		sheVoipRtpMonPmOutPacketsNum OBJECT-TYPE
			SYNTAX Counter64
			MAX-ACCESS read-only
			STATUS current
			DESCRIPTION
				"Number of Packets sent"
			::= { sheVoipRtpMonPmEntry 4 }

		
		sheVoipRtpMonPmPacketLoss OBJECT-TYPE
			SYNTAX Unsigned32
			MAX-ACCESS read-only
			STATUS current
			DESCRIPTION
				"Number of lost packets."
			::= { sheVoipRtpMonPmEntry 5 }

		
		sheVoipRtpMonPmAverageDelay OBJECT-TYPE
			SYNTAX Unsigned32
			UNITS "0.01 second"
			MAX-ACCESS read-only
			STATUS current
			DESCRIPTION
				"The average latency of RTP packets.  
				It is an average value over all calls during the monitoring period."
			::= { sheVoipRtpMonPmEntry 6 }

		
		sheVoipRtpMonPmJitter OBJECT-TYPE
			SYNTAX Unsigned32
			UNITS "0.01 second"
			MAX-ACCESS read-only
			STATUS current
			DESCRIPTION
				"The statistical variance of the RTP data interarrival time. 
				It is an average value over all calls during the monitoring period."
			::= { sheVoipRtpMonPmEntry 7 }

		
		sheVoipRtpMonPmControl OBJECT IDENTIFIER ::= { sheVoipRtpMonPmObjects 4 }

		
		sheVoipRtpMonPmControlRequest OBJECT-TYPE
			SYNTAX SheVoipControlRequestType
			MAX-ACCESS read-write
			STATUS current
			DESCRIPTION
				"The request of a user command: 
				setRtpMonitorTime     (80)
					Must: 	 sheVoipRtpMonPmControlMonitorStartTime 
				         			 sheVoipRtpMonPmControlMonitorStopTime  						     
				"
			::= { sheVoipRtpMonPmControl 1 }

		
		sheVoipRtpMonPmControlMonitorStartTime OBJECT-TYPE
			SYNTAX DateAndTime
			MAX-ACCESS read-write
			STATUS current
			DESCRIPTION
				"Time to start collecting statistics data, can't be set to a time
				value which is earlier than the current time or later than monitor stop time.
				The counters will be cleared when the StartTime or StopTime is changed.  
				They start to be updated when the StartTime is reached.
				
				Date and time should be desplayed as: 
				2d-1d-1d,1d:1d:1d.1d,1a1d:1d
				field  octets  contents                  range
				-----  ------  --------                  -----
				1      1-2   year                      0..65536
				2       3    month                     1..12
				3       4    day                       1..31
				4       5    hour                      0..23
				5       6    minutes                   0..59
				6       7    seconds                   0..60
				           (use 60 for leap-second)
				7       8    deci-seconds              0..9
				8       9    direction from UTC        '+' / '-'
				9      10    hours from UTC            0..11
				10      11    minutes from UTC          0..59
				
				For example, Tuesday May 26, 1992 at 1:30:15 PM EDT would be
				displayed as:
				
				            1992-5-26,13:30:15.0,-4:0
				
				Note that if only local time is known, then timezone
				information (fields 8-10) is not present. 
				"
			::= { sheVoipRtpMonPmControl 2 }

		
		sheVoipRtpMonPmControlMonitorStopTime OBJECT-TYPE
			SYNTAX DateAndTime
			MAX-ACCESS read-write
			STATUS current
			DESCRIPTION
				"Time to stop collecting statistics data.
				
				Date and time should be desplayed as: 
				2d-1d-1d,1d:1d:1d.1d,1a1d:1d
				field  octets  contents                  range
				-----  ------  --------                  -----
				1      1-2   year                      0..65536
				2       3    month                     1..12
				3       4    day                       1..31
				4       5    hour                      0..23
				5       6    minutes                   0..59
				6       7    seconds                   0..60
				           (use 60 for leap-second)
				7       8    deci-seconds              0..9
				8       9    direction from UTC        '+' / '-'
				9      10    hours from UTC            0..11
				10      11    minutes from UTC          0..59
				
				For example, Tuesday May 26, 1992 at 1:30:15 PM EDT would be
				displayed as:
				
				            1992-5-26,13:30:15.0,-4:0
				
				Note that if only local time is known, then timezone
				information (fields 8-10) is not present. 
				"
			::= { sheVoipRtpMonPmControl 3 }

		
		sheVoipRtpMonPmControlStatus OBJECT-TYPE
			SYNTAX SheControlStatusType
			MAX-ACCESS read-only
			STATUS current
			DESCRIPTION
				"The status of a user command."
			::= { sheVoipRtpMonPmControl 4 }

		
		sheVoipRtpMonPmControlTimer OBJECT-TYPE
			SYNTAX Gauge32
			MAX-ACCESS read-only
			STATUS current
			DESCRIPTION
				"The maximum wait time for the manager for a  
				long running user command."
			::= { sheVoipRtpMonPmControl 5 }

		
		sheVoipRtpMonPmControlTimeStamp OBJECT-TYPE
			SYNTAX TimeTicks
			MAX-ACCESS read-only
			STATUS current
			DESCRIPTION
				"The time stamp of the last command (end of command)."
			::= { sheVoipRtpMonPmControl 6 }

		
		sheVoipRtpMonPmControlReqResult OBJECT-TYPE
			SYNTAX SheVoipControlRequestResultType
			MAX-ACCESS read-only
			STATUS current
			DESCRIPTION
				"The result of the last user command."
			::= { sheVoipRtpMonPmControl 7 }

		
		sheVoipVgwMonPmObjects OBJECT IDENTIFIER ::= { sheVoipPerformanceGroup 3 }

		
		sheVoipVgwPmMonitorStartTime OBJECT-TYPE
			SYNTAX DateAndTime
			MAX-ACCESS read-only
			STATUS current
			DESCRIPTION
				"Time to start collecting statistics data.
				The counters will be cleared when the StartTime or StopTime is changed.  
				They start to be updated when the StartTime is reached.
				"
			::= { sheVoipVgwMonPmObjects 1 }

		
		sheVoipVgwPmMonitorStopTime OBJECT-TYPE
			SYNTAX DateAndTime
			MAX-ACCESS read-only
			STATUS current
			DESCRIPTION
				"Time to stop collecting statistics data."
			::= { sheVoipVgwMonPmObjects 2 }

		
		sheVoipVgwMonPmTable OBJECT-TYPE
			SYNTAX SEQUENCE OF SheVoipVgwMonPmEntry
			MAX-ACCESS not-accessible
			STATUS current
			DESCRIPTION
				"This table contains attributes for each sheVoipVgwMonPmTable."
			::= { sheVoipVgwMonPmObjects 3 }

		
		sheVoipVgwMonPmEntry OBJECT-TYPE
			SYNTAX SheVoipVgwMonPmEntry
			MAX-ACCESS not-accessible
			STATUS current
			DESCRIPTION
				"An entry in sheVoipVgwMonPmTable."
			INDEX { sheVoipVgwIndex }
			::= { sheVoipVgwMonPmTable 1 }

		
		SheVoipVgwMonPmEntry ::=
			SEQUENCE { 
				sheVoipVgwPmMonNumInMessages
					Counter64,
				sheVoipVgwPmMonNumOutMessages
					Counter64,
				sheVoipVgwPmMonNumInRtpOctets
					Counter64,
				sheVoipVgwPmMonNumOutRtpOctets
					Counter64,
				sheVoipVgwPmMonAllBusyTime
					Unsigned32
			 }

		sheVoipVgwPmMonNumInMessages OBJECT-TYPE
			SYNTAX Counter64
			MAX-ACCESS read-only
			STATUS current
			DESCRIPTION
				"Total number of messages received on this virtual gateway."
			::= { sheVoipVgwMonPmEntry 1 }

		
		sheVoipVgwPmMonNumOutMessages OBJECT-TYPE
			SYNTAX Counter64
			MAX-ACCESS read-only
			STATUS current
			DESCRIPTION
				"Total number of messages sent on this virtual gateway."
			::= { sheVoipVgwMonPmEntry 2 }

		
		sheVoipVgwPmMonNumInRtpOctets OBJECT-TYPE
			SYNTAX Counter64
			MAX-ACCESS read-only
			STATUS current
			DESCRIPTION
				"Total number of rtp octets received on this virtual gateway."
			::= { sheVoipVgwMonPmEntry 3 }

		
		sheVoipVgwPmMonNumOutRtpOctets OBJECT-TYPE
			SYNTAX Counter64
			MAX-ACCESS read-only
			STATUS current
			DESCRIPTION
				"Total number of rtp octets sent on this virtual gateway."
			::= { sheVoipVgwMonPmEntry 4 }

		
		sheVoipVgwPmMonAllBusyTime OBJECT-TYPE
			SYNTAX Unsigned32
			MAX-ACCESS read-only
			STATUS current
			DESCRIPTION
				"Total number of all busy time on this virtual gateway."
			::= { sheVoipVgwMonPmEntry 5 }

		
		sheVoipVgwMonPmControl OBJECT IDENTIFIER ::= { sheVoipVgwMonPmObjects 4 }

		
		sheVoipVgwMonPmControlRequest OBJECT-TYPE
			SYNTAX SheVoipControlRequestType
			MAX-ACCESS read-write
			STATUS current
			DESCRIPTION
				"The request of a user command: 
				setVgwMonitorTime     (90)
					Must: 	 sheVoipVgwMonPmControlMonitorStartTime 
							 sheVoipVgwMonPmControlMonitorStopTime	 						     
				"
			::= { sheVoipVgwMonPmControl 1 }

		
		sheVoipVgwMonPmControlMonitorStartTime OBJECT-TYPE
			SYNTAX DateAndTime
			MAX-ACCESS read-write
			STATUS current
			DESCRIPTION
				"Time to start collecting statistics data, can't be set to a time
				value which is earlier than the current time or later than monitor stop time.
				The counters will be cleared when the StartTime or StopTime is changed.  
				They start to be updated when the StartTime is reached.
				
				Date and time should be desplayed as: 
				2d-1d-1d,1d:1d:1d.1d,1a1d:1d
				field  octets  contents                  range
				-----  ------  --------                  -----
				1      1-2   year                      0..65536
				2       3    month                     1..12
				3       4    day                       1..31
				4       5    hour                      0..23
				5       6    minutes                   0..59
				6       7    seconds                   0..60
				           (use 60 for leap-second)
				7       8    deci-seconds              0..9
				8       9    direction from UTC        '+' / '-'
				9      10    hours from UTC            0..11
				10      11    minutes from UTC          0..59
				
				For example, Tuesday May 26, 1992 at 1:30:15 PM EDT would be
				displayed as:
				
				            1992-5-26,13:30:15.0,-4:0
				
				Note that if only local time is known, then timezone
				information (fields 8-10) is not present. 
				"
			::= { sheVoipVgwMonPmControl 2 }

		
		sheVoipVgwMonPmControlMonitorStopTime OBJECT-TYPE
			SYNTAX DateAndTime
			MAX-ACCESS read-write
			STATUS current
			DESCRIPTION
				"Time to stop collecting statistics data.
				
				Date and time should be desplayed as: 
				2d-1d-1d,1d:1d:1d.1d,1a1d:1d
				field  octets  contents                  range
				-----  ------  --------                  -----
				1      1-2   year                      0..65536
				2       3    month                     1..12
				3       4    day                       1..31
				4       5    hour                      0..23
				5       6    minutes                   0..59
				6       7    seconds                   0..60
				           (use 60 for leap-second)
				7       8    deci-seconds              0..9
				8       9    direction from UTC        '+' / '-'
				9      10    hours from UTC            0..11
				10      11    minutes from UTC          0..59
				
				For example, Tuesday May 26, 1992 at 1:30:15 PM EDT would be
				displayed as:
				
				            1992-5-26,13:30:15.0,-4:0
				
				Note that if only local time is known, then timezone
				information (fields 8-10) is not present. 
				"
			::= { sheVoipVgwMonPmControl 3 }

		
		sheVoipVgwMonPmControlStatus OBJECT-TYPE
			SYNTAX SheControlStatusType
			MAX-ACCESS read-only
			STATUS current
			DESCRIPTION
				"The status of a user command."
			::= { sheVoipVgwMonPmControl 4 }

		
		sheVoipVgwMonPmControlTimer OBJECT-TYPE
			SYNTAX Gauge32
			MAX-ACCESS read-only
			STATUS current
			DESCRIPTION
				"The maximum wait time for the manager for a  
				long running user command."
			::= { sheVoipVgwMonPmControl 5 }

		
		sheVoipVgwMonPmControlTimeStamp OBJECT-TYPE
			SYNTAX TimeTicks
			MAX-ACCESS read-only
			STATUS current
			DESCRIPTION
				"The time stamp of the last command (end of command)."
			::= { sheVoipVgwMonPmControl 6 }

		
		sheVoipVgwMonPmControlReqResult OBJECT-TYPE
			SYNTAX SheVoipControlRequestResultType
			MAX-ACCESS read-only
			STATUS current
			DESCRIPTION
				"The result of the last user command."
			::= { sheVoipVgwMonPmControl 7 }

		
		sheVoipNotifications OBJECT IDENTIFIER ::= { sheVoipMibModule 7 }

		
		sheVoipEvents OBJECT IDENTIFIER ::= { sheVoipNotifications 1 }

		
		sheVoipVgwEvents OBJECT IDENTIFIER ::= { sheVoipEvents 1 }

		
		sheVoipVgwCreatedTrap NOTIFICATION-TYPE
			OBJECTS { sheVoipVgwIndex, sheVoipVgwName, sheVoipVgwAdminStatus, sheVoipVgwOperStatus, sheVoipVgwMemberList, 
				sheVoipVgwDmList, sheVoipVgwIpAddr, sheVoipVgwPortNumber, sheVoipVgwSignalingProtocol, sheVoipVgwMgConfigProfileIndex, 
				sheVoipVgwMgcConfigProfileIndex, sheVoipVgwAlarmSeverityIndex, sheVoipVgwPrioProfileIndex, sheVoipVgwControlTimeStamp }
			STATUS current
			DESCRIPTION 
				"Indicates that vgw entry is created successfully."
			::= { sheVoipVgwEvents 1 }

		
		sheVoipVgwDeletedTrap NOTIFICATION-TYPE
			OBJECTS { sheVoipVgwIndex, sheVoipVgwName, sheVoipVgwControlTimeStamp }
			STATUS current
			DESCRIPTION 
				"Indicates that vgw entry is deleted successfully."
			::= { sheVoipVgwEvents 2 }

		
		sheVoipVgwConfigModifiedTrap NOTIFICATION-TYPE
			OBJECTS { sheVoipVgwIndex, sheVoipVgwName, sheVoipVgwAdminStatus, sheVoipVgwOperStatus, sheVoipVgwMemberList, 
				sheVoipVgwDmList, sheVoipVgwIpAddr, sheVoipVgwPortNumber, sheVoipVgwSignalingProtocol, sheVoipVgwMgConfigProfileIndex, 
				sheVoipVgwMgcConfigProfileIndex, sheVoipVgwAlarmSeverityIndex, sheVoipVgwPrioProfileIndex, sheVoipVgwControlTimeStamp }
			STATUS current
			DESCRIPTION 
				"Indicates that vgw entry is modified successfully."
			::= { sheVoipVgwEvents 3 }

		
		sheVoipVgwOperStatusChangedTrap NOTIFICATION-TYPE
			OBJECTS { sheVoipVgwIndex, sheVoipVgwName, sheVoipVgwAdminStatus, sheVoipVgwOperStatus, sheVoipVgwMemberList, 
				sheVoipVgwControlTimeStamp }
			STATUS current
			DESCRIPTION 
				"Indicates that vgw operStatus is changed."
			::= { sheVoipVgwEvents 4 }

		
		sheVoipCallPriorityProfileEvents OBJECT IDENTIFIER ::= { sheVoipEvents 2 }

		
		sheVoipCallPriorityProfileCreatedTrap NOTIFICATION-TYPE
			OBJECTS { sheVoipCallPriorityProfileIndex, sheVoipCallPriorityProfileName, sheVoipCallPriorityProfileLevel1, sheVoipCallPriorityProfileLevel2, sheVoipCallPriorityProfileLevel3, 
				sheVoipCallPriorityProfileControlTimeStamp }
			STATUS current
			DESCRIPTION 
				"Indicates that VgwPriorityProfile entry is created successfully."
			::= { sheVoipCallPriorityProfileEvents 1 }

		
		sheVoipCallPriorityProfileDeletedTrap NOTIFICATION-TYPE
			OBJECTS { sheVoipCallPriorityProfileIndex, sheVoipCallPriorityProfileName, sheVoipCallPriorityProfileControlTimeStamp }
			STATUS current
			DESCRIPTION 
				"Indicates that VgwPriorityProfile entry is deleted successfully."
			::= { sheVoipCallPriorityProfileEvents 2 }

		
		sheVoipCallPriorityProfileModifiedTrap NOTIFICATION-TYPE
			OBJECTS { sheVoipCallPriorityProfileIndex, sheVoipCallPriorityProfileName, sheVoipCallPriorityProfileLevel1, sheVoipCallPriorityProfileLevel2, sheVoipCallPriorityProfileLevel3, 
				sheVoipCallPriorityProfileControlTimeStamp }
			STATUS current
			DESCRIPTION 
				"Indicates that VgwPriorityProfile entry is modified successfully."
			::= { sheVoipCallPriorityProfileEvents 3 }

		
		sheVoipMgcConfigProfileEvents OBJECT IDENTIFIER ::= { sheVoipEvents 3 }

		
		sheVoipMgcConfigProfileCreatedTrap NOTIFICATION-TYPE
			OBJECTS { sheVoipMgcConfigProfileIndex, sheVoipMgcConfigProfileName, sheVoipMgcConfigProfileIPAddress1, sheVoipMgcConfigProfileIPAddress2, sheVoipMgcConfigProfileIPAddress3, 
				sheVoipMgcConfigProfileIPAddress4, sheVoipMgcConfigProfileIPAddress5, sheVoipMgcConfigProfilePort1, sheVoipMgcConfigProfilePort2, sheVoipMgcConfigProfilePort3, 
				sheVoipMgcConfigProfilePort4, sheVoipMgcConfigProfilePort5, sheVoipMgcConfigProfileSoftswitch1, sheVoipMgcConfigProfileSoftswitch2, sheVoipMgcConfigProfileSoftswitch3, 
				sheVoipMgcConfigProfileSoftswitch4, sheVoipMgcConfigProfileSoftswitch5, sheVoipMgcConfigProfileControlTimeStamp }
			STATUS current
			DESCRIPTION 
				"Indicates that MgcConfigProfile entry is created successfully."
			::= { sheVoipMgcConfigProfileEvents 1 }

		
		sheVoipMgcConfigProfileDeletedTrap NOTIFICATION-TYPE
			OBJECTS { sheVoipMgcConfigProfileIndex, sheVoipMgcConfigProfileName, sheVoipMgcConfigProfileControlTimeStamp }
			STATUS current
			DESCRIPTION 
				"Indicates that MgcConfigProfile entry is deleted successfully."
			::= { sheVoipMgcConfigProfileEvents 2 }

		
		sheVoipMgcConfigProfileModifiedTrap NOTIFICATION-TYPE
			OBJECTS { sheVoipMgcConfigProfileIndex, sheVoipMgcConfigProfileName, sheVoipMgcConfigProfileIPAddress1, sheVoipMgcConfigProfileIPAddress2, sheVoipMgcConfigProfileIPAddress3, 
				sheVoipMgcConfigProfileIPAddress4, sheVoipMgcConfigProfileIPAddress5, sheVoipMgcConfigProfilePort1, sheVoipMgcConfigProfilePort2, sheVoipMgcConfigProfilePort3, 
				sheVoipMgcConfigProfilePort4, sheVoipMgcConfigProfilePort5, sheVoipMgcConfigProfileSoftswitch1, sheVoipMgcConfigProfileSoftswitch2, sheVoipMgcConfigProfileSoftswitch3, 
				sheVoipMgcConfigProfileSoftswitch4, sheVoipMgcConfigProfileSoftswitch5, sheVoipMgcConfigProfileControlTimeStamp }
			STATUS current
			DESCRIPTION 
				"Indicates that MgcConfigProfile entry is modified successfully."
			::= { sheVoipMgcConfigProfileEvents 3 }

		
		sheVoipH248MgConfigProfileEvents OBJECT IDENTIFIER ::= { sheVoipEvents 4 }

		
		sheVoipH248MgConfigProfileCreatedTrap NOTIFICATION-TYPE
			OBJECTS { sheVoipH248MgConfigProfileIndex, sheVoipH248MgConfigProfileName, sheVoipH248MgConfigProfileEncodingScheme, sheVoipH248MgConfigProfileProtocolVersion, sheVoipH248MgConfigProfileUseTimestamp, 
				sheVoipH248MgConfigProfileNamingPhyTerm, sheVoipH248MgConfigProfileNamingRtpTerm, sheVoipH248MgConfigProfilePkgList, sheVoipH248MgConfigProfileHeartBeatTime, sheVoipH248MgConfigProfileRetransTime, 
				sheVoipH248MgConfigProfileMaxRetransCount, sheVoipH248MgConfigProfileStartupType, sheVoipH248MgConfigProfileMWD, sheVoipH248MgConfigProfileTermQuitMode, sheVoipH248MgConfigProfileTcpUdpCfgProtocol, 
				sheVoipH248MgConfigProfileMarkTos, sheVoipH248MgConfigProfileControlTimeStamp }
			STATUS current
			DESCRIPTION 
				"Indicates that MgConfigProfile entry is created successfully."
			::= { sheVoipH248MgConfigProfileEvents 1 }

		
		sheVoipH248MgConfigProfileDeletedTrap NOTIFICATION-TYPE
			OBJECTS { sheVoipH248MgConfigProfileIndex, sheVoipH248MgConfigProfileName, sheVoipH248MgConfigProfileControlTimeStamp }
			STATUS current
			DESCRIPTION 
				"Indicates that MgConfigProfile entry is deleted successfully."
			::= { sheVoipH248MgConfigProfileEvents 2 }

		
		sheVoipH248MgConfigProfileModifiedTrap NOTIFICATION-TYPE
			OBJECTS { sheVoipH248MgConfigProfileIndex, sheVoipH248MgConfigProfileName, sheVoipH248MgConfigProfileEncodingScheme, sheVoipH248MgConfigProfileProtocolVersion, sheVoipH248MgConfigProfileUseTimestamp, 
				sheVoipH248MgConfigProfileNamingPhyTerm, sheVoipH248MgConfigProfileNamingRtpTerm, sheVoipH248MgConfigProfilePkgList, sheVoipH248MgConfigProfileHeartBeatTime, sheVoipH248MgConfigProfileRetransTime, 
				sheVoipH248MgConfigProfileMaxRetransCount, sheVoipH248MgConfigProfileStartupType, sheVoipH248MgConfigProfileMWD, sheVoipH248MgConfigProfileTermQuitMode, sheVoipH248MgConfigProfileTcpUdpCfgProtocol, 
				sheVoipH248MgConfigProfileMarkTos, sheVoipH248MgConfigProfileControlTimeStamp }
			STATUS current
			DESCRIPTION 
				"Indicates that MgConfigProfile entry is modified successfully."
			::= { sheVoipH248MgConfigProfileEvents 3 }

		
		sheVoipMediaCodecProfileEvents OBJECT IDENTIFIER ::= { sheVoipEvents 5 }

		
		sheVoipMediaCodecProfileCreatedTrap NOTIFICATION-TYPE
			OBJECTS { sheVoipMediaCodecProfileIndex, sheVoipMediaCodecProfileName, sheVoipMediaCodecProfileCodecCapability, sheVoipMediaCodecProfileG726PayloadType, sheVoipMediaCodecProfileG723Bitrate, 
				sheVoipMediaCodecProfileG726Bitrate, sheVoipMediaCodecProfileCodecPTimeG711, sheVoipMediaCodecProfileCodecPTimeG723, sheVoipMediaCodecProfileCodecPTimeG726, sheVoipMediaCodecProfileCodecPTimeG729, 
				sheVoipMediaCodecProfileEC, sheVoipMediaCodecProfileVad, sheVoipMediaCodecProfilePLC, sheVoipMediaCodecProfileCng, sheVoipMediaCodecProfileAutoSwitchCodec, 
				sheVoipMediaCodecProfileG711passThruCodec, sheVoipMediaCodecProfileG711passThruPayloadType, sheVoipMediaCodecProfileControlTimeStamp }
			STATUS current
			DESCRIPTION 
				"Indicates that MediaCodecProfile entry is created successfully."
			::= { sheVoipMediaCodecProfileEvents 1 }

		
		sheVoipMediaCodecProfileDeletedTrap NOTIFICATION-TYPE
			OBJECTS { sheVoipMediaCodecProfileIndex, sheVoipMediaCodecProfileName, sheVoipMediaCodecProfileControlTimeStamp }
			STATUS current
			DESCRIPTION 
				"Indicates that MediaCodecProfile entry is deleted successfully."
			::= { sheVoipMediaCodecProfileEvents 2 }

		
		sheVoipMediaCodecProfileModifiedTrap NOTIFICATION-TYPE
			OBJECTS { sheVoipMediaCodecProfileIndex, sheVoipMediaCodecProfileName, sheVoipMediaCodecProfileCodecCapability, sheVoipMediaCodecProfileG726PayloadType, sheVoipMediaCodecProfileG723Bitrate, 
				sheVoipMediaCodecProfileG726Bitrate, sheVoipMediaCodecProfileCodecPTimeG711, sheVoipMediaCodecProfileCodecPTimeG723, sheVoipMediaCodecProfileCodecPTimeG726, sheVoipMediaCodecProfileCodecPTimeG729, 
				sheVoipMediaCodecProfileEC, sheVoipMediaCodecProfileVad, sheVoipMediaCodecProfilePLC, sheVoipMediaCodecProfileCng, sheVoipMediaCodecProfileAutoSwitchCodec, 
				sheVoipMediaCodecProfileG711passThruCodec, sheVoipMediaCodecProfileG711passThruPayloadType, sheVoipMediaCodecProfileControlTimeStamp }
			STATUS current
			DESCRIPTION 
				"Indicates that MediaCodecProfile entry is modified successfully."
			::= { sheVoipMediaCodecProfileEvents 3 }

		
		sheVoipMediaJitterBufProfileEvents OBJECT IDENTIFIER ::= { sheVoipEvents 6 }

		
		sheVoipMediaJitterBufProfileCreatedTrap NOTIFICATION-TYPE
			OBJECTS { sheVoipMediaJitterBufProfileIndex, sheVoipMediaJitterBufProfileName, sheVoipMediaJitterBufProfileJitterMode, sheVoipMediaJitterBufProfileJitterMin, sheVoipMediaJitterBufProfileJitterMax, 
				sheVoipMediaJitterBufProfileJitterInit, sheVoipMediaJitterBufProfileJitterUpdatePeriod, sheVoipMediaJitterBufProfileJitterDelThreshold, sheVoipMediaJitterBufProfileJitterFaxModem, sheVoipMediaJitterBufProfileControlTimeStamp
				 }
			STATUS current
			DESCRIPTION 
				"Indicates that Jitter Buf Profile entry is created successfully."
			::= { sheVoipMediaJitterBufProfileEvents 1 }

		
		sheVoipMediaJitterBufProfileDeletedTrap NOTIFICATION-TYPE
			OBJECTS { sheVoipMediaJitterBufProfileIndex, sheVoipMediaJitterBufProfileName, sheVoipMediaJitterBufProfileControlTimeStamp }
			STATUS current
			DESCRIPTION 
				"Indicates that Jitter Buf Profile entry is deleted successfully."
			::= { sheVoipMediaJitterBufProfileEvents 2 }

		
		sheVoipMediaJitterBufProfileModifiedTrap NOTIFICATION-TYPE
			OBJECTS { sheVoipMediaJitterBufProfileIndex, sheVoipMediaJitterBufProfileName, sheVoipMediaJitterBufProfileJitterMode, sheVoipMediaJitterBufProfileJitterMin, sheVoipMediaJitterBufProfileJitterMax, 
				sheVoipMediaJitterBufProfileJitterInit, sheVoipMediaJitterBufProfileJitterUpdatePeriod, sheVoipMediaJitterBufProfileJitterDelThreshold, sheVoipMediaJitterBufProfileJitterFaxModem, sheVoipMediaJitterBufProfileControlTimeStamp
				 }
			STATUS current
			DESCRIPTION 
				"Indicates that Jitter Buf Profile entry is modified successfully."
			::= { sheVoipMediaJitterBufProfileEvents 3 }

		
		sheVoipMediaFaxProfileEvents OBJECT IDENTIFIER ::= { sheVoipEvents 7 }

		
		sheVoipMediaFaxProfileCreatedTrap NOTIFICATION-TYPE
			OBJECTS { sheVoipMediaFaxProfileIndex, sheVoipMediaFaxProfileName, sheVoipMediaFaxProfileModemDetect, sheVoipMediaFaxProfileFaxTypeUsed, sheVoipMediaFaxProfileFaxMaxBaudrate, 
				sheVoipMediaFaxProfileT38FaxEcm, sheVoipMediaFaxProfileT38FaxTcfmode, sheVoipMediaFaxProfileT38FaxNumFec, sheVoipMediaFaxProfileT38FaxNumIfp, sheVoipMediaFaxProfileT38FaxBytemode, 
				sheVoipMediaFaxProfileControlTimeStamp }
			STATUS current
			DESCRIPTION 
				"Indicates that fax Profile entry is created successfully."
			::= { sheVoipMediaFaxProfileEvents 1 }

		
		sheVoipMediaFaxProfileDeletedTrap NOTIFICATION-TYPE
			OBJECTS { sheVoipMediaFaxProfileIndex, sheVoipMediaFaxProfileName, sheVoipMediaFaxProfileControlTimeStamp }
			STATUS current
			DESCRIPTION 
				"Indicates that fax Profile entry is deleted successfully."
			::= { sheVoipMediaFaxProfileEvents 2 }

		
		sheVoipMediaFaxProfileModifiedTrap NOTIFICATION-TYPE
			OBJECTS { sheVoipMediaFaxProfileIndex, sheVoipMediaFaxProfileName, sheVoipMediaFaxProfileModemDetect, sheVoipMediaFaxProfileFaxTypeUsed, sheVoipMediaFaxProfileFaxMaxBaudrate, 
				sheVoipMediaFaxProfileT38FaxEcm, sheVoipMediaFaxProfileT38FaxTcfmode, sheVoipMediaFaxProfileT38FaxNumFec, sheVoipMediaFaxProfileT38FaxNumIfp, sheVoipMediaFaxProfileT38FaxBytemode, 
				sheVoipMediaFaxProfileControlTimeStamp }
			STATUS current
			DESCRIPTION 
				"Indicates that fax Profile entry is modified successfully."
			::= { sheVoipMediaFaxProfileEvents 3 }

		
		sheVoipRtcpProfileEvents OBJECT IDENTIFIER ::= { sheVoipEvents 8 }

		
		sheVoipRtcpProfileCreatedTrap NOTIFICATION-TYPE
			OBJECTS { sheVoipRtcpProfileIndex, sheVoipRtcpProfileName, sheVoipRtcpProfileDtmf, sheVoipRtcpProfileT38FaxRedPktCount, sheVoipRtcpProfileT30FaxRedPktCount, 
				sheVoipRtcpProfileDtmfRfc2833PktType, sheVoipRtcpProfileDtmfRfc2833RedPktType, sheVoipRtcpProfileRTPRedPktCount, sheVoipRtcpProfileRtcpGen, sheVoipRtcpProfileRtcpInterval, 
				sheVoipRtcpProfileFecPayLoadType, sheVoipRtcpProfileControlTimeStamp }
			STATUS current
			DESCRIPTION 
				"Indicates that rtpRtcp Profile entry is created successfully."
			::= { sheVoipRtcpProfileEvents 1 }

		
		sheVoipRtcpProfileDeletedTrap NOTIFICATION-TYPE
			OBJECTS { sheVoipRtcpProfileIndex, sheVoipRtcpProfileName, sheVoipRtcpProfileControlTimeStamp }
			STATUS current
			DESCRIPTION 
				"Indicates that rtpRtcp Profile entry is deleted successfully."
			::= { sheVoipRtcpProfileEvents 2 }

		
		sheVoipRtcpProfileModifiedTrap NOTIFICATION-TYPE
			OBJECTS { sheVoipRtcpProfileIndex, sheVoipRtcpProfileName, sheVoipRtcpProfileDtmf, sheVoipRtcpProfileT38FaxRedPktCount, sheVoipRtcpProfileT30FaxRedPktCount, 
				sheVoipRtcpProfileDtmfRfc2833PktType, sheVoipRtcpProfileDtmfRfc2833RedPktType, sheVoipRtcpProfileRTPRedPktCount, sheVoipRtcpProfileRtcpGen, sheVoipRtcpProfileRtcpInterval, 
				sheVoipRtcpProfileFecPayLoadType, sheVoipRtcpProfileControlTimeStamp }
			STATUS current
			DESCRIPTION 
				"Indicates that rtpRtcp Profile entry is modified successfully."
			::= { sheVoipRtcpProfileEvents 3 }

		
		sheVoipVoipVoiceCtpEvents OBJECT IDENTIFIER ::= { sheVoipEvents 9 }

		
		sheVoipVoiceCtpConfigModifiedTrap NOTIFICATION-TYPE
			OBJECTS { ifIndex, sheVoipVoipVoiceCtpVgwIndex, sheVoipVoipVoiceCtpIpHostProfileIndex, sheVoipVoipVoiceCtpCodecProfileIndex, sheVoipVoipVoiceCtpJitterBufProfileIndex, 
				sheVoipVoipVoiceCtpFaxProfileIndex, sheVoipVoipVoiceCtpRtcpProfileIndex, sheVoipVoipVoiceCtpRtpUdpPortBase, sheVoipVoipVoiceCtpRtpStreamTos, sheVoipVoipVoiceCtpControlIfIndexBitMask, 
				sheVoipVoipVoiceCtpControlTimeStamp }
			STATUS current
			DESCRIPTION 
				"Indicates that ctp configuration entry is modified successfully."
			::= { sheVoipVoipVoiceCtpEvents 1 }

		
		sheVoipIpHostProfileEvents OBJECT IDENTIFIER ::= { sheVoipEvents 10 }

		
		sheVoipIpHostProfileCreatedTrap NOTIFICATION-TYPE
			OBJECTS { sheVoipIpHostProfileIndex, sheVoipIpHostProfileName, sheVoipIpHostProfileUseDhcp, sheVoipIpHostProfileIpAddress, sheVoipIpHostProfileSubnetMask, 
				sheVoipIpHostProfileDefaultGateway, sheVoipIpHostProfileControlTimeStamp }
			STATUS current
			DESCRIPTION 
				"Indicates that IP host Profile entry is created successfully."
			::= { sheVoipIpHostProfileEvents 1 }

		
		sheVoipIpHostProfileDeletedTrap NOTIFICATION-TYPE
			OBJECTS { sheVoipIpHostProfileIndex, sheVoipIpHostProfileName, sheVoipIpHostProfileControlTimeStamp }
			STATUS current
			DESCRIPTION 
				"Indicates that IP host Profile entry is deleted successfully."
			::= { sheVoipIpHostProfileEvents 2 }

		
		sheVoipIpHostProfileModifiedTrap NOTIFICATION-TYPE
			OBJECTS { sheVoipIpHostProfileIndex, sheVoipIpHostProfileName, sheVoipIpHostProfileUseDhcp, sheVoipIpHostProfileIpAddress, sheVoipIpHostProfileSubnetMask, 
				sheVoipIpHostProfileDefaultGateway, sheVoipIpHostProfileControlTimeStamp }
			STATUS current
			DESCRIPTION 
				"Indicates that IP host Profile entry is modified successfully."
			::= { sheVoipIpHostProfileEvents 3 }

		
		sheVoipDigitMapProfileEvents OBJECT IDENTIFIER ::= { sheVoipEvents 11 }

		
		sheVoipDigitMapProfileCreatedTrap NOTIFICATION-TYPE
			OBJECTS { sheVoipDigitMapProfileIndex, sheVoipDigitMapProfileName, sheVoipDigitMapProfileDigitMap, sheVoipDigitMapProfileLongTime, sheVoipDigitMapProfileShortTime, 
				sheVoipDigitMapProfileStartTime, sheVoipDigitMapProfileZTime, sheVoipDigitMapProfileControlTimeStamp }
			STATUS current
			DESCRIPTION 
				"Indicates that DigitMap entry is created successfully."
			::= { sheVoipDigitMapProfileEvents 1 }

		
		sheVoipDigitMapProfileDeletedTrap NOTIFICATION-TYPE
			OBJECTS { sheVoipDigitMapProfileIndex, sheVoipDigitMapProfileName, sheVoipDigitMapProfileControlTimeStamp }
			STATUS current
			DESCRIPTION 
				"Indicates that DigitMap entry is deleted successfully."
			::= { sheVoipDigitMapProfileEvents 2 }

		
		sheVoipDigitMapProfileModifiedTrap NOTIFICATION-TYPE
			OBJECTS { sheVoipDigitMapProfileIndex, sheVoipDigitMapProfileName, sheVoipDigitMapProfileDigitMap, sheVoipDigitMapProfileLongTime, sheVoipDigitMapProfileShortTime, 
				sheVoipDigitMapProfileStartTime, sheVoipDigitMapProfileZTime, sheVoipDigitMapProfileControlTimeStamp }
			STATUS current
			DESCRIPTION 
				"Indicates that DigitMap entry is modified successfully."
			::= { sheVoipDigitMapProfileEvents 3 }

		
		sheVoipPerformanceEvents OBJECT IDENTIFIER ::= { sheVoipEvents 12 }

		
		sheVoipCallCtrlStatsFinishedTrap NOTIFICATION-TYPE
			OBJECTS { sheVoipCallCtrlPmMonitorStartTime, sheVoipCallCtrlPmMonitorStopTime }
			STATUS current
			DESCRIPTION 
				"Trap is sent out when call control data collecting is finished. "
			::= { sheVoipPerformanceEvents 1 }

		
		sheVoipRtpMonPmStatsFinishedTrap NOTIFICATION-TYPE
			OBJECTS { sheVoipRtpMonPmMonitorStartTime, sheVoipRtpMonPmMonitorStopTime }
			STATUS current
			DESCRIPTION 
				"Trap is sent out when rtp data collecting is finished. "
			::= { sheVoipPerformanceEvents 2 }

		
		sheVoipVgwMonPmStatsFinishedTrap NOTIFICATION-TYPE
			OBJECTS { sheVoipVgwPmMonitorStartTime, sheVoipVgwPmMonitorStopTime }
			STATUS current
			DESCRIPTION 
				"Trap is sent out when vgw data collecting is finished. "
			::= { sheVoipPerformanceEvents 3 }

		
-- cn2zj090 on 2007-07-12
		sheVoipSipUserAgentEvents OBJECT IDENTIFIER ::= { sheVoipEvents 13 }

		
		sheVoipSipUAConfigProfileCreatedTrap NOTIFICATION-TYPE
			OBJECTS { sheVoipSipUAConfigProfileIndex, sheVoipSipUAConfigProfileName, sheVoipSipUAConfigProfileRegExpTime, sheVoipSipUAConfigProfileReRegHeadStartTime, sheVoipSipUAConfigProfileSipProfileIndex, 
				sheVoipSipUAConfigProfileFACProfileIndex, sheVoipSipUAConfigProfileControlTimeStamp }
			STATUS current
			DESCRIPTION 
				"Indicates that User Agent entry is created successfully."
			::= { sheVoipSipUserAgentEvents 1 }

		
		sheVoipSipUAConfigProfileDeletedTrap NOTIFICATION-TYPE
			OBJECTS { sheVoipSipUAConfigProfileIndex, sheVoipSipUAConfigProfileName, sheVoipSipUAConfigProfileControlTimeStamp }
			STATUS current
			DESCRIPTION 
				"Indicates that User Agent entry is deleted successfully."
			::= { sheVoipSipUserAgentEvents 2 }

		
		sheVoipSipUAConfigProfileModifiedTrap NOTIFICATION-TYPE
			OBJECTS { sheVoipSipUAConfigProfileIndex, sheVoipSipUAConfigProfileName, sheVoipSipUAConfigProfileRegExpTime, sheVoipSipUAConfigProfileReRegHeadStartTime, sheVoipSipUAConfigProfileSipProfileIndex, 
				sheVoipSipUAConfigProfileFACProfileIndex, sheVoipSipUAConfigProfileControlTimeStamp }
			STATUS current
			DESCRIPTION 
				"Indicates that User Agent entry is modified successfully."
			::= { sheVoipSipUserAgentEvents 3 }

		
		sheVoipSipProfileEvents OBJECT IDENTIFIER ::= { sheVoipEvents 14 }

		
		sheVoipSipProfileCreatedTrap NOTIFICATION-TYPE
			OBJECTS { sheVoipSipProfileIndex, sheVoipSipProfileName, sheVoipSipProfileProtocolVersion, sheVoipSipProfileOrganization, sheVoipSipProfileInitialTimerReq, 
				sheVoipSipProfileInitialTimerInvite, sheVoipSipProfileInitialTimerAck, sheVoipSipProfileInitialTimerBye, sheVoipSipProfileInitialTimerCancel, sheVoipSipProfileInitialTimerRegister, 
				sheVoipSipProfileInitialTimerOptions, sheVoipSipProfileInitialTimerPrack, sheVoipSipProfileInitialTimerRsp, sheVoipSipProfileTimerT2, sheVoipSipProfileTimerT4, 
				sheVoipSipProfileRetryReq, sheVoipSipProfileRetryInvite, sheVoipSipProfileRetryAck, sheVoipSipProfileRetryBye, sheVoipSipProfileRetryCancel, 
				sheVoipSipProfileRetryOptions, sheVoipSipProfileRetryPrack, sheVoipSipProfileRetryRegister, sheVoipSipProfileRetryFinalResponse, sheVoipSipProfileCMTimeout, 
				sheVoipSipProfileTimeout, sheVoipSipProfileCacheTimer, sheVoipSipProfileForward100toCM, sheVoipSipProfileTcpSocketTimeout, sheVoipSipProfileSend100, 
				sheVoipSipProfileMaxTransactions, sheVoipSipProfileMaxTcpConnections, sheVoipSipProfileProxyForwardAll1xx, sheVoipSipProfileDefOvlMinor, sheVoipSipProfileDefOvlMajor, 
				sheVoipSipProfileDefOvlCritical, sheVoipSipProfileDefOvlClear, sheVoipSipProfileDefOvlInvite, sheVoipSipProfileDefOvlRegister, sheVoipSipProfileDefOvlAuth, 
				sheVoipSipProfileUseOvlHdl, sheVoipSipProfileControlTimeStamp }
			STATUS current
			DESCRIPTION 
				"Indicates that Sip Profile entry is created successfully."
			::= { sheVoipSipProfileEvents 1 }

		
		sheVoipSipProfileDeletedTrap NOTIFICATION-TYPE
			OBJECTS { sheVoipSipProfileIndex, sheVoipSipProfileName, sheVoipSipProfileControlTimeStamp }
			STATUS current
			DESCRIPTION 
				"Indicates that Sip Profile entry is deleted successfully."
			::= { sheVoipSipProfileEvents 2 }

		
		sheVoipSipProfileModifiedTrap NOTIFICATION-TYPE
			OBJECTS { sheVoipSipProfileIndex, sheVoipSipProfileName, sheVoipSipProfileProtocolVersion, sheVoipSipProfileOrganization, sheVoipSipProfileInitialTimerReq, 
				sheVoipSipProfileInitialTimerInvite, sheVoipSipProfileInitialTimerAck, sheVoipSipProfileInitialTimerBye, sheVoipSipProfileInitialTimerCancel, sheVoipSipProfileInitialTimerRegister, 
				sheVoipSipProfileInitialTimerOptions, sheVoipSipProfileInitialTimerPrack, sheVoipSipProfileInitialTimerRsp, sheVoipSipProfileTimerT2, sheVoipSipProfileTimerT4, 
				sheVoipSipProfileRetryReq, sheVoipSipProfileRetryInvite, sheVoipSipProfileRetryAck, sheVoipSipProfileRetryBye, sheVoipSipProfileRetryCancel, 
				sheVoipSipProfileRetryOptions, sheVoipSipProfileRetryPrack, sheVoipSipProfileRetryRegister, sheVoipSipProfileRetryFinalResponse, sheVoipSipProfileCMTimeout, 
				sheVoipSipProfileTimeout, sheVoipSipProfileCacheTimer, sheVoipSipProfileForward100toCM, sheVoipSipProfileTcpSocketTimeout, sheVoipSipProfileSend100, 
				sheVoipSipProfileMaxTransactions, sheVoipSipProfileMaxTcpConnections, sheVoipSipProfileProxyForwardAll1xx, sheVoipSipProfileDefOvlMinor, sheVoipSipProfileDefOvlMajor, 
				sheVoipSipProfileDefOvlCritical, sheVoipSipProfileDefOvlClear, sheVoipSipProfileDefOvlInvite, sheVoipSipProfileDefOvlRegister, sheVoipSipProfileDefOvlAuth, 
				sheVoipSipProfileUseOvlHdl, sheVoipSipProfileControlTimeStamp }
			STATUS current
			DESCRIPTION 
				"Indicates that Sip Profile entry is modified successfully."
			::= { sheVoipSipProfileEvents 3 }

		
		sheVoipSipServerEvents OBJECT IDENTIFIER ::= { sheVoipEvents 15 }

		
		sheVoipSipServerCreatedTrap NOTIFICATION-TYPE
			OBJECTS { sheVoipSipServerConfigProfileIndex, sheVoipSipRegServerConfigProfileAddr, sheVoipSipServerConfigProfileFunction, sheVoipSipServerConfigProfileName, sheVoipSipProxyServerConfigProfileIpAddress1, 
				sheVoipSipProxyServerConfigProfileIpAddress2, sheVoipSipProxyServerConfigProfileIpAddress3, sheVoipSipProxyServerConfigProfilePort1, sheVoipSipProxyServerConfigProfilePort2, sheVoipSipProxyServerConfigProfilePort3, 
				sheVoipSipUsingProxyServerID, sheVoipSipServerConfigProfileSoftswitch, sheVoipSipServerConfigProfilePrimarySipDns, sheVoipSipServerConfigProfileSecondarySipDns, sheVoipSipServerConfigProfileControlTimeStamp
				 }
			STATUS current
			DESCRIPTION 
				"Indicates that Sip Server entry is created successfully."
			::= { sheVoipSipServerEvents 1 }

		
		sheVoipSipServerDeletedTrap NOTIFICATION-TYPE
			OBJECTS { sheVoipSipServerConfigProfileIndex, sheVoipSipServerConfigProfileName, sheVoipSipServerConfigProfileControlTimeStamp }
			STATUS current
			DESCRIPTION 
				"Indicates that Sip Server entry is deleted successfully."
			::= { sheVoipSipServerEvents 2 }

		
		sheVoipSipServerModifiedTrap NOTIFICATION-TYPE
			OBJECTS { sheVoipSipServerConfigProfileIndex, sheVoipSipRegServerConfigProfileAddr, sheVoipSipServerConfigProfileFunction, sheVoipSipServerConfigProfileName, sheVoipSipProxyServerConfigProfileIpAddress1, 
				sheVoipSipProxyServerConfigProfileIpAddress2, sheVoipSipProxyServerConfigProfileIpAddress3, sheVoipSipProxyServerConfigProfilePort1, sheVoipSipProxyServerConfigProfilePort2, sheVoipSipProxyServerConfigProfilePort3, 
				sheVoipSipUsingProxyServerID, sheVoipSipServerConfigProfileSoftswitch, sheVoipSipServerConfigProfilePrimarySipDns, sheVoipSipServerConfigProfileSecondarySipDns, sheVoipSipServerConfigProfileControlTimeStamp
				 }
			STATUS current
			DESCRIPTION 
				"Indicates that Sip Server entry is modified successfully."
			::= { sheVoipSipServerEvents 3 }

		
		sheVoipSipFACProfileEvents OBJECT IDENTIFIER ::= { sheVoipEvents 16 }

		
		sheVoipSipFACProfileCreatedTrap NOTIFICATION-TYPE
			OBJECTS { sheVoipSipFACProfileIndex, sheVoipSipFACProfileName, sheVoipSipFACProfileCallForwardingUnconditionalActive, sheVoipSipFACProfileCallForwardingUnconditionalDeactive, sheVoipSipFACProfileCallForwardingOnBusyActive, 
				sheVoipSipFACProfileCallForwardingOnBusyDeactive, sheVoipSipFACProfileCallForwardingNoAnswerActive, sheVoipSipFACProfileCallForwardingNoAnswerDeactive, sheVoipSipFACProfileCallingLineIdRestrictionActive, sheVoipSipFACProfileCallingLineIdRestrictionDeactive, 
				sheVoipSipFACProfileMaliciousIdentificationActive, sheVoipSipFACProfileMaliciousIdentificationDeactive, sheVoipSipFACProfileCallCompletiontoOnBusySubsActive, sheVoipSipFACProfileCallCompletiontoOnBusySubsDeactive, sheVoipSipFACProfileCallCompletiontoNoAnswerSubsActive, 
				sheVoipSipFACProfileCallCompletiontoNoAnswerSubsDeactive, sheVoipSipFACProfileOutgoingCallBarringActive, sheVoipSipFACProfileOutgoingCallBarringDeactive, sheVoipSipFACProfileSelectiveCallAcceptanceActive, sheVoipSipFACProfileSelectiveCallAcceptanceDeactive, 
				sheVoipSipFACProfileControlTimeStamp }
			STATUS current
			DESCRIPTION 
				"Indicates that Feature Access Codes entry is created successfully."
			::= { sheVoipSipFACProfileEvents 1 }

		
		sheVoipSipFACProfileDeletedTrap NOTIFICATION-TYPE
			OBJECTS { sheVoipSipFACProfileIndex, sheVoipSipFACProfileName, sheVoipSipFACProfileControlTimeStamp }
			STATUS current
			DESCRIPTION 
				"Indicates that Feature Access Codes entry is deleted successfully."
			::= { sheVoipSipFACProfileEvents 2 }

		
		sheVoipSipFACProfileModifiedTrap NOTIFICATION-TYPE
			OBJECTS { sheVoipSipFACProfileIndex, sheVoipSipFACProfileName, sheVoipSipFACProfileCallForwardingUnconditionalActive, sheVoipSipFACProfileCallForwardingUnconditionalDeactive, sheVoipSipFACProfileCallForwardingOnBusyActive, 
				sheVoipSipFACProfileCallForwardingOnBusyDeactive, sheVoipSipFACProfileCallForwardingNoAnswerActive, sheVoipSipFACProfileCallForwardingNoAnswerDeactive, sheVoipSipFACProfileCallingLineIdRestrictionActive, sheVoipSipFACProfileCallingLineIdRestrictionDeactive, 
				sheVoipSipFACProfileMaliciousIdentificationActive, sheVoipSipFACProfileMaliciousIdentificationDeactive, sheVoipSipFACProfileCallCompletiontoOnBusySubsActive, sheVoipSipFACProfileCallCompletiontoOnBusySubsDeactive, sheVoipSipFACProfileCallCompletiontoNoAnswerSubsActive, 
				sheVoipSipFACProfileCallCompletiontoNoAnswerSubsDeactive, sheVoipSipFACProfileOutgoingCallBarringActive, sheVoipSipFACProfileOutgoingCallBarringDeactive, sheVoipSipFACProfileSelectiveCallAcceptanceActive, sheVoipSipFACProfileSelectiveCallAcceptanceDeactive, 
				sheVoipSipFACProfileControlTimeStamp }
			STATUS current
			DESCRIPTION 
				"Indicates that Feature Access Codes entry is modified successfully."
			::= { sheVoipSipFACProfileEvents 3 }

		
		sheVoipAlarms OBJECT IDENTIFIER ::= { sheVoipNotifications 2 }

		
		sheVoipVgwAlarms OBJECT IDENTIFIER ::= { sheVoipAlarms 1 }

		
		sheVoipVgwDownAlarm NOTIFICATION-TYPE
			OBJECTS { sheAlarmTimeAndDate, sheAlarmReportingSource, sheAlarmReportingSourceType, sheAlarmSeverity }
			STATUS current
			DESCRIPTION 
				"Alarm raised when VGW is down."
			::= { sheVoipVgwAlarms 1 }

		
-- cn2zj090 on 2007-06-27     
		sheVoipSipDataGroup OBJECT IDENTIFIER ::= { sheVoipMibModule 8 }

		
-- cn2zj090 on 2007-06-27 in BeiJing      
-- sheVoipSipUserAgentConfigProfileTable
		sheVoipSipUAConfigProfileTable OBJECT-TYPE
			SYNTAX SEQUENCE OF SheVoipSipUAConfigProfileEntry
			MAX-ACCESS not-accessible
			STATUS current
			DESCRIPTION
				"this table contains all sip user agent atributes "
			::= { sheVoipSipDataGroup 1 }

		
		sheVoipSipUAConfigProfileEntry OBJECT-TYPE
			SYNTAX SheVoipSipUAConfigProfileEntry
			MAX-ACCESS not-accessible
			STATUS current
			DESCRIPTION
				"An entry in  sheVoipSipUserAgentConfigProfileTable."
			INDEX { sheVoipSipUAConfigProfileIndex }
			::= { sheVoipSipUAConfigProfileTable 1 }

		
		SheVoipSipUAConfigProfileEntry ::=
			SEQUENCE { 
				sheVoipSipUAConfigProfileIndex
					Unsigned32,
				sheVoipSipUAConfigProfileName
					DisplayString,
				sheVoipSipUAConfigProfileRegExpTime
					Unsigned32,
				sheVoipSipUAConfigProfileReRegHeadStartTime
					Unsigned32,
				sheVoipSipUAConfigProfileSipProfileIndex
					Unsigned32,
				sheVoipSipUAConfigProfileFACProfileIndex
					Unsigned32
			 }

		sheVoipSipUAConfigProfileIndex OBJECT-TYPE
			SYNTAX Unsigned32
			MAX-ACCESS read-only
			STATUS current
			DESCRIPTION
				"Table index. Each index uniquely identifies one Sip User Agent entry."
			::= { sheVoipSipUAConfigProfileEntry 1 }

		
		sheVoipSipUAConfigProfileName OBJECT-TYPE
			SYNTAX DisplayString
			MAX-ACCESS read-only
			STATUS current
			DESCRIPTION
				"A describable name that uniquely identifies a profile entry  
				of this table."
			::= { sheVoipSipUAConfigProfileEntry 2 }

		
		sheVoipSipUAConfigProfileRegExpTime OBJECT-TYPE
			SYNTAX Unsigned32 (900..86400)
			UNITS "sec"
			MAX-ACCESS read-only
			STATUS current
			DESCRIPTION
				"default: 3600s. The SIP Registration Expiration Time in seconds.
				If this value is zero, the SIP Agent will not add an expiration time to 
				the registration requests,and will not perform re-registration."
			DEFVAL { 3600 }
			::= { sheVoipSipUAConfigProfileEntry 3 }

		
		sheVoipSipUAConfigProfileReRegHeadStartTime OBJECT-TYPE
			SYNTAX Unsigned32 (600..86400)
			UNITS "sec"
			MAX-ACCESS read-only
			STATUS current
			DESCRIPTION
				"The time in seconds prior to timeout that the SIP Agent should start the 
				re-registration process. < RegExpTime value,default: 1500 sec"
			DEFVAL { 1500 }
			::= { sheVoipSipUAConfigProfileEntry 4 }

		
		sheVoipSipUAConfigProfileSipProfileIndex OBJECT-TYPE
			SYNTAX Unsigned32
			MAX-ACCESS read-only
			STATUS current
			DESCRIPTION
				"equal to sheVoipSipProfileIndex in sheVoipSipProfileTable."
			::= { sheVoipSipUAConfigProfileEntry 5 }

		
		sheVoipSipUAConfigProfileFACProfileIndex OBJECT-TYPE
			SYNTAX Unsigned32
			MAX-ACCESS read-only
			STATUS current
			DESCRIPTION
				"equal to sheVoipSipFACProfileIndex in sheVoipSipFACProfileTable."
			::= { sheVoipSipUAConfigProfileEntry 6 }

		
-- --sheVoipSipUserAgentConfigProfileControl
		sheVoipSipUAConfigProfileControl OBJECT IDENTIFIER ::= { sheVoipSipDataGroup 2 }

		
		sheVoipSipUAConfigProfileControlRequest OBJECT-TYPE
			SYNTAX SheVoipControlRequestType
			MAX-ACCESS read-write
			STATUS current
			DESCRIPTION
				"The request of a user command. 
				createSipUAConfigProfile  (100),            
				         	Must:		sheVoipSipUAConfigProfileControlName 				 
				         	Optional:	sheVoipSipUAConfigProfileControlRegExpTime
				         				sheVoipSipUAConfigProfileControlReRegHeadStartTime		 
								sheVoipSipUAConfigProfileControlSipProfileIndex
								sheVoipSipUAConfigProfileControlFACProfileIndex
				     	 	 
				modifySipUAConfigProfile	 (120), 
				         	Must:	 sheVoipSipUAConfigProfileControlIndex	 				 
				         	Optional:	sheVoipSipUAConfigProfileControlRegExpTime
				         				sheVoipSipUAConfigProfileControlReRegHeadStartTime		 
								sheVoipSipUAConfigProfileControlSipProfileIndex
								sheVoipSipUAConfigProfileControlFACProfileIndex
					 
				deleteSipUAConfigProfile  (110), 
				        		Must:	 sheVoipSipUAConfigProfileControlIndex
				"
			::= { sheVoipSipUAConfigProfileControl 1 }

		
		sheVoipSipUAConfigProfileControlStatus OBJECT-TYPE
			SYNTAX SheControlStatusType
			MAX-ACCESS read-only
			STATUS current
			DESCRIPTION
				"The status of a user command."
			::= { sheVoipSipUAConfigProfileControl 2 }

		
		sheVoipSipUAConfigProfileControlTimer OBJECT-TYPE
			SYNTAX Gauge32
			MAX-ACCESS read-only
			STATUS current
			DESCRIPTION
				"The maximum wait time for the manager for a  
				long running user command."
			::= { sheVoipSipUAConfigProfileControl 3 }

		
		sheVoipSipUAConfigProfileControlTimeStamp OBJECT-TYPE
			SYNTAX TimeTicks
			MAX-ACCESS read-only
			STATUS current
			DESCRIPTION
				"The time stamp of the last command (end of command)."
			::= { sheVoipSipUAConfigProfileControl 4 }

		
		sheVoipSipUAConfigProfileControlReqResult OBJECT-TYPE
			SYNTAX SheVoipControlRequestResultType
			MAX-ACCESS read-only
			STATUS current
			DESCRIPTION
				"The result of the last user command."
			::= { sheVoipSipUAConfigProfileControl 5 }

		
		sheVoipSipUAConfigProfileControlIndex OBJECT-TYPE
			SYNTAX Unsigned32
			MAX-ACCESS read-write
			STATUS current
			DESCRIPTION
				"UA Table index"
			::= { sheVoipSipUAConfigProfileControl 6 }

		
		sheVoipSipUAConfigProfileControlName OBJECT-TYPE
			SYNTAX DisplayString
			MAX-ACCESS read-write
			STATUS current
			DESCRIPTION
				"UA Table name"
			::= { sheVoipSipUAConfigProfileControl 7 }

		
		sheVoipSipUAConfigProfileControlRegExpTime OBJECT-TYPE
			SYNTAX Unsigned32 (900..86400)
			UNITS "sec"
			MAX-ACCESS read-write
			STATUS current
			DESCRIPTION
				"default: 3600s. The SIP Registration Expiration Time in seconds.
				If this value is zero, the SIP Agent will not add an expiration time to 
				the registration requests,and will not perform re-registration."
			::= { sheVoipSipUAConfigProfileControl 8 }

		
		sheVoipSipUAConfigProfileControlReRegHeadStartTime OBJECT-TYPE
			SYNTAX Unsigned32 (600..86400)
			UNITS "sec"
			MAX-ACCESS read-write
			STATUS current
			DESCRIPTION
				"The time in seconds prior to timeout that the SIP Agent should start the 
				re-registration process. < RegExpTime value,default: 1500 sec"
			::= { sheVoipSipUAConfigProfileControl 9 }

		
		sheVoipSipUAConfigProfileControlSipProfileIndex OBJECT-TYPE
			SYNTAX Unsigned32
			MAX-ACCESS read-write
			STATUS current
			DESCRIPTION
				"sip profile index in sheVoipSipProfileTable"
			::= { sheVoipSipUAConfigProfileControl 10 }

		
		sheVoipSipUAConfigProfileControlFACProfileIndex OBJECT-TYPE
			SYNTAX Unsigned32
			MAX-ACCESS read-write
			STATUS current
			DESCRIPTION
				"sip FAC profile index in sheVoipSipFACProfileTable"
			::= { sheVoipSipUAConfigProfileControl 11 }

		
-- sheVoipSipProfileTable
		sheVoipSipProfileTable OBJECT-TYPE
			SYNTAX SEQUENCE OF SheVoipSipProfileEntry
			MAX-ACCESS not-accessible
			STATUS current
			DESCRIPTION
				"this table contains all sip profile atributes "
			::= { sheVoipSipDataGroup 3 }

		
		sheVoipSipProfileEntry OBJECT-TYPE
			SYNTAX SheVoipSipProfileEntry
			MAX-ACCESS not-accessible
			STATUS current
			DESCRIPTION
				"An entry in  sheVoipSipProfileTable."
			INDEX { sheVoipSipProfileIndex }
			::= { sheVoipSipProfileTable 1 }

		
		SheVoipSipProfileEntry ::=
			SEQUENCE { 
				sheVoipSipProfileIndex
					Unsigned32,
				sheVoipSipProfileName
					DisplayString,
				sheVoipSipProfileProtocolVersion
					SnmpAdminString,
				sheVoipSipProfileOrganization
					SnmpAdminString,
				sheVoipSipProfileMaxTransactions
					Unsigned32,
				sheVoipSipProfileInitialTimerReq
					Unsigned32,
				sheVoipSipProfileInitialTimerInvite
					Unsigned32,
				sheVoipSipProfileInitialTimerAck
					Unsigned32,
				sheVoipSipProfileInitialTimerBye
					Unsigned32,
				sheVoipSipProfileInitialTimerCancel
					Unsigned32,
				sheVoipSipProfileInitialTimerRegister
					Unsigned32,
				sheVoipSipProfileInitialTimerOptions
					Unsigned32,
				sheVoipSipProfileInitialTimerPrack
					Unsigned32,
				sheVoipSipProfileInitialTimerRsp
					Unsigned32,
				sheVoipSipProfileTimerT2
					Unsigned32,
				sheVoipSipProfileTimerT4
					Unsigned32,
				sheVoipSipProfileRetryReq
					Unsigned32,
				sheVoipSipProfileRetryInvite
					Unsigned32,
				sheVoipSipProfileRetryAck
					Unsigned32,
				sheVoipSipProfileRetryBye
					Unsigned32,
				sheVoipSipProfileRetryCancel
					Unsigned32,
				sheVoipSipProfileRetryOptions
					Unsigned32,
				sheVoipSipProfileRetryPrack
					Unsigned32,
				sheVoipSipProfileRetryRegister
					Unsigned32,
				sheVoipSipProfileRetryFinalResponse
					Unsigned32,
				sheVoipSipProfileCMTimeout
					Unsigned32,
				sheVoipSipProfileTimeout
					Unsigned32,
				sheVoipSipProfileCacheTimer
					Unsigned32,
				sheVoipSipProfileForward100toCM
					Unsigned32,
				sheVoipSipProfileTcpSocketTimeout
					Unsigned32,
				sheVoipSipProfileSend100
					Unsigned32,
				sheVoipSipProfileMaxTcpConnections
					Unsigned32,
				sheVoipSipProfileProxyForwardAll1xx
					Unsigned32,
				sheVoipSipProfileDefOvlMinor
					Unsigned32,
				sheVoipSipProfileDefOvlMajor
					Unsigned32,
				sheVoipSipProfileDefOvlCritical
					Unsigned32,
				sheVoipSipProfileDefOvlClear
					Unsigned32,
				sheVoipSipProfileDefOvlInvite
					SheVoipSipProfileOvlFlagType,
				sheVoipSipProfileDefOvlRegister
					SheVoipSipProfileOvlFlagType,
				sheVoipSipProfileDefOvlAuth
					SheVoipSipProfileOvlFlagType,
				sheVoipSipProfileUseOvlHdl
					SheVoipSipProfileOvlFlagType
			 }

		sheVoipSipProfileIndex OBJECT-TYPE
			SYNTAX Unsigned32
			MAX-ACCESS read-only
			STATUS current
			DESCRIPTION
				"Table index. Each index uniquely identifies one Sip profile entry."
			::= { sheVoipSipProfileEntry 1 }

		
		sheVoipSipProfileName OBJECT-TYPE
			SYNTAX DisplayString
			MAX-ACCESS read-only
			STATUS current
			DESCRIPTION
				"Table name."
			::= { sheVoipSipProfileEntry 2 }

		
		sheVoipSipProfileProtocolVersion OBJECT-TYPE
			SYNTAX SnmpAdminString
			MAX-ACCESS read-only
			STATUS current
			DESCRIPTION
				"This object will reflect the version of SIP supported by this SIP entity. "
			::= { sheVoipSipProfileEntry 3 }

		
		sheVoipSipProfileOrganization OBJECT-TYPE
			SYNTAX SnmpAdminString
			MAX-ACCESS read-only
			STATUS current
			DESCRIPTION
				"software provider name."
			::= { sheVoipSipProfileEntry 4 }

		
		sheVoipSipProfileMaxTransactions OBJECT-TYPE
			SYNTAX Unsigned32
			MAX-ACCESS read-only
			STATUS current
			DESCRIPTION
				"This object indicates the maximum number of simultaneous 
				transactions that the SIP entity can manage. (Registar & Proxy/Redirect)."
			::= { sheVoipSipProfileEntry 5 }

		
		sheVoipSipProfileInitialTimerReq OBJECT-TYPE
			SYNTAX Unsigned32 (100..1000)
			UNITS "msec"
			MAX-ACCESS read-only
			STATUS current
			DESCRIPTION
				"default: 500ms.This project specific value specifies the initial value 
				for the retransmit timer for a generic SIP-request.value = <100..1000>."
			DEFVAL { 500 }
			::= { sheVoipSipProfileEntry 6 }

		
		sheVoipSipProfileInitialTimerInvite OBJECT-TYPE
			SYNTAX Unsigned32 (100..1000)
			UNITS "msec"
			MAX-ACCESS read-only
			STATUS current
			DESCRIPTION
				"default: 500ms.This object specifies the initial value for the retransmit
				timer for the INVITE method. The retransmit timer doubles after each retransmission, 
				ensuring an exponential backoff in network traffic.value = <100..1000>."
			DEFVAL { 500 }
			::= { sheVoipSipProfileEntry 7 }

		
		sheVoipSipProfileInitialTimerAck OBJECT-TYPE
			SYNTAX Unsigned32 (100..1000)
			UNITS "msec"
			MAX-ACCESS read-only
			STATUS current
			DESCRIPTION
				"default: 500ms.This object specifies the initial value for the retransmit timer 
				for the ACK method.value = <100..1000>."
			DEFVAL { 500 }
			::= { sheVoipSipProfileEntry 8 }

		
		sheVoipSipProfileInitialTimerBye OBJECT-TYPE
			SYNTAX Unsigned32 (100..1000)
			UNITS "msec"
			MAX-ACCESS read-only
			STATUS current
			DESCRIPTION
				"default: 500ms.This object specifies the initial value for the retransmit timer 
				for the BYE method.value = <100..1000>."
			DEFVAL { 500 }
			::= { sheVoipSipProfileEntry 9 }

		
		sheVoipSipProfileInitialTimerCancel OBJECT-TYPE
			SYNTAX Unsigned32 (100..1000)
			UNITS "msec"
			MAX-ACCESS read-only
			STATUS current
			DESCRIPTION
				"default: 500ms.This object specifies the initial value for the retransmit timer 
				for the CANVEL method.value = <100..1000>."
			DEFVAL { 500 }
			::= { sheVoipSipProfileEntry 10 }

		
		sheVoipSipProfileInitialTimerRegister OBJECT-TYPE
			SYNTAX Unsigned32 (100..1000)
			UNITS "msec"
			MAX-ACCESS read-only
			STATUS current
			DESCRIPTION
				"default: 500ms.This object specifies the initial value for the retransmit timer 
				for the REGISTER method.value = <100..1000>."
			DEFVAL { 500 }
			::= { sheVoipSipProfileEntry 11 }

		
		sheVoipSipProfileInitialTimerOptions OBJECT-TYPE
			SYNTAX Unsigned32 (100..1000)
			UNITS "msec"
			MAX-ACCESS read-only
			STATUS current
			DESCRIPTION
				"default: 500ms.This object specifies the initial value for the retransmit timer 
				for the OPTIONS method.value = <100..1000>."
			DEFVAL { 500 }
			::= { sheVoipSipProfileEntry 12 }

		
		sheVoipSipProfileInitialTimerPrack OBJECT-TYPE
			SYNTAX Unsigned32 (100..1000)
			UNITS "msec"
			MAX-ACCESS read-only
			STATUS current
			DESCRIPTION
				"default: 500ms.This object specifies the initial value for the retransmit timer 
				for the PRACK method.value = <100..1000>."
			DEFVAL { 500 }
			::= { sheVoipSipProfileEntry 13 }

		
		sheVoipSipProfileInitialTimerRsp OBJECT-TYPE
			SYNTAX Unsigned32 (100..1000)
			UNITS "msec"
			MAX-ACCESS read-only
			STATUS current
			DESCRIPTION
				"default: 500ms.This object specifies the initial value for the retransmit timer 
				for final responses.value = <100..1000>."
			DEFVAL { 500 }
			::= { sheVoipSipProfileEntry 14 }

		
		sheVoipSipProfileTimerT2 OBJECT-TYPE
			SYNTAX Unsigned32 (200..10000)
			UNITS "msec"
			MAX-ACCESS read-only
			STATUS current
			DESCRIPTION
				"default: 4000ms.This object specifies the T2 timer for a SIP entity. 
				value = <200..10000>.REFERENCE Section 10.4 and 10.5 RFC2543."
			DEFVAL { 4000 }
			::= { sheVoipSipProfileEntry 15 }

		
		sheVoipSipProfileTimerT4 OBJECT-TYPE
			SYNTAX Unsigned32 (200..10000)
			UNITS "msec"
			MAX-ACCESS read-only
			STATUS current
			DESCRIPTION
				"default: 5000ms.This object specifies the T4 timer for a SIP entity. 
				value = <200..10000>.REFERENCE Section 17.1.2 RFC3261."
			DEFVAL { 5000 }
			::= { sheVoipSipProfileEntry 16 }

		
		sheVoipSipProfileRetryReq OBJECT-TYPE
			SYNTAX Unsigned32 (1..10)
			MAX-ACCESS read-only
			STATUS current
			DESCRIPTION
				"default: 6.This object will specify the number of times a SIP entity 
				will retry sending astandard request.value = <1..10>."
			DEFVAL { 6 }
			::= { sheVoipSipProfileEntry 17 }

		
		sheVoipSipProfileRetryInvite OBJECT-TYPE
			SYNTAX Unsigned32 (1..10)
			MAX-ACCESS read-only
			STATUS current
			DESCRIPTION
				"default: 6.This object will specify the number of times a SIP entity 
				will retry sending an INVITE request.value = <1..10>."
			DEFVAL { 6 }
			::= { sheVoipSipProfileEntry 18 }

		
		sheVoipSipProfileRetryAck OBJECT-TYPE
			SYNTAX Unsigned32 (1..10)
			MAX-ACCESS read-only
			STATUS current
			DESCRIPTION
				"default: 6.This object will specify the number of times a SIP entity 
				will retry sending an ACK request.value = <1..10>."
			DEFVAL { 6 }
			::= { sheVoipSipProfileEntry 19 }

		
		sheVoipSipProfileRetryBye OBJECT-TYPE
			SYNTAX Unsigned32 (1..10)
			MAX-ACCESS read-only
			STATUS current
			DESCRIPTION
				"default: 10.This object will specify the number of times a SIP entity 
				will retry sending an BYE request.value = <1..10>."
			DEFVAL { 10 }
			::= { sheVoipSipProfileEntry 20 }

		
		sheVoipSipProfileRetryCancel OBJECT-TYPE
			SYNTAX Unsigned32 (1..10)
			MAX-ACCESS read-only
			STATUS current
			DESCRIPTION
				"default: 10.This object will specify the number of times a SIP entity 
				will retry sending an CANCEL request.value = <1..10>."
			DEFVAL { 10 }
			::= { sheVoipSipProfileEntry 21 }

		
		sheVoipSipProfileRetryOptions OBJECT-TYPE
			SYNTAX Unsigned32 (1..10)
			MAX-ACCESS read-only
			STATUS current
			DESCRIPTION
				"default: 10.This object will specify the number of times a SIP entity 
				will retry sending an OPTIONS request.value = <1..10>."
			DEFVAL { 10 }
			::= { sheVoipSipProfileEntry 22 }

		
		sheVoipSipProfileRetryPrack OBJECT-TYPE
			SYNTAX Unsigned32 (1..10)
			MAX-ACCESS read-only
			STATUS current
			DESCRIPTION
				"default: 6.This object will specify the number of times a SIP entity 
				will retry sending an PRACK request.value = <1..10>."
			DEFVAL { 6 }
			::= { sheVoipSipProfileEntry 23 }

		
		sheVoipSipProfileRetryRegister OBJECT-TYPE
			SYNTAX Unsigned32 (1..10)
			MAX-ACCESS read-only
			STATUS current
			DESCRIPTION
				"default: 10.This object will specify the number of times a SIP entity 
				will retry sending an REGISTER request.value = <1..10>."
			DEFVAL { 10 }
			::= { sheVoipSipProfileEntry 24 }

		
		sheVoipSipProfileRetryFinalResponse OBJECT-TYPE
			SYNTAX Unsigned32 (1..10)
			MAX-ACCESS read-only
			STATUS current
			DESCRIPTION
				"default: 10.This object will specify the number of times a SIP entity 
				will retry sending a final response and expecting an ACK.value = <1..10>."
			DEFVAL { 10 }
			::= { sheVoipSipProfileEntry 25 }

		
		sheVoipSipProfileCMTimeout OBJECT-TYPE
			SYNTAX Unsigned32 (1..64000)
			UNITS "msec"
			MAX-ACCESS read-only
			STATUS current
			DESCRIPTION
				"default: 32000ms.Timeout to Callmanager.value=<1..64000>"
			DEFVAL { 32000 }
			::= { sheVoipSipProfileEntry 26 }

		
		sheVoipSipProfileTimeout OBJECT-TYPE
			SYNTAX Unsigned32 (1..192000)
			UNITS "msec"
			MAX-ACCESS read-only
			STATUS current
			DESCRIPTION
				"default:96000.Timeout to Callmanager transactionrelated.value=<1..192000>"
			DEFVAL { 96000 }
			::= { sheVoipSipProfileEntry 27 }

		
		sheVoipSipProfileCacheTimer OBJECT-TYPE
			SYNTAX Unsigned32 (1..64000)
			UNITS "msec"
			MAX-ACCESS read-only
			STATUS current
			DESCRIPTION
				"default:32000.The time a closed transaction is cached."
			DEFVAL { 32000 }
			::= { sheVoipSipProfileEntry 28 }

		
		sheVoipSipProfileForward100toCM OBJECT-TYPE
			SYNTAX Unsigned32
			MAX-ACCESS read-only
			STATUS current
			DESCRIPTION
				"Flag whether stack sends 100 tryings to the callmanager or not.1:yes,0:no.default:0"
			DEFVAL { 0 }
			::= { sheVoipSipProfileEntry 29 }

		
		sheVoipSipProfileTcpSocketTimeout OBJECT-TYPE
			SYNTAX Unsigned32 (1..100000)
			UNITS "msec"
			MAX-ACCESS read-only
			STATUS current
			DESCRIPTION
				"The time a socket is kept open, when its not in use
				default:50000ms.value=<1..100000>"
			DEFVAL { 50000 }
			::= { sheVoipSipProfileEntry 30 }

		
		sheVoipSipProfileSend100 OBJECT-TYPE
			SYNTAX Unsigned32
			MAX-ACCESS read-only
			STATUS current
			DESCRIPTION
				"Flag whether stack sends 100 automatically.1:yes,0:no. default:1"
			DEFVAL { 1 }
			::= { sheVoipSipProfileEntry 31 }

		
		sheVoipSipProfileMaxTcpConnections OBJECT-TYPE
			SYNTAX Unsigned32 (1..3000)
			MAX-ACCESS read-only
			STATUS current
			DESCRIPTION
				"The maximum number of TCP connections.value=<1..3000>"
			DEFVAL { 1500 }
			::= { sheVoipSipProfileEntry 32 }

		
		sheVoipSipProfileProxyForwardAll1xx OBJECT-TYPE
			SYNTAX Unsigned32
			MAX-ACCESS read-only
			STATUS current
			DESCRIPTION
				"sheVoipSipProfileProxyForwardAll1xx.1:yes,0:no. default:1"
			DEFVAL { 1 }
			::= { sheVoipSipProfileEntry 33 }

		
		sheVoipSipProfileDefOvlMinor OBJECT-TYPE
			SYNTAX Unsigned32
			UNITS "%"
			MAX-ACCESS read-only
			STATUS current
			DESCRIPTION
				"Percentage value.This object specifies the default threshold for minor overload alarms.
				default:70."
			DEFVAL { 70 }
			::= { sheVoipSipProfileEntry 34 }

		
		sheVoipSipProfileDefOvlMajor OBJECT-TYPE
			SYNTAX Unsigned32
			UNITS "%"
			MAX-ACCESS read-only
			STATUS current
			DESCRIPTION
				"This object specifies the default threshold for major overload alarms.     
				default:80."
			DEFVAL { 80 }
			::= { sheVoipSipProfileEntry 35 }

		
		sheVoipSipProfileDefOvlCritical OBJECT-TYPE
			SYNTAX Unsigned32
			UNITS "%"
			MAX-ACCESS read-only
			STATUS current
			DESCRIPTION
				"This object specifies the default threshold for critical overload alarms.     
				default:90."
			DEFVAL { 90 }
			::= { sheVoipSipProfileEntry 36 }

		
		sheVoipSipProfileDefOvlClear OBJECT-TYPE
			SYNTAX Unsigned32
			UNITS "%"
			MAX-ACCESS read-only
			STATUS current
			DESCRIPTION
				"This object specifies the default threshold for clearance of overload alarms.
				default:60."
			DEFVAL { 60 }
			::= { sheVoipSipProfileEntry 37 }

		
		sheVoipSipProfileDefOvlInvite OBJECT-TYPE
			SYNTAX SheVoipSipProfileOvlFlagType
			MAX-ACCESS read-only
			STATUS current
			DESCRIPTION
				"Flag whether stack uses extended overload invitation or not. 1:yes,0:no.
				default:1"
			DEFVAL { yes }
			::= { sheVoipSipProfileEntry 38 }

		
		sheVoipSipProfileDefOvlRegister OBJECT-TYPE
			SYNTAX SheVoipSipProfileOvlFlagType
			MAX-ACCESS read-only
			STATUS current
			DESCRIPTION
				"Flag whether stack uses extended overload registration or not.1:yes,0:no.
				default:0"
			DEFVAL { no }
			::= { sheVoipSipProfileEntry 39 }

		
		sheVoipSipProfileDefOvlAuth OBJECT-TYPE
			SYNTAX SheVoipSipProfileOvlFlagType
			MAX-ACCESS read-only
			STATUS current
			DESCRIPTION
				"Flag whether stack uses extended overload authentication or not.1:yes,0:no.
				default:1"
			DEFVAL { yes }
			::= { sheVoipSipProfileEntry 40 }

		
		sheVoipSipProfileUseOvlHdl OBJECT-TYPE
			SYNTAX SheVoipSipProfileOvlFlagType
			MAX-ACCESS read-only
			STATUS current
			DESCRIPTION
				"Flag whether stack uses extended overload handling or not.1:yes,0:no.
				default:1"
			DEFVAL { yes }
			::= { sheVoipSipProfileEntry 41 }

		
-- sheVoipSipProfileControl
		sheVoipSipProfileControl OBJECT IDENTIFIER ::= { sheVoipSipDataGroup 4 }

		
		sheVoipSipProfileControlRequest OBJECT-TYPE
			SYNTAX SheVoipControlRequestType
			MAX-ACCESS read-write
			STATUS current
			DESCRIPTION
				"The request of a user command. 
				createSipProfile	  	(130),            
				         	Must:		sheVoipSipProfileControlName 				 
				         	Optional:	
								sheVoipSipProfileControlOrganization
								sheVoipSipProfileControlInitialTimerReq
								sheVoipSipProfileControlInitialTimerInvite
								sheVoipSipProfileControlInitialTimerAck
								sheVoipSipProfileControlInitialTimerBye
								sheVoipSipProfileControlInitialTimerCancel
								sheVoipSipProfileControlInitialTimerRegister
								sheVoipSipProfileControlInitialTimerOptions
								sheVoipSipProfileControlInitialTimerPrack
								sheVoipSipProfileControlInitialTimerRsp
								sheVoipSipProfileControlTimerT2
								sheVoipSipProfileControlTimerT4
								sheVoipSipProfileControlRetryReq
								sheVoipSipProfileControlRetryInvite
								sheVoipSipProfileControlRetryAck
								sheVoipSipProfileControlRetryBye
								sheVoipSipProfileControlRetryCancel
								sheVoipSipProfileControlRetryOptions
								sheVoipSipProfileControlRetryPrack
								sheVoipSipProfileControlRetryRegister
								sheVoipSipProfileControlRetryFinalResponse
								sheVoipSipProfileControlCMTimeout
								sheVoipSipProfileControlTimeout
								sheVoipSipProfileControlCacheTimer
								sheVoipSipProfileControlForward100toCM
								sheVoipSipProfileControlTcpSocketTimeout
								sheVoipSipProfileControlSend100
								sheVoipSipProfileControlMaxTcpConnections
								sheVoipSipProfileControlProxyForwardAll1xx
								sheVoipSipProfileControlDefOvlMinor
								sheVoipSipProfileControlDefOvlMajor
								sheVoipSipProfileControlDefOvlCritical
								sheVoipSipProfileControlDefOvlClear
								sheVoipSipProfileControlDefOvlInvite
								sheVoipSipProfileControlDefOvlRegister
								sheVoipSipProfileControlDefOvlAuth
								sheVoipSipProfileControlUseOvlHdl
				     	 	 
				modifySipProfile		(150), 
				         	Must:	 sheVoipSipProfileControlIndex	 				 
				         	Optional:	
								sheVoipSipProfileControlOrganization
								sheVoipSipProfileControlInitialTimerReq
								sheVoipSipProfileControlInitialTimerInvite
								sheVoipSipProfileControlInitialTimerAck
								sheVoipSipProfileControlInitialTimerBye
								sheVoipSipProfileControlInitialTimerCancel
								sheVoipSipProfileControlInitialTimerRegister
								sheVoipSipProfileControlInitialTimerOptions
								sheVoipSipProfileControlInitialTimerPrack
								sheVoipSipProfileControlInitialTimerRsp
								sheVoipSipProfileControlTimerT2
								sheVoipSipProfileControlTimerT4
								sheVoipSipProfileControlRetryReq
								sheVoipSipProfileControlRetryInvite
								sheVoipSipProfileControlRetryAck
								sheVoipSipProfileControlRetryBye
								sheVoipSipProfileControlRetryCancel
								sheVoipSipProfileControlRetryOptions
								sheVoipSipProfileControlRetryPrack
								sheVoipSipProfileControlRetryRegister
								sheVoipSipProfileControlRetryFinalResponse
								sheVoipSipProfileControlCMTimeout
								sheVoipSipProfileControlTimeout
								sheVoipSipProfileControlCacheTimer
								sheVoipSipProfileControlForward100toCM
								sheVoipSipProfileControlTcpSocketTimeout
								sheVoipSipProfileControlSend100
								sheVoipSipProfileControlMaxTcpConnections
								sheVoipSipProfileControlProxyForwardAll1xx
								sheVoipSipProfileControlDefOvlMinor
								sheVoipSipProfileControlDefOvlMajor
								sheVoipSipProfileControlDefOvlCritical
								sheVoipSipProfileControlDefOvlClear
								sheVoipSipProfileControlDefOvlInvite
								sheVoipSipProfileControlDefOvlRegister
								sheVoipSipProfileControlDefOvlAuth
								sheVoipSipProfileControlUseOvlHdl
					 
				deleteSipProfile  	    (140), 
				        		Must:	 sheVoipSipProfileControlIndex
				"
			::= { sheVoipSipProfileControl 1 }

		
		sheVoipSipProfileControlStatus OBJECT-TYPE
			SYNTAX SheControlStatusType
			MAX-ACCESS read-only
			STATUS current
			DESCRIPTION
				"The status of a user command."
			::= { sheVoipSipProfileControl 2 }

		
		sheVoipSipProfileControlTimer OBJECT-TYPE
			SYNTAX Gauge32
			MAX-ACCESS read-only
			STATUS current
			DESCRIPTION
				"The maximum wait time for the manager for a  
				long running user command."
			::= { sheVoipSipProfileControl 3 }

		
		sheVoipSipProfileControlTimeStamp OBJECT-TYPE
			SYNTAX TimeTicks
			MAX-ACCESS read-only
			STATUS current
			DESCRIPTION
				"The time stamp of the last command (end of command)."
			::= { sheVoipSipProfileControl 4 }

		
		sheVoipSipProfileControlReqResult OBJECT-TYPE
			SYNTAX SheVoipControlRequestResultType
			MAX-ACCESS read-only
			STATUS current
			DESCRIPTION
				"The result of the last user command."
			::= { sheVoipSipProfileControl 5 }

		
		sheVoipSipProfileControlIndex OBJECT-TYPE
			SYNTAX Unsigned32
			MAX-ACCESS read-write
			STATUS current
			DESCRIPTION
				"sip profile index."
			::= { sheVoipSipProfileControl 6 }

		
		sheVoipSipProfileControlName OBJECT-TYPE
			SYNTAX DisplayString
			MAX-ACCESS read-write
			STATUS current
			DESCRIPTION
				"sip profile name."
			::= { sheVoipSipProfileControl 7 }

		
		sheVoipSipProfileControlOrganization OBJECT-TYPE
			SYNTAX OCTET STRING (SIZE (256))
			MAX-ACCESS read-write
			STATUS current
			DESCRIPTION
				"sheVoipSipProfileControlOrganization."
			::= { sheVoipSipProfileControl 8 }

		
		sheVoipSipProfileControlInitialTimerReq OBJECT-TYPE
			SYNTAX Unsigned32 (100..1000)
			UNITS "msec"
			MAX-ACCESS read-write
			STATUS current
			DESCRIPTION
				"This project specific value specifies the initial value 
				for the retransmit timer for a generic SIP-request.value = <100..1000>, 
				the unit is milli-seconds."
			::= { sheVoipSipProfileControl 9 }

		
		sheVoipSipProfileControlInitialTimerInvite OBJECT-TYPE
			SYNTAX Unsigned32 (100..1000)
			UNITS "msec"
			MAX-ACCESS read-write
			STATUS current
			DESCRIPTION
				"This object specifies the initial value for the retransmit
				timer for the INVITE method. The retransmit timer doubles after each retransmission, 
				ensuring an exponential backoff in network traffic.value = <100..1000>, 
				the unit is milli-seconds."
			::= { sheVoipSipProfileControl 10 }

		
		sheVoipSipProfileControlInitialTimerAck OBJECT-TYPE
			SYNTAX Unsigned32 (100..1000)
			UNITS "msec"
			MAX-ACCESS read-write
			STATUS current
			DESCRIPTION
				"This object specifies the initial value for the retransmit timer 
				for the ACK method.value = <100..1000>, the unit is milli-seconds."
			::= { sheVoipSipProfileControl 11 }

		
		sheVoipSipProfileControlInitialTimerBye OBJECT-TYPE
			SYNTAX Unsigned32 (100..1000)
			UNITS "msec"
			MAX-ACCESS read-write
			STATUS current
			DESCRIPTION
				"This object specifies the initial value for the retransmit timer 
				for the BYE method.value = <100..1000>, the unit is milli-seconds."
			::= { sheVoipSipProfileControl 12 }

		
		sheVoipSipProfileControlInitialTimerCancel OBJECT-TYPE
			SYNTAX Unsigned32 (100..1000)
			UNITS "msec"
			MAX-ACCESS read-write
			STATUS current
			DESCRIPTION
				"This object specifies the initial value for the retransmit timer 
				for the CANVEL method.value = <100..1000>, the unit is milli-seconds."
			::= { sheVoipSipProfileControl 13 }

		
		sheVoipSipProfileControlInitialTimerRegister OBJECT-TYPE
			SYNTAX Unsigned32 (100..1000)
			UNITS "msec"
			MAX-ACCESS read-write
			STATUS current
			DESCRIPTION
				"This object specifies the initial value for the retransmit timer 
				for the REGISTER method. value = <100..1000>, the unit is milli-seconds."
			::= { sheVoipSipProfileControl 14 }

		
		sheVoipSipProfileControlInitialTimerOptions OBJECT-TYPE
			SYNTAX Unsigned32 (100..1000)
			UNITS "msec"
			MAX-ACCESS read-write
			STATUS current
			DESCRIPTION
				"This object specifies the initial value for the retransmit timer 
				for the OPTIONS method.value = <100..1000>, the unit is milli-seconds."
			::= { sheVoipSipProfileControl 15 }

		
		sheVoipSipProfileControlInitialTimerPrack OBJECT-TYPE
			SYNTAX Unsigned32 (100..1000)
			UNITS "msec"
			MAX-ACCESS read-write
			STATUS current
			DESCRIPTION
				"This object specifies the initial value for the retransmit timer 
				for the PRACK method.value = <100..1000>, the unit is milli-seconds."
			::= { sheVoipSipProfileControl 16 }

		
		sheVoipSipProfileControlInitialTimerRsp OBJECT-TYPE
			SYNTAX Unsigned32 (100..1000)
			UNITS "msec"
			MAX-ACCESS read-write
			STATUS current
			DESCRIPTION
				"This object specifies the initial value for the retransmit timer 
				for final responses.value = <100..1000>, the unit is milli-seconds."
			::= { sheVoipSipProfileControl 17 }

		
		sheVoipSipProfileControlTimerT2 OBJECT-TYPE
			SYNTAX Unsigned32 (200..10000)
			UNITS "msec"
			MAX-ACCESS read-write
			STATUS current
			DESCRIPTION
				"This object specifies the T2 timer for a SIP entity. 
				value = <200..10000>.REFERENCE Section 10.4 and 10.5 RFC2543, 
				the unit is milli-seconds."
			::= { sheVoipSipProfileControl 18 }

		
		sheVoipSipProfileControlTimerT4 OBJECT-TYPE
			SYNTAX Unsigned32 (200..10000)
			UNITS "msec"
			MAX-ACCESS read-write
			STATUS current
			DESCRIPTION
				"This object specifies the T4 timer for a SIP entity. 
				value = <200..10000>.REFERENCE Section 10.4 and 10.5 RFC2543, 
				the unit is milli-seconds."
			::= { sheVoipSipProfileControl 19 }

		
		sheVoipSipProfileControlRetryReq OBJECT-TYPE
			SYNTAX Unsigned32 (1..10)
			MAX-ACCESS read-write
			STATUS current
			DESCRIPTION
				"This object will specify the number of times a SIP entity 
				will retry sending astandard request.value = <1..10>."
			::= { sheVoipSipProfileControl 20 }

		
		sheVoipSipProfileControlRetryInvite OBJECT-TYPE
			SYNTAX Unsigned32 (1..10)
			MAX-ACCESS read-write
			STATUS current
			DESCRIPTION
				"This object will specify the number of times a SIP entity 
				will retry sending an INVITE request.value = <1..10>."
			::= { sheVoipSipProfileControl 21 }

		
		sheVoipSipProfileControlRetryAck OBJECT-TYPE
			SYNTAX Unsigned32 (1..10)
			MAX-ACCESS read-write
			STATUS current
			DESCRIPTION
				"This object will specify the number of times a SIP entity 
				will retry sending an ACK request.value = <1..10>."
			::= { sheVoipSipProfileControl 22 }

		
		sheVoipSipProfileControlRetryBye OBJECT-TYPE
			SYNTAX Unsigned32 (1..10)
			MAX-ACCESS read-write
			STATUS current
			DESCRIPTION
				"This object will specify the number of times a SIP entity 
				will retry sending an BYE request.value = <1..10>."
			::= { sheVoipSipProfileControl 23 }

		
		sheVoipSipProfileControlRetryCancel OBJECT-TYPE
			SYNTAX Unsigned32 (1..10)
			MAX-ACCESS read-write
			STATUS current
			DESCRIPTION
				"This object will specify the number of times a SIP entity 
				will retry sending an CANCEL request.value = <1..10>."
			::= { sheVoipSipProfileControl 24 }

		
		sheVoipSipProfileControlRetryOptions OBJECT-TYPE
			SYNTAX Unsigned32 (1..10)
			MAX-ACCESS read-write
			STATUS current
			DESCRIPTION
				"This object will specify the number of times a SIP entity 
				will retry sending an OPTIONS request.value = <1..10>."
			::= { sheVoipSipProfileControl 25 }

		
		sheVoipSipProfileControlRetryPrack OBJECT-TYPE
			SYNTAX Unsigned32 (1..10)
			MAX-ACCESS read-write
			STATUS current
			DESCRIPTION
				"This object will specify the number of times a SIP entity 
				will retry sending an PRACK request.value = <1..10>."
			::= { sheVoipSipProfileControl 26 }

		
		sheVoipSipProfileControlRetryRegister OBJECT-TYPE
			SYNTAX Unsigned32 (1..10)
			MAX-ACCESS read-write
			STATUS current
			DESCRIPTION
				"This object will specify the number of times a SIP entity 
				will retry sending an REGISTER request.value = <1..10>."
			::= { sheVoipSipProfileControl 27 }

		
		sheVoipSipProfileControlRetryFinalResponse OBJECT-TYPE
			SYNTAX Unsigned32 (1..10)
			MAX-ACCESS read-write
			STATUS current
			DESCRIPTION
				".This object will specify the number of times a SIP entity 
				will retry sending a final response and expecting an ACK.value = <1..10>."
			::= { sheVoipSipProfileControl 28 }

		
		sheVoipSipProfileControlCMTimeout OBJECT-TYPE
			SYNTAX Unsigned32 (1..64000)
			UNITS "msec"
			MAX-ACCESS read-write
			STATUS current
			DESCRIPTION
				"Timeout to Callmanager."
			::= { sheVoipSipProfileControl 29 }

		
		sheVoipSipProfileControlTimeout OBJECT-TYPE
			SYNTAX Unsigned32 (1..192000)
			UNITS "msec"
			MAX-ACCESS read-write
			STATUS current
			DESCRIPTION
				"Timeout to Callmanager transactionrelated."
			::= { sheVoipSipProfileControl 30 }

		
		sheVoipSipProfileControlCacheTimer OBJECT-TYPE
			SYNTAX Unsigned32 (1..64000)
			UNITS "msec"
			MAX-ACCESS read-write
			STATUS current
			DESCRIPTION
				"The time a closed transaction is cached."
			::= { sheVoipSipProfileControl 31 }

		
		sheVoipSipProfileControlForward100toCM OBJECT-TYPE
			SYNTAX Unsigned32
			MAX-ACCESS read-write
			STATUS current
			DESCRIPTION
				"Flag whether stack sends 100 tryings to the callmanager or not.1:yes,0:no.default:0."
			::= { sheVoipSipProfileControl 32 }

		
		sheVoipSipProfileControlTcpSocketTimeout OBJECT-TYPE
			SYNTAX Unsigned32 (1..100000)
			UNITS "msec"
			MAX-ACCESS read-write
			STATUS current
			DESCRIPTION
				"The time a socket is kept open, when its not in use.default:50s."
			::= { sheVoipSipProfileControl 33 }

		
		sheVoipSipProfileControlSend100 OBJECT-TYPE
			SYNTAX Unsigned32
			MAX-ACCESS read-write
			STATUS current
			DESCRIPTION
				"Flag whether stack sends 100 automatically.1:yes,0:no. default:1."
			::= { sheVoipSipProfileControl 34 }

		
		sheVoipSipProfileControlMaxTcpConnections OBJECT-TYPE
			SYNTAX Unsigned32 (1..3000)
			MAX-ACCESS read-write
			STATUS current
			DESCRIPTION
				"This object indicates the maximum number of simultaneous 
				transactions that the SIP entity can manage. (Registar & Proxy/Redirect)."
			::= { sheVoipSipProfileControl 35 }

		
		sheVoipSipProfileControlProxyForwardAll1xx OBJECT-TYPE
			SYNTAX Unsigned32
			MAX-ACCESS read-write
			STATUS current
			DESCRIPTION
				"sheVoipSipProfileProxyForwardAll1xx.1:yes,0:no. default:1."
			::= { sheVoipSipProfileControl 36 }

		
		sheVoipSipProfileControlDefOvlMinor OBJECT-TYPE
			SYNTAX Unsigned32
			UNITS "%"
			MAX-ACCESS read-write
			STATUS current
			DESCRIPTION
				"Percentage value.This object specifies the default threshold for minor overload alarms.
				default:70."
			::= { sheVoipSipProfileControl 37 }

		
		sheVoipSipProfileControlDefOvlMajor OBJECT-TYPE
			SYNTAX Unsigned32
			UNITS "%"
			MAX-ACCESS read-write
			STATUS current
			DESCRIPTION
				"This object specifies the default threshold for major overload alarms."
			::= { sheVoipSipProfileControl 38 }

		
		sheVoipSipProfileControlDefOvlCritical OBJECT-TYPE
			SYNTAX Unsigned32
			UNITS "%"
			MAX-ACCESS read-write
			STATUS current
			DESCRIPTION
				"This object specifies the default threshold for critical overload alarms."
			::= { sheVoipSipProfileControl 39 }

		
		sheVoipSipProfileControlDefOvlClear OBJECT-TYPE
			SYNTAX Unsigned32
			UNITS "%"
			MAX-ACCESS read-write
			STATUS current
			DESCRIPTION
				"This object specifies the default threshold for clearance of overload alarms."
			::= { sheVoipSipProfileControl 40 }

		
		sheVoipSipProfileControlDefOvlInvite OBJECT-TYPE
			SYNTAX SheVoipSipProfileOvlFlagType
			MAX-ACCESS read-write
			STATUS current
			DESCRIPTION
				"Flag whether stack uses extended overload invitation or not. 1:yes,0:no.
				default:1"
			::= { sheVoipSipProfileControl 41 }

		
		sheVoipSipProfileControlDefOvlRegister OBJECT-TYPE
			SYNTAX SheVoipSipProfileOvlFlagType
			MAX-ACCESS read-write
			STATUS current
			DESCRIPTION
				"Flag whether stack uses extended overload registration or not.1:yes,0:no.
				default:0"
			::= { sheVoipSipProfileControl 42 }

		
		sheVoipSipProfileControlDefOvlAuth OBJECT-TYPE
			SYNTAX SheVoipSipProfileOvlFlagType
			MAX-ACCESS read-write
			STATUS current
			DESCRIPTION
				"Flag whether stack uses extended overload authentication or not.1:yes,0:no.
				default:1"
			::= { sheVoipSipProfileControl 43 }

		
		sheVoipSipProfileControlUseOvlHdl OBJECT-TYPE
			SYNTAX SheVoipSipProfileOvlFlagType
			MAX-ACCESS read-write
			STATUS current
			DESCRIPTION
				"Flag whether stack uses extended overload handling or not.1:yes,0:no.
				default:1"
			::= { sheVoipSipProfileControl 44 }

		
-- sheVoipSipServerConfigProfileTable
		sheVoipSipServerConfigProfileTable OBJECT-TYPE
			SYNTAX SEQUENCE OF SheVoipSipServerConfigProfileEntry
			MAX-ACCESS not-accessible
			STATUS current
			DESCRIPTION
				"this table contains all sip server profile atributes "
			::= { sheVoipSipDataGroup 5 }

		
		sheVoipSipServerConfigProfileEntry OBJECT-TYPE
			SYNTAX SheVoipSipServerConfigProfileEntry
			MAX-ACCESS not-accessible
			STATUS current
			DESCRIPTION
				"An entry in  sheVoipSipServerConfigProfileTable."
			INDEX { sheVoipSipServerConfigProfileIndex }
			::= { sheVoipSipServerConfigProfileTable 1 }

		
		SheVoipSipServerConfigProfileEntry ::=
			SEQUENCE { 
				sheVoipSipServerConfigProfileIndex
					Unsigned32,
				sheVoipSipServerConfigProfileName
					DisplayString,
				sheVoipSipRegServerConfigProfileAddr
					OCTET STRING,
				sheVoipSipServerConfigProfileFunction
					SheVoipSipServerFunctionType,
				sheVoipSipProxyServerConfigProfileIpAddress1
					IpAddress,
				sheVoipSipProxyServerConfigProfileIpAddress2
					IpAddress,
				sheVoipSipProxyServerConfigProfileIpAddress3
					IpAddress,
				sheVoipSipProxyServerConfigProfilePort1
					Unsigned32,
				sheVoipSipProxyServerConfigProfilePort2
					Unsigned32,
				sheVoipSipProxyServerConfigProfilePort3
					Unsigned32,
				sheVoipSipUsingProxyServerID
					Unsigned32,
				sheVoipSipServerConfigProfileSoftswitch
					OCTET STRING,
				sheVoipSipServerConfigProfilePrimarySipDns
					IpAddress,
				sheVoipSipServerConfigProfileSecondarySipDns
					IpAddress
			 }

		sheVoipSipServerConfigProfileIndex OBJECT-TYPE
			SYNTAX Unsigned32
			MAX-ACCESS read-only
			STATUS current
			DESCRIPTION
				"Table index. Each index uniquely identifies one Sip server profile entry."
			::= { sheVoipSipServerConfigProfileEntry 1 }

		
		sheVoipSipServerConfigProfileName OBJECT-TYPE
			SYNTAX DisplayString
			MAX-ACCESS read-only
			STATUS current
			DESCRIPTION
				"Table name. "
			::= { sheVoipSipServerConfigProfileEntry 2 }

		
		sheVoipSipRegServerConfigProfileAddr OBJECT-TYPE
			SYNTAX OCTET STRING (SIZE (64))
			MAX-ACCESS read-only
			STATUS current
			DESCRIPTION
				"This object reflects the address of a SIP server.
				this user agent will use to register."
			::= { sheVoipSipServerConfigProfileEntry 3 }

		
		sheVoipSipServerConfigProfileFunction OBJECT-TYPE
			SYNTAX SheVoipSipServerFunctionType
			MAX-ACCESS read-only
			STATUS current
			DESCRIPTION
				"This object reflects the function of the SIP server.
				this user agent should communicate with: registrar, proxy (outbound proxy), etc."
			::= { sheVoipSipServerConfigProfileEntry 4 }

		
		sheVoipSipProxyServerConfigProfileIpAddress1 OBJECT-TYPE
			SYNTAX IpAddress
			MAX-ACCESS read-only
			STATUS current
			DESCRIPTION
				"proxy server ip address 1. "
			::= { sheVoipSipServerConfigProfileEntry 5 }

		
		sheVoipSipProxyServerConfigProfileIpAddress2 OBJECT-TYPE
			SYNTAX IpAddress
			MAX-ACCESS read-only
			STATUS current
			DESCRIPTION
				"proxy server ip address 2. "
			::= { sheVoipSipServerConfigProfileEntry 6 }

		
		sheVoipSipProxyServerConfigProfileIpAddress3 OBJECT-TYPE
			SYNTAX IpAddress
			MAX-ACCESS read-only
			STATUS current
			DESCRIPTION
				"proxy server ip address 3. "
			::= { sheVoipSipServerConfigProfileEntry 7 }

		
		sheVoipSipProxyServerConfigProfilePort1 OBJECT-TYPE
			SYNTAX Unsigned32
			MAX-ACCESS read-only
			STATUS current
			DESCRIPTION
				"proxy server port number 1. "
			::= { sheVoipSipServerConfigProfileEntry 8 }

		
		sheVoipSipProxyServerConfigProfilePort2 OBJECT-TYPE
			SYNTAX Unsigned32
			MAX-ACCESS read-only
			STATUS current
			DESCRIPTION
				"proxy server port number 2. "
			::= { sheVoipSipServerConfigProfileEntry 9 }

		
		sheVoipSipProxyServerConfigProfilePort3 OBJECT-TYPE
			SYNTAX Unsigned32
			MAX-ACCESS read-only
			STATUS current
			DESCRIPTION
				"proxy server port number 3. "
			::= { sheVoipSipServerConfigProfileEntry 10 }

		
		sheVoipSipUsingProxyServerID OBJECT-TYPE
			SYNTAX Unsigned32 (0..4)
			MAX-ACCESS read-only
			STATUS current
			DESCRIPTION
				"indicate which proxy server is using,default value is 0, value range is <0-4>."
			::= { sheVoipSipServerConfigProfileEntry 11 }

		
		sheVoipSipServerConfigProfileSoftswitch OBJECT-TYPE
			SYNTAX OCTET STRING (SIZE (4))
			MAX-ACCESS read-only
			STATUS current
			DESCRIPTION
				"The SIP Gateway softswitch vendor. 
				The format is four ASCII coded alphabetic characters [A - Z] as defined in ANSI T1.220. 
				All NULL characters indicates no particular vendor."
			::= { sheVoipSipServerConfigProfileEntry 12 }

		
		sheVoipSipServerConfigProfilePrimarySipDns OBJECT-TYPE
			SYNTAX IpAddress
			MAX-ACCESS read-only
			STATUS current
			DESCRIPTION
				"The Primary SIP DNS IP Address. If this value is zero,
				the Primary SIP DNS should not be used.. "
			::= { sheVoipSipServerConfigProfileEntry 13 }

		
		sheVoipSipServerConfigProfileSecondarySipDns OBJECT-TYPE
			SYNTAX IpAddress
			MAX-ACCESS read-only
			STATUS current
			DESCRIPTION
				"The Secondary SIP DNS IP Address. If this value is zero,  
				the Secondary SIP DNS should not be used. "
			::= { sheVoipSipServerConfigProfileEntry 14 }

		
-- sheVoipSipServerConfigProfileControl
		sheVoipSipServerConfigProfileControl OBJECT IDENTIFIER ::= { sheVoipSipDataGroup 6 }

		
		sheVoipSipServerConfigProfileControlRequest OBJECT-TYPE
			SYNTAX SheVoipControlRequestType
			MAX-ACCESS read-write
			STATUS current
			DESCRIPTION
				"The request of a user command. 
				createSipServerConfigProfile	  	(160),            
				         	Must:		sheVoipSipProfileControlName 				 
				         	Optional:	
								sheVoipSipRegServerConfigProfileControlAddr
								sheVoipSipServerConfigProfileControlFunction
								sheVoipSipServerConfigProfileControlName
								sheVoipSipProxyServerConfigProfileControlIpAddress1
								sheVoipSipProxyServerConfigProfileControlIpAddress2
								sheVoipSipProxyServerConfigProfileControlIpAddress3
								sheVoipSipProxyServerConfigProfileControlPort1
								sheVoipSipProxyServerConfigProfileControlPort2
								sheVoipSipProxyServerConfigProfileControlPort3
								sheVoipSipServerConfigProfileControlSoftswitch
								sheVoipSipServerConfigProfileControlPrimarySipDns
								sheVoipSipServerConfigProfileControlSecondarySipDns
				modifySipServerConfigProfile		(180), 
				         	Must:	 sheVoipSipServerConfigProfileControlIndex	 				 
				         	Optional:	
								sheVoipSipRegServerConfigProfileControlAddr
								sheVoipSipServerConfigProfileControlFunction
								sheVoipSipServerConfigProfileControlName
								sheVoipSipProxyServerConfigProfileControlIpAddress1
								sheVoipSipProxyServerConfigProfileControlIpAddress2
								sheVoipSipProxyServerConfigProfileControlIpAddress3
								sheVoipSipProxyServerConfigProfileControlPort1
								sheVoipSipProxyServerConfigProfileControlPort2
								sheVoipSipProxyServerConfigProfileControlPort3
								sheVoipSipServerConfigProfileControlSoftswitch
								sheVoipSipServerConfigProfileControlPrimarySipDns
								sheVoipSipServerConfigProfileControlSecondarySipDns
				 
				  	deleteSipServerConfigProfile   (170), 
				        		Must:	 sheVoipSipServerConfigProfileControlIndex
				"
			::= { sheVoipSipServerConfigProfileControl 1 }

		
		sheVoipSipServerConfigProfileControlStatus OBJECT-TYPE
			SYNTAX SheControlStatusType
			MAX-ACCESS read-only
			STATUS current
			DESCRIPTION
				"The status of a user command."
			::= { sheVoipSipServerConfigProfileControl 2 }

		
		sheVoipSipServerConfigProfileControlTimer OBJECT-TYPE
			SYNTAX Gauge32
			MAX-ACCESS read-only
			STATUS current
			DESCRIPTION
				"The maximum wait time for the manager for a  
				long running user command."
			::= { sheVoipSipServerConfigProfileControl 3 }

		
		sheVoipSipServerConfigProfileControlTimeStamp OBJECT-TYPE
			SYNTAX TimeTicks
			MAX-ACCESS read-only
			STATUS current
			DESCRIPTION
				"The time stamp of the last command (end of command)."
			::= { sheVoipSipServerConfigProfileControl 4 }

		
		sheVoipSipServerConfigProfileControlReqResult OBJECT-TYPE
			SYNTAX SheVoipControlRequestResultType
			MAX-ACCESS read-only
			STATUS current
			DESCRIPTION
				"The result of the last user command."
			::= { sheVoipSipServerConfigProfileControl 5 }

		
		sheVoipSipServerConfigProfileControlIndex OBJECT-TYPE
			SYNTAX Unsigned32
			MAX-ACCESS read-write
			STATUS current
			DESCRIPTION
				"sip server profile index in sheVoipSipServerConfigProfileTable"
			::= { sheVoipSipServerConfigProfileControl 6 }

		
		sheVoipSipServerConfigProfileControlName OBJECT-TYPE
			SYNTAX DisplayString
			MAX-ACCESS read-write
			STATUS current
			DESCRIPTION
				"sip server profile name in sheVoipSipServerConfigProfileTable"
			::= { sheVoipSipServerConfigProfileControl 7 }

		
		sheVoipSipRegServerConfigProfileControlAddr OBJECT-TYPE
			SYNTAX OCTET STRING (SIZE (64))
			MAX-ACCESS read-write
			STATUS current
			DESCRIPTION
				"This object reflects the address of a SIP server.
				this user agent will use to register."
			::= { sheVoipSipServerConfigProfileControl 8 }

		
		sheVoipSipServerConfigProfileControlFunction OBJECT-TYPE
			SYNTAX SheVoipSipServerFunctionType
			MAX-ACCESS read-write
			STATUS current
			DESCRIPTION
				"This object reflects the function of the SIP server.
				this user agent should communicate with: registrar, proxy (outbound proxy), etc."
			::= { sheVoipSipServerConfigProfileControl 9 }

		
		sheVoipSipProxyServerConfigProfileControlIpAddress1 OBJECT-TYPE
			SYNTAX IpAddress
			MAX-ACCESS read-write
			STATUS current
			DESCRIPTION
				"proxy Server Ip address 1 ."
			::= { sheVoipSipServerConfigProfileControl 10 }

		
		sheVoipSipProxyServerConfigProfileControlIpAddress2 OBJECT-TYPE
			SYNTAX IpAddress
			MAX-ACCESS read-write
			STATUS current
			DESCRIPTION
				"proxy Server Ip address 2."
			::= { sheVoipSipServerConfigProfileControl 11 }

		
		sheVoipSipProxyServerConfigProfileControlIpAddress3 OBJECT-TYPE
			SYNTAX IpAddress
			MAX-ACCESS read-write
			STATUS current
			DESCRIPTION
				"proxy Server Ip address 3."
			::= { sheVoipSipServerConfigProfileControl 12 }

		
		sheVoipSipProxyServerConfigProfileControlPort1 OBJECT-TYPE
			SYNTAX Unsigned32
			MAX-ACCESS read-write
			STATUS current
			DESCRIPTION
				"proxy Server port number 1."
			::= { sheVoipSipServerConfigProfileControl 13 }

		
		sheVoipSipProxyServerConfigProfileControlPort2 OBJECT-TYPE
			SYNTAX Unsigned32
			MAX-ACCESS read-write
			STATUS current
			DESCRIPTION
				"proxy Server port number 2."
			::= { sheVoipSipServerConfigProfileControl 14 }

		
		sheVoipSipProxyServerConfigProfileControlPort3 OBJECT-TYPE
			SYNTAX Unsigned32
			MAX-ACCESS read-write
			STATUS current
			DESCRIPTION
				"proxy Server port number 3."
			::= { sheVoipSipServerConfigProfileControl 15 }

		
		sheVoipSipServerConfigProfileControlSoftswitch OBJECT-TYPE
			SYNTAX OCTET STRING (SIZE (4))
			MAX-ACCESS read-write
			STATUS current
			DESCRIPTION
				"The SIP Gateway softswitch vendor. 
				The format is four ASCII coded alphabetic characters [A - Z] as defined in ANSI T1.220. 
				All NULL characters indicates no particular vendor.."
			::= { sheVoipSipServerConfigProfileControl 16 }

		
		sheVoipSipServerConfigProfileControlPrimarySipDns OBJECT-TYPE
			SYNTAX IpAddress
			MAX-ACCESS read-write
			STATUS current
			DESCRIPTION
				"The Primary SIP DNS IP Address. If this value is zero,
				the Primary SIP DNS should not be used.."
			::= { sheVoipSipServerConfigProfileControl 17 }

		
		sheVoipSipServerConfigProfileControlSecondarySipDns OBJECT-TYPE
			SYNTAX IpAddress
			MAX-ACCESS read-write
			STATUS current
			DESCRIPTION
				"The Secondary SIP DNS IP Address. If this value is zero,  
				the Secondary SIP DNS should not be used."
			::= { sheVoipSipServerConfigProfileControl 18 }

		
-- sheVoipSipFeatureAccessCodesTable                       
		sheVoipSipFACProfileTable OBJECT-TYPE
			SYNTAX SEQUENCE OF SheVoipSipFACProfileEntry
			MAX-ACCESS not-accessible
			STATUS current
			DESCRIPTION
				"this table contains all sip Feature Access Codes profile atributes. "
			::= { sheVoipSipDataGroup 7 }

		
		sheVoipSipFACProfileEntry OBJECT-TYPE
			SYNTAX SheVoipSipFACProfileEntry
			MAX-ACCESS not-accessible
			STATUS current
			DESCRIPTION
				"An entry in  sheVoipSipFeatureAccessCodesTable."
			INDEX { sheVoipSipFACProfileIndex }
			::= { sheVoipSipFACProfileTable 1 }

		
		SheVoipSipFACProfileEntry ::=
			SEQUENCE { 
				sheVoipSipFACProfileIndex
					Unsigned32,
				sheVoipSipFACProfileName
					DisplayString,
				sheVoipSipFACProfileCallForwardingUnconditionalActive
					OCTET STRING,
				sheVoipSipFACProfileCallForwardingUnconditionalDeactive
					OCTET STRING,
				sheVoipSipFACProfileCallForwardingOnBusyActive
					OCTET STRING,
				sheVoipSipFACProfileCallForwardingOnBusyDeactive
					OCTET STRING,
				sheVoipSipFACProfileCallForwardingNoAnswerActive
					OCTET STRING,
				sheVoipSipFACProfileCallForwardingNoAnswerDeactive
					OCTET STRING,
				sheVoipSipFACProfileCallingLineIdRestrictionActive
					OCTET STRING,
				sheVoipSipFACProfileCallingLineIdRestrictionDeactive
					OCTET STRING,
				sheVoipSipFACProfileMaliciousIdentificationActive
					OCTET STRING,
				sheVoipSipFACProfileMaliciousIdentificationDeactive
					OCTET STRING,
				sheVoipSipFACProfileCallCompletiontoOnBusySubsActive
					OCTET STRING,
				sheVoipSipFACProfileCallCompletiontoOnBusySubsDeactive
					OCTET STRING,
				sheVoipSipFACProfileCallCompletiontoNoAnswerSubsActive
					OCTET STRING,
				sheVoipSipFACProfileCallCompletiontoNoAnswerSubsDeactive
					OCTET STRING,
				sheVoipSipFACProfileOutgoingCallBarringActive
					OCTET STRING,
				sheVoipSipFACProfileOutgoingCallBarringDeactive
					OCTET STRING,
				sheVoipSipFACProfileSelectiveCallAcceptanceActive
					OCTET STRING,
				sheVoipSipFACProfileSelectiveCallAcceptanceDeactive
					OCTET STRING
			 }

		sheVoipSipFACProfileIndex OBJECT-TYPE
			SYNTAX Unsigned32
			MAX-ACCESS read-only
			STATUS current
			DESCRIPTION
				"Table index. Each index uniquely identifies one Sip FAC  entry."
			::= { sheVoipSipFACProfileEntry 1 }

		
		sheVoipSipFACProfileName OBJECT-TYPE
			SYNTAX DisplayString
			MAX-ACCESS read-only
			STATUS current
			DESCRIPTION
				"Table name. Each index uniquely identifies one Sip FAC  entry."
			::= { sheVoipSipFACProfileEntry 2 }

		
		sheVoipSipFACProfileCallForwardingUnconditionalActive OBJECT-TYPE
			SYNTAX OCTET STRING (SIZE (16))
			MAX-ACCESS read-only
			STATUS current
			DESCRIPTION
				"Unconditional call forwarding active value."
			::= { sheVoipSipFACProfileEntry 3 }

		
		sheVoipSipFACProfileCallForwardingUnconditionalDeactive OBJECT-TYPE
			SYNTAX OCTET STRING (SIZE (16))
			MAX-ACCESS read-only
			STATUS current
			DESCRIPTION
				"Unconditional call forwarding deactive value."
			::= { sheVoipSipFACProfileEntry 4 }

		
		sheVoipSipFACProfileCallForwardingOnBusyActive OBJECT-TYPE
			SYNTAX OCTET STRING (SIZE (16))
			MAX-ACCESS read-only
			STATUS current
			DESCRIPTION
				"On busy call forwarding active value."
			::= { sheVoipSipFACProfileEntry 5 }

		
		sheVoipSipFACProfileCallForwardingOnBusyDeactive OBJECT-TYPE
			SYNTAX OCTET STRING (SIZE (16))
			MAX-ACCESS read-only
			STATUS current
			DESCRIPTION
				"On busy call forwarding deactive value."
			::= { sheVoipSipFACProfileEntry 6 }

		
		sheVoipSipFACProfileCallForwardingNoAnswerActive OBJECT-TYPE
			SYNTAX OCTET STRING (SIZE (16))
			MAX-ACCESS read-only
			STATUS current
			DESCRIPTION
				"No Answer call forwarding active value"
			::= { sheVoipSipFACProfileEntry 7 }

		
		sheVoipSipFACProfileCallForwardingNoAnswerDeactive OBJECT-TYPE
			SYNTAX OCTET STRING (SIZE (16))
			MAX-ACCESS read-only
			STATUS current
			DESCRIPTION
				"No Answer call forwarding deactive value."
			::= { sheVoipSipFACProfileEntry 8 }

		
		sheVoipSipFACProfileCallingLineIdRestrictionActive OBJECT-TYPE
			SYNTAX OCTET STRING (SIZE (16))
			MAX-ACCESS read-only
			STATUS current
			DESCRIPTION
				"Calling line Identification restriction active value."
			::= { sheVoipSipFACProfileEntry 9 }

		
		sheVoipSipFACProfileCallingLineIdRestrictionDeactive OBJECT-TYPE
			SYNTAX OCTET STRING (SIZE (16))
			MAX-ACCESS read-only
			STATUS current
			DESCRIPTION
				"Calling line Identification restriction deactive value."
			::= { sheVoipSipFACProfileEntry 10 }

		
		sheVoipSipFACProfileMaliciousIdentificationActive OBJECT-TYPE
			SYNTAX OCTET STRING (SIZE (16))
			MAX-ACCESS read-only
			STATUS current
			DESCRIPTION
				"Malicious Identification active value."
			::= { sheVoipSipFACProfileEntry 11 }

		
		sheVoipSipFACProfileMaliciousIdentificationDeactive OBJECT-TYPE
			SYNTAX OCTET STRING (SIZE (16))
			MAX-ACCESS read-only
			STATUS current
			DESCRIPTION
				"Malicious Identification deactive value."
			::= { sheVoipSipFACProfileEntry 12 }

		
		sheVoipSipFACProfileCallCompletiontoOnBusySubsActive OBJECT-TYPE
			SYNTAX OCTET STRING (SIZE (16))
			MAX-ACCESS read-only
			STATUS current
			DESCRIPTION
				"Call completionto on busy subscriber active value."
			::= { sheVoipSipFACProfileEntry 13 }

		
		sheVoipSipFACProfileCallCompletiontoOnBusySubsDeactive OBJECT-TYPE
			SYNTAX OCTET STRING (SIZE (16))
			MAX-ACCESS read-only
			STATUS current
			DESCRIPTION
				"Call completion to on busy subscriber deactive value."
			::= { sheVoipSipFACProfileEntry 14 }

		
		sheVoipSipFACProfileCallCompletiontoNoAnswerSubsActive OBJECT-TYPE
			SYNTAX OCTET STRING (SIZE (16))
			MAX-ACCESS read-only
			STATUS current
			DESCRIPTION
				"Call completion to no answer subscriber active value."
			::= { sheVoipSipFACProfileEntry 15 }

		
		sheVoipSipFACProfileCallCompletiontoNoAnswerSubsDeactive OBJECT-TYPE
			SYNTAX OCTET STRING (SIZE (16))
			MAX-ACCESS read-only
			STATUS current
			DESCRIPTION
				"Call completion to no answer subscriber deactive value."
			::= { sheVoipSipFACProfileEntry 16 }

		
		sheVoipSipFACProfileOutgoingCallBarringActive OBJECT-TYPE
			SYNTAX OCTET STRING (SIZE (16))
			MAX-ACCESS read-only
			STATUS current
			DESCRIPTION
				"Outgoing call barring active value."
			::= { sheVoipSipFACProfileEntry 17 }

		
		sheVoipSipFACProfileOutgoingCallBarringDeactive OBJECT-TYPE
			SYNTAX OCTET STRING (SIZE (16))
			MAX-ACCESS read-only
			STATUS current
			DESCRIPTION
				"Outgoing call barring deactive value."
			::= { sheVoipSipFACProfileEntry 18 }

		
		sheVoipSipFACProfileSelectiveCallAcceptanceActive OBJECT-TYPE
			SYNTAX OCTET STRING (SIZE (16))
			MAX-ACCESS read-only
			STATUS current
			DESCRIPTION
				"Selective call acceptance active value."
			::= { sheVoipSipFACProfileEntry 19 }

		
		sheVoipSipFACProfileSelectiveCallAcceptanceDeactive OBJECT-TYPE
			SYNTAX OCTET STRING (SIZE (16))
			MAX-ACCESS read-only
			STATUS current
			DESCRIPTION
				"Selective call acceptance deactive value."
			::= { sheVoipSipFACProfileEntry 20 }

		
-- sheVoipSipFeatureAccessCodesControl
		sheVoipSipFACProfileControl OBJECT IDENTIFIER ::= { sheVoipSipDataGroup 8 }

		
		sheVoipSipFACProfileControlRequest OBJECT-TYPE
			SYNTAX SheVoipControlRequestType
			MAX-ACCESS read-write
			STATUS current
			DESCRIPTION
				"The request of a user command.  
				createSipFACProfile	  	(190),            
				         	Must:		sheVoipSipFACProfileControlname 				 
				         	Optional:	
								sheVoipSipFACProfileControlCallForwardingUnconditionalActive			
								sheVoipSipFACProfileControlCallForwardingUnconditionalDeactive			
								sheVoipSipFACProfileControlCallForwardingOnBusyActive			
								sheVoipSipFACProfileControlCallForwardingOnBusyDeactive				
								sheVoipSipFACProfileControlCallForwardingNoAnswerActive				
								sheVoipSipFACProfileControlCallForwardingNoAnswerDeactive		
								sheVoipSipFACProfileControlCallingLineIdRestrictionActive 			
								sheVoipSipFACProfileControlCallingLineIdRestrictionDeactive			
								sheVoipSipFACProfileControlMaliciousIdentificationActive				
								sheVoipSipFACProfileControlMaliciousIdentificationDeactive				
								sheVoipSipFACProfileControlCallCompletiontoOnBusySubscriberActive			
								sheVoipSipFACProfileControlCallCompletiontoOnBusySubscriberDeactive			
								sheVoipSipFACProfileControlCallCompletiontoNoAnswerSubscriberActive			
								sheVoipSipFACProfileControlCallCompletiontoNoAnswerSubscriberDeactive				
								sheVoipSipFACProfileControlOutgoingCallBarringActive
								sheVoipSipFACProfileControlOutgoingCallBarringDeactive
								sheVoipSipFACProfileControlSelectiveCallAcceptanceActive			
								sheVoipSipFACProfileControlSelectiveCallAcceptanceDeactive			
					modifySipFACProfile   (210), 
				         	Must:	 sheVoipSipFACProfileControlIndex	 				 
				         	Optional:	
								sheVoipSipFACProfileControlCallForwardingUnconditionalActive			
								sheVoipSipFACProfileControlCallForwardingUnconditionalDeactive			
								sheVoipSipFACProfileControlCallForwardingOnBusyActive			
								sheVoipSipFACProfileControlCallForwardingOnBusyDeactive				
								sheVoipSipFACProfileControlCallForwardingNoAnswerActive				
								sheVoipSipFACProfileControlCallForwardingNoAnswerDeactive		
								sheVoipSipFACProfileControlCallingLineIdRestrictionActive 			
								sheVoipSipFACProfileControlCallingLineIdRestrictionDeactive			
								sheVoipSipFACProfileControlMaliciousIdentificationActive				
								sheVoipSipFACProfileControlMaliciousIdentificationDeactive				
								sheVoipSipFACProfileControlCallCompletiontoOnBusySubscriberActive			
								sheVoipSipFACProfileControlCallCompletiontoOnBusySubscriberDeactive			
								sheVoipSipFACProfileControlCallCompletiontoNoAnswerSubscriberActive			
								sheVoipSipFACProfileControlCallCompletiontoNoAnswerSubscriberDeactive				
								sheVoipSipFACProfileControlOutgoingCallBarringActive
								sheVoipSipFACProfileControlOutgoingCallBarringDeactive
								sheVoipSipFACProfileControlSelectiveCallAcceptanceActive			
								sheVoipSipFACProfileControlSelectiveCallAcceptanceDeactive			
				 
				    deleteSipFACProfile		(200),
				        		Must:	 sheVoipSipFACProfileControlIndex
				"
			::= { sheVoipSipFACProfileControl 1 }

		
		sheVoipSipFACProfileControlStatus OBJECT-TYPE
			SYNTAX SheControlStatusType
			MAX-ACCESS read-only
			STATUS current
			DESCRIPTION
				"The status of a user command."
			::= { sheVoipSipFACProfileControl 2 }

		
		sheVoipSipFACProfileControlTimer OBJECT-TYPE
			SYNTAX Gauge32
			MAX-ACCESS read-only
			STATUS current
			DESCRIPTION
				"The maximum wait time for the manager for a  
				long running user command."
			::= { sheVoipSipFACProfileControl 3 }

		
		sheVoipSipFACProfileControlTimeStamp OBJECT-TYPE
			SYNTAX TimeTicks
			MAX-ACCESS read-only
			STATUS current
			DESCRIPTION
				"The time stamp of the last command (end of command)."
			::= { sheVoipSipFACProfileControl 4 }

		
		sheVoipSipFACProfileControlReqResult OBJECT-TYPE
			SYNTAX SheVoipControlRequestResultType
			MAX-ACCESS read-only
			STATUS current
			DESCRIPTION
				"The result of the last user command."
			::= { sheVoipSipFACProfileControl 5 }

		
		sheVoipSipFACProfileControlIndex OBJECT-TYPE
			SYNTAX Unsigned32
			MAX-ACCESS read-write
			STATUS current
			DESCRIPTION
				"sip Feature Access Codes Profile Index."
			::= { sheVoipSipFACProfileControl 6 }

		
		sheVoipSipFACProfileControlName OBJECT-TYPE
			SYNTAX DisplayString
			MAX-ACCESS read-write
			STATUS current
			DESCRIPTION
				"Table name. Each index uniquely identifies one Sip FAC  entry."
			::= { sheVoipSipFACProfileControl 7 }

		
		sheVoipSipFACProfileControlCallForwardingUnconditionalActive OBJECT-TYPE
			SYNTAX OCTET STRING (SIZE (16))
			MAX-ACCESS read-write
			STATUS current
			DESCRIPTION
				"Unconditional call forwarding active value."
			::= { sheVoipSipFACProfileControl 8 }

		
		sheVoipSipFACProfileControlCallForwardingUnconditionalDeactive OBJECT-TYPE
			SYNTAX OCTET STRING (SIZE (16))
			MAX-ACCESS read-write
			STATUS current
			DESCRIPTION
				"Unconditional call forwarding deactive value."
			::= { sheVoipSipFACProfileControl 9 }

		
		sheVoipSipFACProfileControlCallForwardingOnBusyActive OBJECT-TYPE
			SYNTAX OCTET STRING (SIZE (16))
			MAX-ACCESS read-write
			STATUS current
			DESCRIPTION
				"On busy call forwarding active value."
			::= { sheVoipSipFACProfileControl 10 }

		
		sheVoipSipFACProfileControlCallForwardingOnBusyDeactive OBJECT-TYPE
			SYNTAX OCTET STRING (SIZE (16))
			MAX-ACCESS read-write
			STATUS current
			DESCRIPTION
				"On busy call forwarding deactive value."
			::= { sheVoipSipFACProfileControl 11 }

		
		sheVoipSipFACProfileControlCallForwardingNoAnswerActive OBJECT-TYPE
			SYNTAX OCTET STRING (SIZE (16))
			MAX-ACCESS read-write
			STATUS current
			DESCRIPTION
				"No Answer call forwarding active value"
			::= { sheVoipSipFACProfileControl 12 }

		
		sheVoipSipFACProfileControlCallForwardingNoAnswerDeactive OBJECT-TYPE
			SYNTAX OCTET STRING (SIZE (16))
			MAX-ACCESS read-write
			STATUS current
			DESCRIPTION
				"No Answer call forwarding deactive value."
			::= { sheVoipSipFACProfileControl 13 }

		
		sheVoipSipFACProfileControlCallingLineIdRestrictionActive OBJECT-TYPE
			SYNTAX OCTET STRING (SIZE (16))
			MAX-ACCESS read-write
			STATUS current
			DESCRIPTION
				"Calling line Identification restriction active value."
			::= { sheVoipSipFACProfileControl 14 }

		
		sheVoipSipFACProfileControlCallingLineIdRestrictionDeactive OBJECT-TYPE
			SYNTAX OCTET STRING (SIZE (16))
			MAX-ACCESS read-write
			STATUS current
			DESCRIPTION
				"Calling line Identification restriction deactive value."
			::= { sheVoipSipFACProfileControl 15 }

		
		sheVoipSipFACProfileControlMaliciousIdentificationActive OBJECT-TYPE
			SYNTAX OCTET STRING (SIZE (16))
			MAX-ACCESS read-write
			STATUS current
			DESCRIPTION
				"Malicious Identification active value."
			::= { sheVoipSipFACProfileControl 16 }

		
		sheVoipSipFACProfileControlMaliciousIdentificationDeactive OBJECT-TYPE
			SYNTAX OCTET STRING (SIZE (16))
			MAX-ACCESS read-write
			STATUS current
			DESCRIPTION
				"Malicious Identification deactive value."
			::= { sheVoipSipFACProfileControl 17 }

		
		sheVoipSipFACProfileControlCallCompletiontoOnBusySubsActive OBJECT-TYPE
			SYNTAX OCTET STRING (SIZE (16))
			MAX-ACCESS read-write
			STATUS current
			DESCRIPTION
				"Call completionto on busy subscriber active value."
			::= { sheVoipSipFACProfileControl 18 }

		
		sheVoipSipFACProfileControlCallCompletiontoOnBusySubsDeactive OBJECT-TYPE
			SYNTAX OCTET STRING (SIZE (16))
			MAX-ACCESS read-write
			STATUS current
			DESCRIPTION
				"Call completion to on busy subscriber deactive value."
			::= { sheVoipSipFACProfileControl 19 }

		
		sheVoipSipFACProfileControlCallCompletiontoNoAnswerSubsActive OBJECT-TYPE
			SYNTAX OCTET STRING (SIZE (16))
			MAX-ACCESS read-write
			STATUS current
			DESCRIPTION
				"Call completion to no answer subscriber active value."
			::= { sheVoipSipFACProfileControl 20 }

		
		sheVoipSipFACProfileControlCallCompletiontoNoAnswerSubsDeactive OBJECT-TYPE
			SYNTAX OCTET STRING (SIZE (16))
			MAX-ACCESS read-write
			STATUS current
			DESCRIPTION
				"Call completion to no answer subscriber deactive value."
			::= { sheVoipSipFACProfileControl 21 }

		
		sheVoipSipFACProfileControlOutgoingCallBarringActive OBJECT-TYPE
			SYNTAX OCTET STRING (SIZE (16))
			MAX-ACCESS read-write
			STATUS current
			DESCRIPTION
				"Outgoing call barring active value."
			::= { sheVoipSipFACProfileControl 22 }

		
		sheVoipSipFACProfileControlOutgoingCallBarringDeactive OBJECT-TYPE
			SYNTAX OCTET STRING (SIZE (16))
			MAX-ACCESS read-write
			STATUS current
			DESCRIPTION
				"Outgoing call barring deactive value."
			::= { sheVoipSipFACProfileControl 23 }

		
		sheVoipSipFACProfileControlSelectiveCallAcceptanceActive OBJECT-TYPE
			SYNTAX OCTET STRING (SIZE (16))
			MAX-ACCESS read-write
			STATUS current
			DESCRIPTION
				"Selective call acceptance active value."
			::= { sheVoipSipFACProfileControl 24 }

		
		sheVoipSipFACProfileControlSelectiveCallAcceptanceDeactive OBJECT-TYPE
			SYNTAX OCTET STRING (SIZE (16))
			MAX-ACCESS read-write
			STATUS current
			DESCRIPTION
				"Selective call acceptance deactive value."
			::= { sheVoipSipFACProfileControl 25 }

		
		sheVoipConformance OBJECT IDENTIFIER ::= { sheVoipMibModule 100 }

		
		sheVoipGroups OBJECT IDENTIFIER ::= { sheVoipConformance 1 }

		
		sheVoipGroup OBJECT-GROUP
			OBJECTS { sheVoipVgwIndex, sheVoipVgwName, sheVoipVgwAdminStatus, sheVoipVgwOperStatus, sheVoipVgwMemberList, 
				sheVoipVgwDmList, sheVoipVgwIpAddr, sheVoipVgwPortNumber, sheVoipVgwSignalingProtocol, sheVoipVgwMgConfigProfileIndex, 
				sheVoipVgwMgcConfigProfileIndex, sheVoipVgwAlarmSeverityIndex, sheVoipVgwPrioProfileIndex, sheVoipCallPriorityProfileIndex, sheVoipCallPriorityProfileName, 
				sheVoipCallPriorityProfileLevel1, sheVoipCallPriorityProfileLevel2, sheVoipCallPriorityProfileLevel3, sheVoipMgcConfigProfileIndex, sheVoipMgcConfigProfileName, 
				sheVoipMgcConfigProfileIPAddress1, sheVoipMgcConfigProfileIPAddress2, sheVoipMgcConfigProfileIPAddress3, sheVoipMgcConfigProfileIPAddress4, sheVoipMgcConfigProfileIPAddress5, 
				sheVoipMgcConfigProfilePort1, sheVoipMgcConfigProfilePort2, sheVoipMgcConfigProfilePort3, sheVoipMgcConfigProfilePort4, sheVoipMgcConfigProfilePort5, 
				sheVoipH248MgConfigProfileIndex, sheVoipH248MgConfigProfileName, sheVoipH248MgConfigProfileEncodingScheme, sheVoipH248MgConfigProfileProtocolVersion, sheVoipH248MgConfigProfileUseTimestamp, 
				sheVoipH248MgConfigProfileNamingPhyTerm, sheVoipH248MgConfigProfileNamingRtpTerm, sheVoipH248MgConfigProfilePkgList, sheVoipH248MgConfigProfileHeartBeatTime, sheVoipH248MgConfigProfileRetransTime, 
				sheVoipH248MgConfigProfileMaxRetransCount, sheVoipH248MgConfigProfileStartupType, sheVoipH248MgConfigProfileMWD, sheVoipH248MgConfigProfileTermQuitMode, sheVoipH248MgConfigProfileTcpUdpCfgProtocol, 
				sheVoipH248MgConfigProfileMarkTos, sheVoipMediaCodecProfileIndex, sheVoipMediaCodecProfileName, sheVoipMediaCodecProfileG726PayloadType, sheVoipMediaCodecProfileG723Bitrate, 
				sheVoipMediaCodecProfileG726Bitrate, sheVoipMediaCodecProfileCodecPTimeG711, sheVoipMediaCodecProfileCodecPTimeG723, sheVoipMediaCodecProfileCodecPTimeG726, sheVoipMediaCodecProfileCodecPTimeG729, 
				sheVoipMediaCodecProfileEC, sheVoipMediaCodecProfileVad, sheVoipMediaCodecProfilePLC, sheVoipMediaCodecProfileCng, sheVoipMediaCodecProfileAutoSwitchCodec, 
				sheVoipMediaCodecProfileG711passThruCodec, sheVoipMediaCodecProfileG711passThruPayloadType, sheVoipMediaJitterBufProfileIndex, sheVoipMediaJitterBufProfileName, sheVoipMediaJitterBufProfileJitterMode, 
				sheVoipMediaJitterBufProfileJitterMin, sheVoipMediaJitterBufProfileJitterMax, sheVoipMediaJitterBufProfileJitterInit, sheVoipMediaJitterBufProfileJitterUpdatePeriod, sheVoipMediaJitterBufProfileJitterDelThreshold, 
				sheVoipMediaFaxProfileIndex, sheVoipMediaFaxProfileName, sheVoipMediaFaxProfileModemDetect, sheVoipMediaFaxProfileFaxTypeUsed, sheVoipMediaFaxProfileFaxMaxBaudrate, 
				sheVoipMediaFaxProfileT38FaxEcm, sheVoipMediaFaxProfileT38FaxTcfmode, sheVoipMediaFaxProfileT38FaxNumFec, sheVoipMediaFaxProfileT38FaxNumIfp, sheVoipMediaFaxProfileT38FaxBytemode, 
				sheVoipRtcpProfileIndex, sheVoipRtcpProfileName, sheVoipRtcpProfileT38FaxRedPktCount, sheVoipRtcpProfileT30FaxRedPktCount, sheVoipRtcpProfileDtmfRfc2833PktType, 
				sheVoipRtcpProfileDtmfRfc2833RedPktType, sheVoipRtcpProfileRTPRedPktCount, sheVoipRtcpProfileRtcpGen, sheVoipRtcpProfileRtcpInterval, sheVoipVoipVoiceCtpVgwIndex, 
				sheVoipVoipVoiceCtpIpHostProfileIndex, sheVoipVoipVoiceCtpCodecProfileIndex, sheVoipVoipVoiceCtpJitterBufProfileIndex, sheVoipVoipVoiceCtpFaxProfileIndex, sheVoipVoipVoiceCtpRtcpProfileIndex, 
				sheVoipVoipVoiceCtpRtpUdpPortBase, sheVoipIpHostProfileIndex, sheVoipIpHostProfileName, sheVoipIpHostProfileUseDhcp, sheVoipIpHostProfileIpAddress, 
				sheVoipIpHostProfileSubnetMask, sheVoipIpHostProfileDefaultGateway, sheVoipDigitMapProfileIndex, sheVoipDigitMapProfileName, sheVoipDigitMapProfileDigitMap, 
				sheVoipDigitMapProfileLongTime, sheVoipDigitMapProfileShortTime, sheVoipDigitMapProfileStartTime, sheVoipDigitMapProfileZTime, sheVoipMgcConfigProfileSoftswitch1, 
				sheVoipMgcConfigProfileSoftswitch2, sheVoipMgcConfigProfileSoftswitch3, sheVoipMgcConfigProfileSoftswitch4, sheVoipMgcConfigProfileSoftswitch5, sheVoipMediaCodecProfileCodecCapability, 
				sheVoipMediaJitterBufProfileJitterFaxModem, sheVoipRtcpProfileDtmf, sheVoipRtcpProfileFecPayLoadType, sheVoipVoipVoiceCtpRtpStreamTos, sheVoipCallCtrlPmAverageCallDuration, 
				sheVoipCallCtrlPmAtpOccuNum, sheVoipCallCtrlPmOccuNum, sheVoipRtpMonPmInOctetsNum, sheVoipRtpMonPmOutOctetsNum, sheVoipRtpMonPmInPacketsNum, 
				sheVoipRtpMonPmOutPacketsNum, sheVoipRtpMonPmPacketLoss, sheVoipRtpMonPmAverageDelay, sheVoipRtpMonPmJitter, sheVoipVgwPmMonNumInMessages, 
				sheVoipVgwPmMonNumOutMessages, sheVoipVgwPmMonNumInRtpOctets, sheVoipVgwPmMonNumOutRtpOctets, sheVoipVgwPmMonAllBusyTime }
			STATUS current
			DESCRIPTION 
				"A collection of objects providing information about
				a VDSL Line."
			::= { sheVoipGroups 1 }

		
		sheVoipControlGroup OBJECT-GROUP
			OBJECTS { sheVoipVgwControlRequest, sheVoipVgwControlIndex, sheVoipVgwControlName, sheVoipVgwControlAdminStatus, sheVoipVgwControlMemberList, 
				sheVoipVgwControlDmList, sheVoipVgwControlIpAddr, sheVoipVgwControlPortNumber, sheVoipVgwControlSignalingProtocol, sheVoipVgwControlMgConfigProfileIndex, 
				sheVoipVgwControlMgcConfigProfileIndex, sheVoipVgwControlAlarmSeverityIndex, sheVoipVgwControlPrioProfileIndex, sheVoipVgwControlStatus, sheVoipVgwControlTimer, 
				sheVoipVgwControlTimeStamp, sheVoipVgwControlReqResult, sheVoipMgcConfigProfileControlRequest, sheVoipMgcConfigProfileControlIndex, sheVoipMgcConfigProfileControlName, 
				sheVoipMgcConfigProfileControlIPAddress1, sheVoipMgcConfigProfileControlIPAddress2, sheVoipMgcConfigProfileControlIPAddress3, sheVoipMgcConfigProfileControlIPAddress4, sheVoipMgcConfigProfileControlIPAddress5, 
				sheVoipMgcConfigProfileControlPort1, sheVoipMgcConfigProfileControlPort2, sheVoipMgcConfigProfileControlPort3, sheVoipMgcConfigProfileControlPort4, sheVoipMgcConfigProfileControlPort5, 
				sheVoipMgcConfigProfileControlStatus, sheVoipMgcConfigProfileControlTimer, sheVoipMgcConfigProfileControlTimeStamp, sheVoipMgcConfigProfileControlReqResult, sheVoipH248MgConfigProfileControlRequest, 
				sheVoipH248MgConfigProfileControlIndex, sheVoipH248MgConfigProfileControlName, sheVoipH248MgConfigProfileControlEncodingScheme, sheVoipH248MgConfigProfileControlProtocolVersion, sheVoipH248MgConfigProfileControlUseTimestamp, 
				sheVoipH248MgConfigProfileControlNamingPhyTerm, sheVoipH248MgConfigProfileControlNamingRtpTerm, sheVoipH248MgConfigProfileControlPkgList, sheVoipH248MgConfigProfileControlHeartBeatTime, sheVoipH248MgConfigProfileControlRetransTime, 
				sheVoipH248MgConfigProfileControlMaxRetransCount, sheVoipH248MgConfigProfileControlStartupType, sheVoipH248MgConfigProfileControlMWD, sheVoipH248MgConfigProfileControlTermQuitMode, sheVoipH248MgConfigProfileControlTcpUdpCfgProtocol, 
				sheVoipH248MgConfigProfileControlMarkTos, sheVoipH248MgConfigProfileControlStatus, sheVoipH248MgConfigProfileControlTimer, sheVoipH248MgConfigProfileControlTimeStamp, sheVoipH248MgConfigProfileControlReqResult, 
				sheVoipMediaCodecProfileControlRequest, sheVoipMediaCodecProfileControlIndex, sheVoipMediaCodecProfileControlName, sheVoipMediaCodecProfileControlG726PayloadType, sheVoipMediaCodecProfileControlG723Bitrate, 
				sheVoipMediaCodecProfileControlG726Bitrate, sheVoipMediaCodecProfileControlCodecPTimeG711, sheVoipMediaCodecProfileControlCodecPTimeG723, sheVoipMediaCodecProfileControlCodecPTimeG726, sheVoipMediaCodecProfileControlCodecPTimeG729, 
				sheVoipMediaCodecProfileControlEC, sheVoipMediaCodecProfileControlVad, sheVoipMediaCodecProfileControlPLC, sheVoipMediaCodecProfileControlCng, sheVoipMediaCodecProfileControlAutoSwitchCodec, 
				sheVoipMediaCodecProfileControlG711passThruCodec, sheVoipMediaCodecProfileControlG711passThruPayloadType, sheVoipMediaCodecProfileControlStatus, sheVoipMediaCodecProfileControlTimer, sheVoipMediaCodecProfileControlTimeStamp, 
				sheVoipMediaCodecProfileControlReqResult, sheVoipMediaFaxProfileControlRequest, sheVoipMediaFaxProfileControlIndex, sheVoipMediaFaxProfileControlName, sheVoipMediaFaxProfileControlModemDetect, 
				sheVoipMediaFaxProfileControlFaxTypeUsed, sheVoipMediaFaxProfileControlFaxMaxBaudrate, sheVoipMediaFaxProfileControlT38FaxEcm, sheVoipMediaFaxProfileControlT38FaxTcfmode, sheVoipMediaFaxProfileControlT38FaxNumFec, 
				sheVoipMediaFaxProfileControlT38FaxNumIfp, sheVoipMediaFaxProfileControlT38FaxBytemode, sheVoipMediaFaxProfileControlStatus, sheVoipMediaFaxProfileControlTimer, sheVoipMediaFaxProfileControlTimeStamp, 
				sheVoipMediaFaxProfileControlReqResult, sheVoipRtcpProfileControlRequest, sheVoipRtcpProfileControlIndex, sheVoipRtcpProfileControlName, sheVoipRtcpProfileControlT38FaxRedPktCount, 
				sheVoipRtcpProfileControlT30FaxRedPktCount, sheVoipRtcpProfileControlDtmfRfc2833PktType, sheVoipRtcpProfileControlDtmfRfc2833RedPktType, sheVoipRtcpProfileControlRTPRedPktCount, sheVoipRtcpProfileControlRtcpGen, 
				sheVoipRtcpProfileControlRtcpInterval, sheVoipRtcpProfileControlStatus, sheVoipRtcpProfileControlTimer, sheVoipRtcpProfileControlReqResult, sheVoipRtcpProfileControlTimeStamp, 
				sheVoipVoipVoiceCtpControlRequest, sheVoipVoipVoiceCtpControlIfIndexBitMask, sheVoipVoipVoiceCtpControlIpHostProfileIndex, sheVoipVoipVoiceCtpControlCodecProfileIndex, sheVoipVoipVoiceCtpControlJitterBufProfileIndex, 
				sheVoipVoipVoiceCtpControlFaxProfileIndex, sheVoipVoipVoiceCtpControlRtcpProfileIndex, sheVoipVoipVoiceCtpControlRtpUdpPortBase, sheVoipVoipVoiceCtpControlStatus, sheVoipVoipVoiceCtpControlTimer, 
				sheVoipVoipVoiceCtpControlReqResult, sheVoipVoipVoiceCtpControlTimeStamp, sheVoipIpHostProfileControlRequest, sheVoipIpHostProfileControlIndex, sheVoipIpHostProfileControlName, 
				sheVoipIpHostProfileControlUseDhcp, sheVoipIpHostProfileControlIpAddress, sheVoipIpHostProfileControlSubnetMask, sheVoipIpHostProfileControlDefaultGateway, sheVoipIpHostProfileControlStatus, 
				sheVoipIpHostProfileControlTimer, sheVoipIpHostProfileControlReqResult, sheVoipIpHostProfileControlTimeStamp, sheVoipDigitMapProfileControlRequest, sheVoipDigitMapProfileControlIndex, 
				sheVoipDigitMapProfileControlName, sheVoipDigitMapProfileControlDigitMap, sheVoipDigitMapProfileControlLongTime, sheVoipDigitMapProfileControlShortTime, sheVoipDigitMapProfileControlStartTime, 
				sheVoipDigitMapProfileControlZTime, sheVoipDigitMapProfileControlStatus, sheVoipDigitMapProfileControlTimer, sheVoipDigitMapProfileControlReqResult, sheVoipVgwMonPmControlRequest, 
				sheVoipVgwMonPmControlMonitorStartTime, sheVoipVgwMonPmControlMonitorStopTime, sheVoipVgwMonPmControlStatus, sheVoipVgwMonPmControlTimer, sheVoipVgwMonPmControlTimeStamp, 
				sheVoipVgwMonPmControlReqResult, sheVoipRtpMonPmControlRequest, sheVoipRtpMonPmControlMonitorStartTime, sheVoipRtpMonPmControlMonitorStopTime, sheVoipRtpMonPmControlStatus, 
				sheVoipRtpMonPmControlTimer, sheVoipRtpMonPmControlTimeStamp, sheVoipRtpMonPmControlReqResult, sheVoipVgwPmMonitorStartTime, sheVoipVgwPmMonitorStopTime, 
				sheVoipCallCtrlPmControlRequest, sheVoipCallCtrlPmControlMonitorStartTime, sheVoipCallCtrlPmControlMonitorStopTime, sheVoipCallCtrlPmControlStatus, sheVoipCallCtrlPmControlTimer, 
				sheVoipCallCtrlPmControlTimeStamp, sheVoipCallCtrlPmControlReqResult, sheVoipRtpMonPmMonitorStartTime, sheVoipRtpMonPmMonitorStopTime, sheVoipCallCtrlPmMonitorStartTime, 
				sheVoipCallCtrlPmMonitorStopTime, sheVoipVoipVoiceCtpControlRtpStreamTos, sheVoipRtcpProfileControlDtmf, sheVoipRtcpProfileControlFecPayLoadType, sheVoipMediaJitterBufProfileControlJitterFaxModem, 
				sheVoipMediaCodecProfileControlCodecCapability, sheVoipMgcConfigProfileControlSoftswitch1, sheVoipMgcConfigProfileControlSoftswitch2, sheVoipMgcConfigProfileControlSoftswitch3, sheVoipMgcConfigProfileControlSoftswitch4, 
				sheVoipMgcConfigProfileControlSoftswitch5, sheVoipDigitMapProfileControlTimeStamp, sheVoipCallPriorityProfileControlRequest, sheVoipCallPriorityProfileControlIndex, sheVoipCallPriorityProfileControlName, 
				sheVoipCallPriorityProfileControlLevel1, sheVoipCallPriorityProfileControlLevel2, sheVoipCallPriorityProfileControlLevel3, sheVoipCallPriorityProfileControlStatus, sheVoipCallPriorityProfileControlTimer, 
				sheVoipCallPriorityProfileControlTimeStamp, sheVoipCallPriorityProfileControlReqResult, sheVoipMediaJitterBufProfileControlRequest, sheVoipMediaJitterBufProfileControlIndex, sheVoipMediaJitterBufProfileControlName, 
				sheVoipMediaJitterBufProfileControlJitterMode, sheVoipMediaJitterBufProfileControlJitterMin, sheVoipMediaJitterBufProfileControlJitterMax, sheVoipMediaJitterBufProfileControlJitterInit, sheVoipMediaJitterBufProfileControlJitterUpdatePeriod, 
				sheVoipMediaJitterBufProfileControlJitterDelThreshold, sheVoipMediaJitterBufProfileControlStatus, sheVoipMediaJitterBufProfileControlTimer, sheVoipMediaJitterBufProfileControlTimeStamp, sheVoipMediaJitterBufProfileControlReqResult
				 }
			STATUS current
			DESCRIPTION 
				"Description."
			::= { sheVoipGroups 2 }

		
		sheVoipNotificationGroup NOTIFICATION-GROUP
			NOTIFICATIONS { sheVoipVgwCreatedTrap, sheVoipVgwDeletedTrap, sheVoipVgwConfigModifiedTrap, sheVoipCallPriorityProfileCreatedTrap, sheVoipCallPriorityProfileDeletedTrap, 
				sheVoipCallPriorityProfileModifiedTrap, sheVoipMgcConfigProfileCreatedTrap, sheVoipMgcConfigProfileDeletedTrap, sheVoipMgcConfigProfileModifiedTrap, sheVoipH248MgConfigProfileCreatedTrap, 
				sheVoipH248MgConfigProfileDeletedTrap, sheVoipH248MgConfigProfileModifiedTrap, sheVoipMediaCodecProfileCreatedTrap, sheVoipMediaCodecProfileDeletedTrap, sheVoipMediaCodecProfileModifiedTrap, 
				sheVoipMediaJitterBufProfileCreatedTrap, sheVoipMediaJitterBufProfileDeletedTrap, sheVoipMediaJitterBufProfileModifiedTrap, sheVoipMediaFaxProfileCreatedTrap, sheVoipMediaFaxProfileDeletedTrap, 
				sheVoipMediaFaxProfileModifiedTrap, sheVoipRtcpProfileCreatedTrap, sheVoipRtcpProfileDeletedTrap, sheVoipRtcpProfileModifiedTrap, sheVoipVoiceCtpConfigModifiedTrap, 
				sheVoipIpHostProfileCreatedTrap, sheVoipIpHostProfileDeletedTrap, sheVoipIpHostProfileModifiedTrap, sheVoipDigitMapProfileCreatedTrap, sheVoipDigitMapProfileDeletedTrap, 
				sheVoipDigitMapProfileModifiedTrap, sheVoipSipUAConfigProfileCreatedTrap, sheVoipSipUAConfigProfileDeletedTrap, sheVoipSipUAConfigProfileModifiedTrap, sheVoipSipProfileCreatedTrap, 
				sheVoipSipProfileDeletedTrap, sheVoipSipProfileModifiedTrap, sheVoipSipServerCreatedTrap, sheVoipSipServerDeletedTrap, sheVoipSipServerModifiedTrap, 
				sheVoipSipFACProfileCreatedTrap, sheVoipSipFACProfileDeletedTrap, sheVoipSipFACProfileModifiedTrap, sheVoipVgwDownAlarm, sheVoipVgwOperStatusChangedTrap, 
				sheVoipCallCtrlStatsFinishedTrap, sheVoipRtpMonPmStatsFinishedTrap, sheVoipVgwMonPmStatsFinishedTrap }
			STATUS current
			DESCRIPTION 
				"This group supports notifications of significant 
				conditions associated with physical objects."
			::= { sheVoipGroups 3 }

		
		sheVoipSipGroup OBJECT-GROUP
			OBJECTS { sheVoipSipUAConfigProfileIndex, sheVoipSipUAConfigProfileName, sheVoipSipUAConfigProfileRegExpTime, sheVoipSipUAConfigProfileReRegHeadStartTime, sheVoipSipUAConfigProfileSipProfileIndex, 
				sheVoipSipUAConfigProfileFACProfileIndex, sheVoipSipProfileIndex, sheVoipSipProfileName, sheVoipSipProfileProtocolVersion, sheVoipSipProfileOrganization, 
				sheVoipSipProfileMaxTransactions, sheVoipSipProfileInitialTimerReq, sheVoipSipProfileInitialTimerInvite, sheVoipSipProfileInitialTimerAck, sheVoipSipProfileInitialTimerBye, 
				sheVoipSipProfileInitialTimerCancel, sheVoipSipProfileInitialTimerRegister, sheVoipSipProfileInitialTimerOptions, sheVoipSipProfileInitialTimerPrack, sheVoipSipProfileInitialTimerRsp, 
				sheVoipSipProfileTimerT2, sheVoipSipProfileTimerT4, sheVoipSipProfileRetryReq, sheVoipSipProfileRetryInvite, sheVoipSipProfileRetryAck, 
				sheVoipSipProfileRetryBye, sheVoipSipProfileRetryCancel, sheVoipSipProfileRetryOptions, sheVoipSipProfileRetryPrack, sheVoipSipProfileRetryRegister, 
				sheVoipSipProfileRetryFinalResponse, sheVoipSipProfileCMTimeout, sheVoipSipProfileTimeout, sheVoipSipProfileCacheTimer, sheVoipSipProfileForward100toCM, 
				sheVoipSipProfileTcpSocketTimeout, sheVoipSipProfileSend100, sheVoipSipProfileMaxTcpConnections, sheVoipSipProfileProxyForwardAll1xx, sheVoipSipProfileDefOvlMinor, 
				sheVoipSipProfileDefOvlMajor, sheVoipSipProfileDefOvlCritical, sheVoipSipProfileDefOvlClear, sheVoipSipProfileDefOvlInvite, sheVoipSipProfileDefOvlRegister, 
				sheVoipSipProfileDefOvlAuth, sheVoipSipProfileUseOvlHdl, sheVoipSipServerConfigProfileIndex, sheVoipSipServerConfigProfileName, sheVoipSipRegServerConfigProfileAddr, 
				sheVoipSipServerConfigProfileFunction, sheVoipSipProxyServerConfigProfileIpAddress1, sheVoipSipProxyServerConfigProfileIpAddress2, sheVoipSipProxyServerConfigProfileIpAddress3, sheVoipSipProxyServerConfigProfilePort1, 
				sheVoipSipProxyServerConfigProfilePort2, sheVoipSipProxyServerConfigProfilePort3, sheVoipSipUsingProxyServerID, sheVoipSipServerConfigProfileSoftswitch, sheVoipSipServerConfigProfilePrimarySipDns, 
				sheVoipSipServerConfigProfileSecondarySipDns, sheVoipSipFACProfileIndex, sheVoipSipFACProfileName, sheVoipSipFACProfileCallForwardingUnconditionalActive, sheVoipSipFACProfileCallForwardingUnconditionalDeactive, 
				sheVoipSipFACProfileCallForwardingOnBusyActive, sheVoipSipFACProfileCallForwardingOnBusyDeactive, sheVoipSipFACProfileCallForwardingNoAnswerActive, sheVoipSipFACProfileCallForwardingNoAnswerDeactive, sheVoipSipFACProfileCallingLineIdRestrictionActive, 
				sheVoipSipFACProfileCallingLineIdRestrictionDeactive, sheVoipSipFACProfileMaliciousIdentificationActive, sheVoipSipFACProfileMaliciousIdentificationDeactive, sheVoipSipFACProfileCallCompletiontoOnBusySubsActive, sheVoipSipFACProfileCallCompletiontoOnBusySubsDeactive, 
				sheVoipSipFACProfileCallCompletiontoNoAnswerSubsActive, sheVoipSipFACProfileCallCompletiontoNoAnswerSubsDeactive, sheVoipSipFACProfileOutgoingCallBarringActive, sheVoipSipFACProfileOutgoingCallBarringDeactive, sheVoipSipFACProfileSelectiveCallAcceptanceActive, 
				sheVoipSipFACProfileSelectiveCallAcceptanceDeactive, sheVoipVgwSipUAConfigProfileIndex, sheVoipVgwSipServerConfigProfileIndex }
			STATUS current
			DESCRIPTION 
				"Description."
			::= { sheVoipGroups 4 }

		
		sheVoipSipControlGroup OBJECT-GROUP
			OBJECTS { sheVoipVgwControlSipUAConfigProfileIndex, sheVoipVgwControlSipServerConfigProfileIndex, sheVoipSipUAConfigProfileControlRequest, sheVoipSipUAConfigProfileControlStatus, sheVoipSipUAConfigProfileControlTimer, 
				sheVoipSipUAConfigProfileControlTimeStamp, sheVoipSipUAConfigProfileControlReqResult, sheVoipSipUAConfigProfileControlIndex, sheVoipSipUAConfigProfileControlName, sheVoipSipUAConfigProfileControlRegExpTime, 
				sheVoipSipUAConfigProfileControlReRegHeadStartTime, sheVoipSipUAConfigProfileControlSipProfileIndex, sheVoipSipUAConfigProfileControlFACProfileIndex, sheVoipSipProfileControlRequest, sheVoipSipProfileControlStatus, 
				sheVoipSipProfileControlTimer, sheVoipSipProfileControlTimeStamp, sheVoipSipProfileControlReqResult, sheVoipSipProfileControlIndex, sheVoipSipProfileControlName, 
				sheVoipSipProfileControlOrganization, sheVoipSipProfileControlInitialTimerReq, sheVoipSipProfileControlInitialTimerInvite, sheVoipSipProfileControlInitialTimerAck, sheVoipSipProfileControlInitialTimerBye, 
				sheVoipSipProfileControlInitialTimerCancel, sheVoipSipProfileControlInitialTimerRegister, sheVoipSipProfileControlInitialTimerOptions, sheVoipSipProfileControlInitialTimerPrack, sheVoipSipProfileControlInitialTimerRsp, 
				sheVoipSipProfileControlTimerT2, sheVoipSipProfileControlTimerT4, sheVoipSipProfileControlRetryReq, sheVoipSipProfileControlRetryInvite, sheVoipSipProfileControlRetryAck, 
				sheVoipSipProfileControlRetryBye, sheVoipSipProfileControlRetryCancel, sheVoipSipProfileControlRetryOptions, sheVoipSipProfileControlRetryPrack, sheVoipSipProfileControlRetryRegister, 
				sheVoipSipProfileControlRetryFinalResponse, sheVoipSipProfileControlCMTimeout, sheVoipSipProfileControlTimeout, sheVoipSipProfileControlCacheTimer, sheVoipSipProfileControlForward100toCM, 
				sheVoipSipProfileControlTcpSocketTimeout, sheVoipSipProfileControlSend100, sheVoipSipProfileControlMaxTcpConnections, sheVoipSipProfileControlProxyForwardAll1xx, sheVoipSipProfileControlDefOvlMinor, 
				sheVoipSipProfileControlDefOvlMajor, sheVoipSipProfileControlDefOvlCritical, sheVoipSipProfileControlDefOvlClear, sheVoipSipProfileControlDefOvlInvite, sheVoipSipProfileControlDefOvlRegister, 
				sheVoipSipProfileControlDefOvlAuth, sheVoipSipProfileControlUseOvlHdl, sheVoipSipFACProfileControlRequest, sheVoipSipFACProfileControlStatus, sheVoipSipFACProfileControlTimer, 
				sheVoipSipFACProfileControlTimeStamp, sheVoipSipFACProfileControlReqResult, sheVoipSipFACProfileControlIndex, sheVoipSipFACProfileControlName, sheVoipSipFACProfileControlCallForwardingUnconditionalActive, 
				sheVoipSipFACProfileControlCallForwardingUnconditionalDeactive, sheVoipSipFACProfileControlCallForwardingOnBusyActive, sheVoipSipFACProfileControlCallForwardingOnBusyDeactive, sheVoipSipFACProfileControlCallForwardingNoAnswerActive, sheVoipSipFACProfileControlCallForwardingNoAnswerDeactive, 
				sheVoipSipFACProfileControlCallingLineIdRestrictionActive, sheVoipSipFACProfileControlCallingLineIdRestrictionDeactive, sheVoipSipFACProfileControlMaliciousIdentificationActive, sheVoipSipFACProfileControlMaliciousIdentificationDeactive, sheVoipSipFACProfileControlCallCompletiontoOnBusySubsActive, 
				sheVoipSipFACProfileControlCallCompletiontoOnBusySubsDeactive, sheVoipSipFACProfileControlCallCompletiontoNoAnswerSubsActive, sheVoipSipFACProfileControlCallCompletiontoNoAnswerSubsDeactive, sheVoipSipFACProfileControlOutgoingCallBarringActive, sheVoipSipFACProfileControlOutgoingCallBarringDeactive, 
				sheVoipSipFACProfileControlSelectiveCallAcceptanceActive, sheVoipSipFACProfileControlSelectiveCallAcceptanceDeactive, sheVoipSipServerConfigProfileControlRequest, sheVoipSipServerConfigProfileControlStatus, sheVoipSipServerConfigProfileControlTimer, 
				sheVoipSipServerConfigProfileControlTimeStamp, sheVoipSipServerConfigProfileControlReqResult, sheVoipSipServerConfigProfileControlIndex, sheVoipSipRegServerConfigProfileControlAddr, sheVoipSipServerConfigProfileControlFunction, 
				sheVoipSipProxyServerConfigProfileControlIpAddress1, sheVoipSipProxyServerConfigProfileControlIpAddress2, sheVoipSipProxyServerConfigProfileControlIpAddress3, sheVoipSipProxyServerConfigProfileControlPort1, sheVoipSipProxyServerConfigProfileControlPort2, 
				sheVoipSipProxyServerConfigProfileControlPort3, sheVoipSipServerConfigProfileControlSoftswitch, sheVoipSipServerConfigProfileControlPrimarySipDns, sheVoipSipServerConfigProfileControlSecondarySipDns, sheVoipSipServerConfigProfileControlName
				 }
			STATUS current
			DESCRIPTION 
				"Description."
			::= { sheVoipGroups 5 }

		
		sheVoipCompliances OBJECT IDENTIFIER ::= { sheVoipConformance 2 }

		
		sheVoipMibCompliance MODULE-COMPLIANCE
			STATUS current
			DESCRIPTION 
				"Description."
			MODULE -- this module
				MANDATORY-GROUPS { sheVoipGroup, sheVoipControlGroup, sheVoipNotificationGroup, sheVoipSipGroup, sheVoipSipControlGroup
					 }
			::= { sheVoipCompliances 1 }

		
	
	END

--
-- she-voip-mib-module.mib
--
