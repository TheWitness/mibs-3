--
-- SLE-BRIDGE-MIB.my
-- MIB generated by MG-SOFT Visual MIB Builder Version 6.0  Build 88
-- Friday, January 16, 2009 at 16:08:49
--

--  SLE-BRIDGE-MIB.my
-- MIB generated by MG-SOFT Visual MIB Builder Version 3.0 Build 285
-- Monday, December 13, 2004 at 13:09:15
-- 
--  SLE-BRIDGE-MIB.my
-- MIB generated by MG-SOFT Visual MIB Builder Version 4.0 Build 417
-- Wednesday, December 08, 2004 at 13:53:43
-- 

	SLE-BRIDGE-MIB DEFINITIONS ::= BEGIN
 
		IMPORTS
			sleMgmt			
				FROM DASAN-SMI			
			InterfaceIndex			
				FROM IF-MIB			
			SleControlStatusType, SleControlRequestResultType			
				FROM SLE-TC-MIB			
			OBJECT-GROUP, NOTIFICATION-GROUP			
				FROM SNMPv2-CONF			
			TimeTicks, IpAddress, Integer32, Unsigned32, Gauge32, 
			Counter32, BITS, OBJECT-TYPE, MODULE-IDENTITY, NOTIFICATION-TYPE			
				FROM SNMPv2-SMI			
			TimeStamp, MacAddress, TruthValue			
				FROM SNMPv2-TC;
	
	
--  			sle			
-- FROM AN-MIB			
-- December 08, 2004 at 08:40 GMT
-- 
-- 1.3.6.1.4.1.6296.9.8
-- December 08, 2004 at 09:03 GMT
-- December 08, 2004 at 08:40 GMT
		-- 1.3.6.1.4.1.6296.101.3
		sleBridge MODULE-IDENTITY 
			LAST-UPDATED "200412080903Z"		-- December 08, 2004 at 09:03 GMT
			ORGANIZATION 
				" "
			CONTACT-INFO 
				" "
			DESCRIPTION 
				"This MIB contains all needed informations about bridgePorts and
				all supported sle bridgeing features."
			REVISION "200412080840Z"		-- December 08, 2004 at 08:40 GMT
			DESCRIPTION 
				"AFI"
			::= { sleMgmt 3 }

		
	
--
-- Type definitions
--
	
		Boolean ::= INTEGER
			{
			disable(0),
			enable(1)
			}

		SleLldpSysCapType ::= BITS
			{
			other(0),
			repeater(1),
			bridge(2),
			wlanAccessPoint(3),
			router(4),
			telephone(5),
			docsisCableDevice(6),
			stationOnly(7)
			}

--  Type definitions
-- 
		SleIgmpMcastControlRequestType ::= INTEGER
			{
			createIgmpStaticMcast(1),
			destroyIgmpStaticMcast(2)
			}

		SleIgmpConfControlRequestType ::= INTEGER { setIgmpConfProfile(1) }

	
	
--
-- Node definitions
--
	
--  Node definitions
-- 
-- 1.3.6.1.4.1.6296.9.8.1
		-- 1.3.6.1.4.1.6296.101.3.1
		sleBridgeBase OBJECT IDENTIFIER ::= { sleBridge 1 }

		
--  1.3.6.1.4.1.6296.9.8.1.1
		-- 1.3.6.1.4.1.6296.101.3.1.1
		sleBridgeBaseInfo OBJECT IDENTIFIER ::= { sleBridgeBase 1 }

		
--  1.3.6.1.4.1.6296.9.8.1.1.1
		-- 1.3.6.1.4.1.6296.101.3.1.1.1
		sleBridgeMacAddress OBJECT-TYPE
			SYNTAX OCTET STRING (SIZE (6))
			MAX-ACCESS read-only
			STATUS current
			DESCRIPTION
				"System MAC Address of bridge"
			::= { sleBridgeBaseInfo 1 }

		
--  1.3.6.1.4.1.6296.9.8.1.1.2
		-- 1.3.6.1.4.1.6296.101.3.1.1.2
		sleBridgePortNum OBJECT-TYPE
			SYNTAX INTEGER (1..256)
			MAX-ACCESS read-only
			STATUS current
			DESCRIPTION
				"Number of bridge ports"
			::= { sleBridgeBaseInfo 2 }

		
--  1.3.6.1.4.1.6296.9.8.1.1.3
		-- 1.3.6.1.4.1.6296.101.3.1.1.3
		sleBridgeLagMaxId OBJECT-TYPE
			SYNTAX INTEGER (1..14)
			MAX-ACCESS read-only
			STATUS current
			DESCRIPTION
				"This value assigned to the aggregation max id."
			::= { sleBridgeBaseInfo 3 }

		
--  1.3.6.1.4.1.6296.9.8.1.1.4
		-- 1.3.6.1.4.1.6296.101.3.1.1.4
		sleBridgeLacpActivity OBJECT-TYPE
			SYNTAX INTEGER
				{
				disabled(0),
				enabled(1)
				}
			MAX-ACCESS read-only
			STATUS current
			DESCRIPTION
				"The LACP enabled/disabled status of the switch"
			::= { sleBridgeBaseInfo 4 }

		
--  1.3.6.1.4.1.6296.9.8.1.1.5
		-- 1.3.6.1.4.1.6296.101.3.1.1.5
		sleBridgeLacpPriority OBJECT-TYPE
			SYNTAX INTEGER (1..65535)
			MAX-ACCESS read-only
			STATUS current
			DESCRIPTION
				"The priority assigned to the Actor System"
			::= { sleBridgeBaseInfo 5 }

		
--  1.3.6.1.4.1.6296.9.8.1.1.6
		-- 1.3.6.1.4.1.6296.101.3.1.1.6
		sleBridgeVlanSupportMode OBJECT-TYPE
			SYNTAX BITS
				{
				portbased(0),
				protocolbased(1),
				subnetbased(2)
				}
			MAX-ACCESS read-only
			STATUS current
			DESCRIPTION
				"The supported VLAN mode for ingress untagged frame"
			::= { sleBridgeBaseInfo 6 }

		
--  1.3.6.1.4.1.6296.9.8.1.1.7
		-- 1.3.6.1.4.1.6296.101.3.1.1.7
		sleBridgeVlanMaxNum OBJECT-TYPE
			SYNTAX INTEGER (0..4096)
			MAX-ACCESS read-only
			STATUS current
			DESCRIPTION
				"sleBridgeVlanMaxNum"
			::= { sleBridgeBaseInfo 7 }

		
--  1.3.6.1.4.1.6296.9.8.1.1.8
		-- 1.3.6.1.4.1.6296.101.3.1.1.8
		sleBridgeDoubleTagProtoId OBJECT-TYPE
			SYNTAX INTEGER
				{
				dtag8100(33024),
				dtag9100(37120)
				}
			MAX-ACCESS read-only
			STATUS current
			DESCRIPTION
				"programmable Double Tag Protocol Identifier."
			::= { sleBridgeBaseInfo 8 }

		
--  1.3.6.1.4.1.6296.9.8.1.1.23
		-- 1.3.6.1.4.1.6296.101.3.1.1.9
		sleBridgeMirrorMode OBJECT-TYPE
			SYNTAX INTEGER
				{
				disabled(0),
				enabled(1)
				}
			MAX-ACCESS read-only
			STATUS current
			DESCRIPTION
				"Mirror mode of bridge"
			::= { sleBridgeBaseInfo 9 }

		
--  1.3.6.1.4.1.6296.9.8.1.1.24
		-- 1.3.6.1.4.1.6296.101.3.1.1.10
		sleBridgeMirrorMonitorPortId OBJECT-TYPE
			SYNTAX INTEGER (1..255)
			MAX-ACCESS read-only
			STATUS current
			DESCRIPTION
				"Mirroring port ID
				1-254: physical port ID
				255: mirror to cpu"
			::= { sleBridgeBaseInfo 10 }

		
		-- 1.3.6.1.4.1.6296.101.3.1.1.11
		sleBridgeMirroredIngressPorts OBJECT-TYPE
			SYNTAX OCTET STRING (SIZE (0..32))
			MAX-ACCESS read-only
			STATUS current
			DESCRIPTION
				"Ingress mirrored port map"
			::= { sleBridgeBaseInfo 11 }

		
		-- 1.3.6.1.4.1.6296.101.3.1.1.12
		sleBridgeMirroredEgressPorts OBJECT-TYPE
			SYNTAX OCTET STRING (SIZE (0..32))
			MAX-ACCESS read-only
			STATUS current
			DESCRIPTION
				"Egress mirrored port map"
			::= { sleBridgeBaseInfo 12 }

		
		-- 1.3.6.1.4.1.6296.101.3.1.1.13
		sleBridgeMaxLearnPerUnit OBJECT-TYPE
			SYNTAX INTEGER (-1..2147483647)
			MAX-ACCESS read-only
			STATUS current
			DESCRIPTION
				"Limit maximum number of MAC addresses learning 
				newly per unit time(one second) on a bridge.
				(0: nothing learned, -l: unlimited.)"
			::= { sleBridgeBaseInfo 13 }

		
--  1.3.6.1.4.1.6296.9.8.1.1.25
		-- 1.3.6.1.4.1.6296.101.3.1.1.14
		sleBridgeFdbAgeingTime OBJECT-TYPE
			SYNTAX Integer32 (10..21474830)
			MAX-ACCESS read-only
			STATUS current
			DESCRIPTION
				"The timeout period in seconds for aging out 
				dynamically learned forwarding information."
			DEFVAL { 300 }
			::= { sleBridgeBaseInfo 14 }

		
--  1.3.6.1.4.1.6296.9.8.1.1.26
		-- 1.3.6.1.4.1.6296.101.3.1.1.15
		sleBridgeFdbMaxEntries OBJECT-TYPE
			SYNTAX Integer32
			MAX-ACCESS read-only
			STATUS current
			DESCRIPTION
				"The supported maximum fdb entries."
			::= { sleBridgeBaseInfo 15 }

		
		-- 1.3.6.1.4.1.6296.101.3.1.1.16
		sleBridgeFdbCurrentEntries OBJECT-TYPE
			SYNTAX Integer32
			MAX-ACCESS read-only
			STATUS current
			DESCRIPTION
				"Number of Fdb entries learned currently."
			::= { sleBridgeBaseInfo 16 }

		
--  1.3.6.1.4.1.6296.9.8.1.1.27
		-- 1.3.6.1.4.1.6296.101.3.1.1.17
		sleBridgeStackMode OBJECT-TYPE
			SYNTAX INTEGER
				{
				disable(0),
				master(1),
				slave(2)
				}
			MAX-ACCESS read-only
			STATUS current
			DESCRIPTION
				"Stack status of device."
			::= { sleBridgeBaseInfo 17 }

		
--  1.3.6.1.4.1.6296.9.8.1.1.28
		-- 1.3.6.1.4.1.6296.101.3.1.1.18
		sleBridgeStackDeviceName OBJECT-TYPE
			SYNTAX OCTET STRING (SIZE (0..8))
			MAX-ACCESS read-only
			STATUS current
			DESCRIPTION
				"Device name of stack device."
			::= { sleBridgeBaseInfo 18 }

		
--  1.3.6.1.4.1.6296.9.8.1.1.29
		-- 1.3.6.1.4.1.6296.101.3.1.1.19
		sleBridgeStackNodeId OBJECT-TYPE
			SYNTAX INTEGER (1..65534)
			MAX-ACCESS read-only
			STATUS current
			DESCRIPTION
				"Node ID of stack device"
			::= { sleBridgeBaseInfo 19 }

		
--  1.3.6.1.4.1.6296.9.8.1.1.30
		-- 1.3.6.1.4.1.6296.101.3.1.1.20
		sleBridgeLldpMessageTxInterval OBJECT-TYPE
			SYNTAX Integer32 (5..32768)
			MAX-ACCESS read-write
			STATUS current
			DESCRIPTION
				"The interval at which LLDP frames are transmitted on behalf of this LLDP agent."
			::= { sleBridgeBaseInfo 20 }

		
--  1.3.6.1.4.1.6296.9.8.1.1.31
		-- 1.3.6.1.4.1.6296.101.3.1.1.21
		sleBridgeLldpTxHoldMultiplier OBJECT-TYPE
			SYNTAX Integer32 (2..10)
			MAX-ACCESS read-write
			STATUS current
			DESCRIPTION
				"The time-to-live value expressed as a multiple of the sleBridgeLldpMessageTxInterval object."
			::= { sleBridgeBaseInfo 21 }

		
--  1.3.6.1.4.1.6296.9.8.1.1.32
		-- 1.3.6.1.4.1.6296.101.3.1.1.22
		sleBridgeLldpReinitDelay OBJECT-TYPE
			SYNTAX Integer32 (1..10)
			MAX-ACCESS read-write
			STATUS current
			DESCRIPTION
				"Delay (in units of seconds) from when lldpPortConfigAdminStatus object of a particular port  becomes 'disabled' until re-initialization will be attempted."
			::= { sleBridgeBaseInfo 22 }

		
--  1.3.6.1.4.1.6296.9.8.1.1.33
		-- 1.3.6.1.4.1.6296.101.3.1.1.23
		sleBridgeLldpTxDelay OBJECT-TYPE
			SYNTAX Integer32 (1..8192)
			MAX-ACCESS read-write
			STATUS current
			DESCRIPTION
				"Delay (in units of seconds) between successive LLDP frame transmissions initiated by value/status changes in the LLDP local systems MIB."
			::= { sleBridgeBaseInfo 23 }

		
--  1.3.6.1.4.1.6296.9.8.1.1.34
		-- 1.3.6.1.4.1.6296.101.3.1.1.24
		sleBridgeLldpNotificationInterval OBJECT-TYPE
			SYNTAX Integer32 (5..3600)
			MAX-ACCESS read-write
			STATUS current
			DESCRIPTION
				"The agent must not generate more than one lldpRemTablesChangenotification-event in the indicated period."
			DEFVAL { 5 }
			::= { sleBridgeBaseInfo 24 }

		
--  1.3.6.1.4.1.6296.9.8.1.1.36
		-- 1.3.6.1.4.1.6296.101.3.1.1.25
		sleBridgeLldpStatsRemTablesLastChangeTime OBJECT-TYPE
			SYNTAX TimeTicks
			MAX-ACCESS read-only
			STATUS current
			DESCRIPTION
				"The value of sysUpTime object (defined in IETF RFC 3418)at the time an entry is created, modified, or deleted in thein tables associated with the lldpRemoteSystemsData objects and all LLDP extension objects associated with remote systems."
			::= { sleBridgeBaseInfo 25 }

		
--  1.3.6.1.4.1.6296.9.8.1.1.37
		-- 1.3.6.1.4.1.6296.101.3.1.1.26
		sleBridgeLldpStatsRemTablesInserts OBJECT-TYPE
			SYNTAX Integer32
			MAX-ACCESS read-only
			STATUS current
			DESCRIPTION
				"The number of times the complete set of informationadvertised by a particular MSAP has been inserted into tables contained in lldpRemoteSystemsData and lldpExtensions objects."
			::= { sleBridgeBaseInfo 26 }

		
--  1.3.6.1.4.1.6296.9.8.1.1.38
		-- 1.3.6.1.4.1.6296.101.3.1.1.27
		sleBridgeLldpStatsRemTablesDeletes OBJECT-TYPE
			SYNTAX Integer32
			MAX-ACCESS read-only
			STATUS current
			DESCRIPTION
				"The number of times the complete set of informationadvertised by a particular MSAP has been deleted fromtables contained in lldpRemoteSystemsData and lldpExtensions objects."
			::= { sleBridgeBaseInfo 27 }

		
--  1.3.6.1.4.1.6296.9.8.1.1.39
		-- 1.3.6.1.4.1.6296.101.3.1.1.28
		sleBridgeLldpStatsRemTablesDrops OBJECT-TYPE
			SYNTAX Integer32
			MAX-ACCESS read-only
			STATUS current
			DESCRIPTION
				"The number of times the complete set of information advertised by a particular MSAP could not be entered intotables contained in lldpRemoteSystemsData and lldpExtensions objects because of insufficient resources."
			::= { sleBridgeBaseInfo 28 }

		
--  1.3.6.1.4.1.6296.9.8.1.1.40
		-- 1.3.6.1.4.1.6296.101.3.1.1.29
		sleBridgeLldpStatsRemTablesAgeouts OBJECT-TYPE
			SYNTAX Integer32
			MAX-ACCESS read-only
			STATUS current
			DESCRIPTION
				"The number of times the complete set of informationadvertised by a particular MSAP has been deleted from tables contained in lldpRemoteSystemsData and lldpExtensions objectsbecause the information timeliness interval has expired."
			::= { sleBridgeBaseInfo 29 }

		
--  1.3.6.1.4.1.6296.9.8.1.1.41
		-- 1.3.6.1.4.1.6296.101.3.1.1.30
		sleBridgeLldpLocalChassisIdSubtype OBJECT-TYPE
			SYNTAX INTEGER
				{
				chassisComponent(1),
				interfaceAlias(2),
				portComponent(3),
				macAddress(4),
				networkAddress(5),
				interfaceName(6),
				local(7)
				}
			MAX-ACCESS read-only
			STATUS current
			DESCRIPTION
				"The type of encoding used to identify the chassis associated with the local system."
			::= { sleBridgeBaseInfo 30 }

		
--  1.3.6.1.4.1.6296.9.8.1.1.42
		-- 1.3.6.1.4.1.6296.101.3.1.1.31
		sleBridgeLldpLocalChassisId OBJECT-TYPE
			SYNTAX OCTET STRING (SIZE (1..255))
			MAX-ACCESS read-only
			STATUS current
			DESCRIPTION
				"The string value used to identify the chassis component associated with the local system."
			::= { sleBridgeBaseInfo 31 }

		
--  1.3.6.1.4.1.6296.9.8.1.1.43
		-- 1.3.6.1.4.1.6296.101.3.1.1.32
		sleBridgeLldpLocalSysName OBJECT-TYPE
			SYNTAX OCTET STRING (SIZE (0..255))
			MAX-ACCESS read-only
			STATUS current
			DESCRIPTION
				"The string value used to identify the system name of the local system."
			::= { sleBridgeBaseInfo 32 }

		
--  1.3.6.1.4.1.6296.9.8.1.1.44
		-- 1.3.6.1.4.1.6296.101.3.1.1.33
		sleBridgeLldpLocalSysDes OBJECT-TYPE
			SYNTAX OCTET STRING (SIZE (0..255))
			MAX-ACCESS read-write
			STATUS current
			DESCRIPTION
				"The string value used to identify the system description of the local system."
			::= { sleBridgeBaseInfo 33 }

		
--  1.3.6.1.4.1.6296.9.8.1.1.45
		-- 1.3.6.1.4.1.6296.101.3.1.1.34
		sleBridgeLldpLocalSysCapSupported OBJECT-TYPE
			SYNTAX BITS
				{
				other(0),
				repeater(1),
				bridge(2),
				wlanAccessPoint(3),
				router(4),
				telephone(5),
				docsisCableDevice(6),
				stationOnly(7)
				}
			MAX-ACCESS read-only
			STATUS current
			DESCRIPTION
				"The bitmap value used to identify which system capabilities are supported on the local system."
			::= { sleBridgeBaseInfo 34 }

		
--  1.3.6.1.4.1.6296.9.8.1.1.46
		-- 1.3.6.1.4.1.6296.101.3.1.1.35
		sleBridgeLldpLocalSysCapEnabled OBJECT-TYPE
			SYNTAX BITS
				{
				other(0),
				repeater(1),
				bridge(2),
				wlanAccessPoint(3),
				router(4),
				telephone(5),
				docsisCableDevice(6),
				stationOnly(7)
				}
			MAX-ACCESS read-only
			STATUS current
			DESCRIPTION
				"The bitmap value used to identify which system capabilities are enabled on the local system."
			::= { sleBridgeBaseInfo 35 }

		
--  1.3.6.1.4.1.6296.9.8.1.1.47
		-- 1.3.6.1.4.1.6296.101.3.1.1.36
		sleBridgeStpActivity OBJECT-TYPE
			SYNTAX INTEGER
				{
				disabled(0),
				enabled(1)
				}
			MAX-ACCESS read-only
			STATUS current
			DESCRIPTION
				"The STP enabled/disabled status of the switch."
			::= { sleBridgeBaseInfo 36 }

		
		-- 1.3.6.1.4.1.6296.101.3.1.1.37
		sleBridgeStpSelfLoop OBJECT-TYPE
			SYNTAX INTEGER
				{
				disable(0),
				enable(1)
				}
			MAX-ACCESS read-write
			STATUS current
			DESCRIPTION
				"Description."
			::= { sleBridgeBaseInfo 37 }

		
		-- 1.3.6.1.4.1.6296.101.3.1.1.38
		sleBridgePvlanOnePromPortEnable OBJECT-TYPE
			SYNTAX INTEGER
				{
				disable(0),
				enable(1)
				}
			MAX-ACCESS read-write
			STATUS current
			DESCRIPTION
				"Description."
			DEFVAL { 0 }
			::= { sleBridgeBaseInfo 38 }

		
		-- 1.3.6.1.4.1.6296.101.3.1.1.39
		sleBridgeTcpSyncookie OBJECT-TYPE
			SYNTAX INTEGER
				{
				disable(0),
				enable(1)
				}
			MAX-ACCESS read-only
			STATUS current
			DESCRIPTION
				"Description."
			::= { sleBridgeBaseInfo 39 }

		
		-- 1.3.6.1.4.1.6296.101.3.1.1.40
		sleBridgeTcpIgnoreRstUnknown OBJECT-TYPE
			SYNTAX INTEGER
				{
				disable(0),
				enable(1)
				}
			MAX-ACCESS read-only
			STATUS current
			DESCRIPTION
				"Description."
			::= { sleBridgeBaseInfo 40 }

		
		-- 1.3.6.1.4.1.6296.101.3.1.1.41
		sleBridgeAutoInterfaceActivation OBJECT-TYPE
			SYNTAX INTEGER
				{
				enable(1),
				disable(2)
				}
			MAX-ACCESS read-only
			STATUS current
			DESCRIPTION
				"Description."
			::= { sleBridgeBaseInfo 41 }

		
		-- 1.3.6.1.4.1.6296.101.3.1.1.42
		sleBridgeLoopDetectStatus OBJECT-TYPE
			SYNTAX INTEGER
				{
				enable(1),
				disable(2)
				}
			MAX-ACCESS read-only
			STATUS current
			DESCRIPTION
				"Description."
			::= { sleBridgeBaseInfo 42 }

		
		-- 1.3.6.1.4.1.6296.101.3.1.1.43
		sleBridgeLoopDetectPacketType OBJECT-TYPE
			SYNTAX INTEGER
				{
				laa(1),
				system(2)
				}
			MAX-ACCESS read-only
			STATUS current
			DESCRIPTION
				"Description."
			::= { sleBridgeBaseInfo 43 }

		
		-- 1.3.6.1.4.1.6296.101.3.1.1.44
		sleBridgePvlanPromSelectMode OBJECT-TYPE
			SYNTAX INTEGER
				{
				normal(0),
				manual(1),
				stp(2),
				erp(3)
				}
			MAX-ACCESS read-only
			STATUS current
			DESCRIPTION
				"Description."
			::= { sleBridgeBaseInfo 44 }

		
		-- 1.3.6.1.4.1.6296.101.3.1.1.45
		sleBridgePvlanPromiscuousPorts OBJECT-TYPE
			SYNTAX OCTET STRING
			MAX-ACCESS read-only
			STATUS current
			DESCRIPTION
				"Description."
			::= { sleBridgeBaseInfo 45 }

		
--  1.3.6.1.4.1.6296.9.8.1.2
		-- 1.3.6.1.4.1.6296.101.3.1.2
		sleBridgeBaseControl OBJECT IDENTIFIER ::= { sleBridgeBase 2 }

		
--   1.3.6.1.4.1.6296.9.8.1.2.1
-- 1.3.6.1.4.1.6296.101.3.1.2.1
		-- 1.3.6.1.4.1.6296.101.3.1.2.1
		sleBridgeControlRequest OBJECT-TYPE
			SYNTAX INTEGER
				{
				setLacpProfile(1),
				setDoubleTagProtoId(2),
				setMirrorProfile(3),
				setMaxLearnPerUnit(4),
				setFdbAgeingTime(5),
				setStackProfile(6),
				setLldpProfile(7),
				setStpProfile(8),
				setTcpSyncookie(9),
				setTcpIgnoreRstUnknown(10),
				setAutoInterfaceActivation(11),
				setLoopDetectProfile(12),
				setPvlanPromSelectMode(13)
				}
			MAX-ACCESS read-write
			STATUS current
			DESCRIPTION
				" "
			::= { sleBridgeBaseControl 1 }

		
--  1.3.6.1.4.1.6296.9.8.1.2.2
		-- 1.3.6.1.4.1.6296.101.3.1.2.2
		sleBridgeControlStatus OBJECT-TYPE
			SYNTAX SleControlStatusType
			MAX-ACCESS read-only
			STATUS current
			DESCRIPTION
				" "
			::= { sleBridgeBaseControl 2 }

		
--  1.3.6.1.4.1.6296.9.8.1.2.3
		-- 1.3.6.1.4.1.6296.101.3.1.2.3
		sleBridgeControlTimer OBJECT-TYPE
			SYNTAX Gauge32
			MAX-ACCESS read-write
			STATUS current
			DESCRIPTION
				" "
			::= { sleBridgeBaseControl 3 }

		
--  1.3.6.1.4.1.6296.9.8.1.2.5
		-- 1.3.6.1.4.1.6296.101.3.1.2.4
		sleBridgeControlTimeStamp OBJECT-TYPE
			SYNTAX TimeTicks
			MAX-ACCESS read-only
			STATUS current
			DESCRIPTION
				" "
			::= { sleBridgeBaseControl 4 }

		
--  1.3.6.1.4.1.6296.9.8.1.2.4
		-- 1.3.6.1.4.1.6296.101.3.1.2.5
		sleBridgeControlReqResult OBJECT-TYPE
			SYNTAX SleControlRequestResultType
			MAX-ACCESS read-only
			STATUS current
			DESCRIPTION
				"Result of the last command."
			::= { sleBridgeBaseControl 5 }

		
--  1.3.6.1.4.1.6296.9.8.1.2.6
		-- 1.3.6.1.4.1.6296.101.3.1.2.6
		sleBridgeControlLacpActivity OBJECT-TYPE
			SYNTAX INTEGER
				{
				disabled(0),
				enabled(1)
				}
			MAX-ACCESS read-write
			STATUS current
			DESCRIPTION
				" "
			::= { sleBridgeBaseControl 6 }

		
--  1.3.6.1.4.1.6296.9.8.1.2.7
		-- 1.3.6.1.4.1.6296.101.3.1.2.7
		sleBridgeControlLacpPriority OBJECT-TYPE
			SYNTAX INTEGER (1..65535)
			MAX-ACCESS read-write
			STATUS current
			DESCRIPTION
				" "
			::= { sleBridgeBaseControl 7 }

		
--  1.3.6.1.4.1.6296.9.8.1.2.8
		-- 1.3.6.1.4.1.6296.101.3.1.2.8
		sleBridgeControlDoubleTagProtoId OBJECT-TYPE
			SYNTAX Integer32
			MAX-ACCESS read-write
			STATUS current
			DESCRIPTION
				" "
			::= { sleBridgeBaseControl 8 }

		
--  1.3.6.1.4.1.6296.9.8.1.2.18
		-- 1.3.6.1.4.1.6296.101.3.1.2.9
		sleBridgeControlMirrorMode OBJECT-TYPE
			SYNTAX INTEGER
				{
				disabled(0),
				enabled(1)
				}
			MAX-ACCESS read-write
			STATUS current
			DESCRIPTION
				" "
			::= { sleBridgeBaseControl 9 }

		
--  1.3.6.1.4.1.6296.9.8.1.2.19
		-- 1.3.6.1.4.1.6296.101.3.1.2.10
		sleBridgeControlMirrorMonitorPortId OBJECT-TYPE
			SYNTAX INTEGER (1..255)
			MAX-ACCESS read-write
			STATUS current
			DESCRIPTION
				"1-254:physical port ID
				255: mirror to cpu"
			::= { sleBridgeBaseControl 10 }

		
		-- 1.3.6.1.4.1.6296.101.3.1.2.11
		sleBridgeControlMaxLearnPerUnit OBJECT-TYPE
			SYNTAX INTEGER (-1..2147483647)
			MAX-ACCESS read-write
			STATUS current
			DESCRIPTION
				"Description."
			::= { sleBridgeBaseControl 11 }

		
--  1.3.6.1.4.1.6296.9.8.1.2.20
		-- 1.3.6.1.4.1.6296.101.3.1.2.12
		sleBridgeControlFdbAgeingTime OBJECT-TYPE
			SYNTAX Unsigned32 (10..21474830)
			MAX-ACCESS read-write
			STATUS current
			DESCRIPTION
				"The timeout period in seconds for aging out
				dynamically learned forwarding information."
			DEFVAL { 300 }
			::= { sleBridgeBaseControl 12 }

		
--  1.3.6.1.4.1.6296.9.8.1.2.21
		-- 1.3.6.1.4.1.6296.101.3.1.2.13
		sleBridgeControlStackMode OBJECT-TYPE
			SYNTAX INTEGER
				{
				disable(0),
				master(1),
				slave(2)
				}
			MAX-ACCESS read-write
			STATUS current
			DESCRIPTION
				"Stack status of device."
			::= { sleBridgeBaseControl 13 }

		
--  1.3.6.1.4.1.6296.9.8.1.2.22
		-- 1.3.6.1.4.1.6296.101.3.1.2.14
		sleBridgeControlStackDeviceName OBJECT-TYPE
			SYNTAX OCTET STRING (SIZE (0..8))
			MAX-ACCESS read-write
			STATUS current
			DESCRIPTION
				"Device name of stack device."
			::= { sleBridgeBaseControl 14 }

		
--  1.3.6.1.4.1.6296.9.8.1.2.23
		-- 1.3.6.1.4.1.6296.101.3.1.2.15
		sleBridgeControlLldpMessageTxInterval OBJECT-TYPE
			SYNTAX INTEGER (5..32767)
			MAX-ACCESS read-write
			STATUS current
			DESCRIPTION
				" "
			::= { sleBridgeBaseControl 15 }

		
--  1.3.6.1.4.1.6296.9.8.1.2.24
		-- 1.3.6.1.4.1.6296.101.3.1.2.16
		sleBridgeControlLldpTxHoldMultiplier OBJECT-TYPE
			SYNTAX INTEGER (2..10)
			MAX-ACCESS read-write
			STATUS current
			DESCRIPTION
				"
				"
			::= { sleBridgeBaseControl 16 }

		
--  1.3.6.1.4.1.6296.9.8.1.2.25
		-- 1.3.6.1.4.1.6296.101.3.1.2.17
		sleBridgeControlLldpReinitDelay OBJECT-TYPE
			SYNTAX INTEGER (1..10)
			MAX-ACCESS read-write
			STATUS current
			DESCRIPTION
				" "
			::= { sleBridgeBaseControl 17 }

		
--  1.3.6.1.4.1.6296.9.8.1.2.26
		-- 1.3.6.1.4.1.6296.101.3.1.2.18
		sleBridgeControlLldpTxDelay OBJECT-TYPE
			SYNTAX INTEGER (1..8192)
			MAX-ACCESS read-write
			STATUS current
			DESCRIPTION
				"
				"
			::= { sleBridgeBaseControl 18 }

		
--  1.3.6.1.4.1.6296.9.8.1.2.27
		-- 1.3.6.1.4.1.6296.101.3.1.2.19
		sleBridgeControlLldpNotificationInterval OBJECT-TYPE
			SYNTAX INTEGER (5..3600)
			MAX-ACCESS read-write
			STATUS current
			DESCRIPTION
				" "
			::= { sleBridgeBaseControl 19 }

		
--  1.3.6.1.4.1.6296.9.8.1.2.29
		-- 1.3.6.1.4.1.6296.101.3.1.2.20
		sleBridgeControlStpActivity OBJECT-TYPE
			SYNTAX INTEGER
				{
				disabled(0),
				enabled(1)
				}
			MAX-ACCESS read-write
			STATUS current
			DESCRIPTION
				" "
			::= { sleBridgeBaseControl 20 }

		
		-- 1.3.6.1.4.1.6296.101.3.1.2.21
		sleBridgeControlStpSelfLoop OBJECT-TYPE
			SYNTAX INTEGER
				{
				disable(0),
				enable(1)
				}
			MAX-ACCESS read-write
			STATUS current
			DESCRIPTION
				"Description."
			::= { sleBridgeBaseControl 21 }

		
		-- 1.3.6.1.4.1.6296.101.3.1.2.22
		sleBridgeControlTcpSyncookie OBJECT-TYPE
			SYNTAX INTEGER
				{
				disable(0),
				enable(1)
				}
			MAX-ACCESS read-write
			STATUS current
			DESCRIPTION
				"Description."
			::= { sleBridgeBaseControl 22 }

		
		-- 1.3.6.1.4.1.6296.101.3.1.2.23
		sleBridgeControlTcpIgnoreRstUnknown OBJECT-TYPE
			SYNTAX INTEGER
				{
				disable(0),
				enable(1)
				}
			MAX-ACCESS read-write
			STATUS current
			DESCRIPTION
				"Description."
			::= { sleBridgeBaseControl 23 }

		
		-- 1.3.6.1.4.1.6296.101.3.1.2.24
		sleBridgeControlAutoInterfaceActivation OBJECT-TYPE
			SYNTAX INTEGER
				{
				enable(1),
				disable(2)
				}
			MAX-ACCESS read-write
			STATUS current
			DESCRIPTION
				"Description."
			::= { sleBridgeBaseControl 24 }

		
		-- 1.3.6.1.4.1.6296.101.3.1.2.25
		sleBridgeControlLoopDetectStatus OBJECT-TYPE
			SYNTAX INTEGER
				{
				enable(1),
				disable(2)
				}
			MAX-ACCESS read-write
			STATUS current
			DESCRIPTION
				"Description."
			::= { sleBridgeBaseControl 25 }

		
		-- 1.3.6.1.4.1.6296.101.3.1.2.26
		sleBridgeControlLoopDetectPacketType OBJECT-TYPE
			SYNTAX INTEGER
				{
				laa(1),
				system(2)
				}
			MAX-ACCESS read-write
			STATUS current
			DESCRIPTION
				"Description."
			::= { sleBridgeBaseControl 26 }

		
		-- 1.3.6.1.4.1.6296.101.3.1.2.27
		sleBridgeControlPvlanPromSelectMode OBJECT-TYPE
			SYNTAX INTEGER
				{
				normal(0),
				manual(1),
				stp(2),
				erp(3)
				}
			MAX-ACCESS read-write
			STATUS current
			DESCRIPTION
				"Description."
			::= { sleBridgeBaseControl 27 }

		
		-- 1.3.6.1.4.1.6296.101.3.1.2.28
		sleBridgeControlPvlanPromiscuousPorts OBJECT-TYPE
			SYNTAX OCTET STRING
			MAX-ACCESS read-write
			STATUS current
			DESCRIPTION
				"Description."
			::= { sleBridgeBaseControl 28 }

		
--  1.3.6.1.4.1.6296.9.8.1.4
		-- 1.3.6.1.4.1.6296.101.3.1.3
		sleBridgeBaseNotification OBJECT IDENTIFIER ::= { sleBridgeBase 3 }

		
--  1.3.6.1.4.1.6296.9.8.1.4.1
		-- 1.3.6.1.4.1.6296.101.3.1.3.1
		sleBridgeLacpProfileChanged NOTIFICATION-TYPE
			OBJECTS { sleBridgeLacpActivity, sleBridgeLacpPriority, sleBridgeControlRequest, sleBridgeControlTimeStamp, sleBridgeControlReqResult
				 }
			STATUS current
			DESCRIPTION 
				" "
			::= { sleBridgeBaseNotification 1 }

		
--  1.3.6.1.4.1.6296.9.8.1.4.2
		-- 1.3.6.1.4.1.6296.101.3.1.3.2
		sleBridgeDoubleTagProtoIdChanged NOTIFICATION-TYPE
			OBJECTS { sleBridgeDoubleTagProtoId, sleBridgeControlRequest, sleBridgeControlTimeStamp, sleBridgeControlReqResult }
			STATUS current
			DESCRIPTION 
				" "
			::= { sleBridgeBaseNotification 2 }

		
--  1.3.6.1.4.1.6296.9.8.1.4.5
		-- 1.3.6.1.4.1.6296.101.3.1.3.3
		sleBridgeMirrorProfileChanged NOTIFICATION-TYPE
			OBJECTS { sleBridgeMirrorMode, sleBridgeMirrorMonitorPortId, sleBridgeControlRequest, sleBridgeControlTimeStamp, sleBridgeControlReqResult
				 }
			STATUS current
			DESCRIPTION 
				" "
			::= { sleBridgeBaseNotification 3 }

		
		-- 1.3.6.1.4.1.6296.101.3.1.3.4
		sleBridgeMaxLearnPerUnitChanged NOTIFICATION-TYPE
			OBJECTS { sleBridgeControlRequest, sleBridgeControlTimeStamp, sleBridgeControlReqResult, sleBridgeMaxLearnPerUnit }
			STATUS current
			DESCRIPTION 
				"Description."
			::= { sleBridgeBaseNotification 4 }

		
--  1.3.6.1.4.1.6296.9.8.1.4.6
		-- 1.3.6.1.4.1.6296.101.3.1.3.5
		sleBridgeFdbAgeingTimeChanged NOTIFICATION-TYPE
			OBJECTS { sleBridgeFdbAgeingTime, sleBridgeControlRequest, sleBridgeControlTimeStamp, sleBridgeControlReqResult }
			STATUS current
			DESCRIPTION 
				"Changed Fdb ageding time."
			::= { sleBridgeBaseNotification 5 }

		
--  1.3.6.1.4.1.6296.9.8.1.4.7
		-- 1.3.6.1.4.1.6296.101.3.1.3.6
		sleBridgeStackProfileChanged NOTIFICATION-TYPE
			OBJECTS { sleBridgeStackMode, sleBridgeStackDeviceName, sleBridgeControlRequest, sleBridgeControlTimeStamp, sleBridgeControlReqResult
				 }
			STATUS current
			DESCRIPTION 
				"Changed Stack device's profile."
			::= { sleBridgeBaseNotification 6 }

		
--  1.3.6.1.4.1.6296.9.8.1.4.8
		-- 1.3.6.1.4.1.6296.101.3.1.3.7
		sleBridgeLldpProfileChanged NOTIFICATION-TYPE
			OBJECTS { sleBridgeLldpMessageTxInterval, sleBridgeLldpTxHoldMultiplier, sleBridgeLldpReinitDelay, sleBridgeLldpTxDelay, sleBridgeLldpNotificationInterval, 
				sleBridgeControlRequest, sleBridgeControlTimeStamp, sleBridgeControlReqResult }
			STATUS current
			DESCRIPTION 
				" "
			::= { sleBridgeBaseNotification 7 }

		
--  1.3.6.1.4.1.6296.9.8.1.4.9
		-- 1.3.6.1.4.1.6296.101.3.1.3.8
		sleBridgeStpProfileChanged NOTIFICATION-TYPE
			OBJECTS { sleBridgeControlRequest, sleBridgeControlReqResult, sleBridgeControlTimeStamp, sleBridgeStpActivity, sleBridgeStpSelfLoop
				 }
			STATUS current
			DESCRIPTION 
				" "
			::= { sleBridgeBaseNotification 8 }

		
		-- 1.3.6.1.4.1.6296.101.3.1.3.9
		sleBridgeTcpSyncookieChanged NOTIFICATION-TYPE
			OBJECTS { sleBridgeControlRequest, sleBridgeControlTimeStamp, sleBridgeControlReqResult, sleBridgeTcpSyncookie }
			STATUS current
			DESCRIPTION 
				"Description."
			::= { sleBridgeBaseNotification 9 }

		
		-- 1.3.6.1.4.1.6296.101.3.1.3.10
		sleBridgeTcpIgnoreRstUnknownChanged NOTIFICATION-TYPE
			OBJECTS { sleBridgeControlRequest, sleBridgeControlTimeStamp, sleBridgeControlReqResult, sleBridgeTcpIgnoreRstUnknown }
			STATUS current
			DESCRIPTION 
				"Description."
			::= { sleBridgeBaseNotification 10 }

		
		-- 1.3.6.1.4.1.6296.101.3.1.3.11
		sleBridgeAutoInterfaceActivationChanged NOTIFICATION-TYPE
			OBJECTS { sleBridgeControlRequest, sleBridgeControlTimeStamp, sleBridgeControlReqResult, sleBridgeAutoInterfaceActivation }
			STATUS current
			DESCRIPTION 
				"Description."
			::= { sleBridgeBaseNotification 11 }

		
		-- 1.3.6.1.4.1.6296.101.3.1.3.12
		sleBridgeLoopDetectProfileChanged NOTIFICATION-TYPE
			OBJECTS { sleBridgeControlRequest, sleBridgeControlTimeStamp, sleBridgeControlReqResult, sleBridgeLoopDetectStatus, sleBridgeLoopDetectPacketType
				 }
			STATUS current
			DESCRIPTION 
				"Description."
			::= { sleBridgeBaseNotification 12 }

		
		-- 1.3.6.1.4.1.6296.101.3.1.3.13
		sleBridgePvlanPormSelectModeChanged NOTIFICATION-TYPE
			OBJECTS { sleBridgeControlRequest, sleBridgeControlTimeStamp, sleBridgeControlReqResult, sleBridgeControlPvlanPromSelectMode, sleBridgeControlPvlanPromiscuousPorts
				 }
			STATUS current
			DESCRIPTION 
				"Description."
			::= { sleBridgeBaseNotification 13 }

		
--  			::= { sle 4 }
-- 
-- Node definitions
-- 
-- 1.3.6.1.4.1.6296.9.8.2
		-- 1.3.6.1.4.1.6296.101.3.2
		sleBridgePort OBJECT IDENTIFIER ::= { sleBridge 2 }

		
--  1.3.6.1.4.1.6296.9.8.2.1
		-- 1.3.6.1.4.1.6296.101.3.2.1
		sleBridgePortTable OBJECT-TYPE
			SYNTAX SEQUENCE OF SleBridgePortEntry
			MAX-ACCESS not-accessible
			STATUS current
			DESCRIPTION
				"Bridge Port Table"
			::= { sleBridgePort 1 }

		
--  1.3.6.1.4.1.6296.9.8.2.1.1
		-- 1.3.6.1.4.1.6296.101.3.2.1.1
		sleBridgePortEntry OBJECT-TYPE
			SYNTAX SleBridgePortEntry
			MAX-ACCESS not-accessible
			STATUS current
			DESCRIPTION
				"Bridge Port Entry"
			INDEX { sleBridgePortIndex }
			::= { sleBridgePortTable 1 }

		
		SleBridgePortEntry ::=
			SEQUENCE { 
				sleBridgePortIndex
					INTEGER,
				sleBridgePortIfIndex
					INTEGER,
				sleBridgePortPVid
					INTEGER,
				sleBridgePortMaxHosts
					INTEGER,
				sleBridgePortCurrentHosts
					INTEGER,
				sleBridgePortMaxLearnPerUnit
					INTEGER,
				sleBridgePortMACFilterPermission
					INTEGER,
				sleBridgePortIngMirrorStatus
					INTEGER,
				sleBridgePortEgMirrorStatus
					INTEGER,
				sleBridgePortBcastThreshold
					INTEGER,
				sleBridgePortMcastThreshold
					INTEGER,
				sleBridgePortDlfThreshold
					INTEGER,
				sleBridgePortQinQStatus
					INTEGER,
				sleBridgePortAdminLinktype
					INTEGER,
				sleBridgePortAdminEdgemode
					INTEGER,
				sleBridgePortOperLinktype
					INTEGER,
				sleBridgePortOperEdgemode
					INTEGER,
				sleBridgePortStpBpduFilter
					INTEGER,
				sleBridgePortPvlanIsolatedStatus
					INTEGER,
				sleBridgePortPvlanPromPorts
					OCTET STRING,
				sleBridgePortDhcpFilterServer
					INTEGER,
				sleBridgePortLoopDetectStatus
					INTEGER,
				sleBridgePortLoopDetectBlock
					INTEGER,
				sleBridgePortLoopDetectPeriod
					INTEGER,
				sleBridgePortLoopDetectTimer
					INTEGER,
				sleBridgePortLoopDetectBlockStatus
					INTEGER,
				sleBridgePortNetBIOSFilter
					INTEGER,
				sleBridgePortPushInnertag
					INTEGER,
				sleBridgePortPopInnertag
					INTEGER,
				sleBridgePortInnertag
					INTEGER,
				sleBridgePortPriority
					INTEGER,
				sleBridgePortInner2outerPri
					INTEGER,
				sleBridgePortInner2outerVid
					INTEGER
			 }

--  1.3.6.1.4.1.6296.9.8.2.1.1.1
		-- 1.3.6.1.4.1.6296.101.3.2.1.1.1
		sleBridgePortIndex OBJECT-TYPE
			SYNTAX INTEGER (1..65535)
			MAX-ACCESS read-only
			STATUS current
			DESCRIPTION
				"Same as ifIndex (for all ifTable entries),
				additionally aggregation group index values available."
			::= { sleBridgePortEntry 1 }

		
--  1.3.6.1.4.1.6296.9.8.2.1.1.1
		-- 1.3.6.1.4.1.6296.101.3.2.1.1.2
		sleBridgePortIfIndex OBJECT-TYPE
			SYNTAX INTEGER (1..4094)
			MAX-ACCESS read-only
			STATUS current
			DESCRIPTION
				"Bridge Interface Index."
			::= { sleBridgePortEntry 2 }

		
--  1.3.6.1.4.1.6296.9.8.2.1.1.2
		-- 1.3.6.1.4.1.6296.101.3.2.1.1.3
		sleBridgePortPVid OBJECT-TYPE
			SYNTAX INTEGER (1..4094)
			MAX-ACCESS read-only
			STATUS current
			DESCRIPTION
				"The PVID of port. 
				Taken if no other rule given for VLAN association. 
				If aggregated: only for group."
			::= { sleBridgePortEntry 3 }

		
--  1.3.6.1.4.1.6296.9.8.2.1.1.3
		-- 1.3.6.1.4.1.6296.101.3.2.1.1.4
		sleBridgePortMaxHosts OBJECT-TYPE
			SYNTAX INTEGER (0..2147483647)
			MAX-ACCESS read-only
			STATUS current
			DESCRIPTION
				"The maximum number of hosts allowed. 
				Aggregation group available. Value 0 is allowed. 
				Default value is -1: it means unlimited. "
			::= { sleBridgePortEntry 4 }

		
--  1.3.6.1.4.1.6296.9.8.2.1.1.4
		-- 1.3.6.1.4.1.6296.101.3.2.1.1.5
		sleBridgePortCurrentHosts OBJECT-TYPE
			SYNTAX INTEGER (0..65535)
			MAX-ACCESS read-only
			STATUS current
			DESCRIPTION
				"The number hosts which is allowed to be used. 
				Aggregation group available."
			::= { sleBridgePortEntry 5 }

		
		-- 1.3.6.1.4.1.6296.101.3.2.1.1.6
		sleBridgePortMaxLearnPerUnit OBJECT-TYPE
			SYNTAX INTEGER (-1..2147483647)
			MAX-ACCESS read-only
			STATUS current
			DESCRIPTION
				"Limit maximum number of MAC addresses learning 
				newly per unit time(one second) on a port.
				(0: nothing learned, -l: unlimited.)"
			::= { sleBridgePortEntry 6 }

		
--  1.3.6.1.4.1.6296.9.8.2.1.1.5
		-- 1.3.6.1.4.1.6296.101.3.2.1.1.7
		sleBridgePortMACFilterPermission OBJECT-TYPE
			SYNTAX INTEGER
				{
				deny(0),
				permit(1)
				}
			MAX-ACCESS read-only
			STATUS current
			DESCRIPTION
				"The default permission for mac filtering. 
				Valid only for physical ports,
				use values from MFDB Table. "
			DEFVAL { 1 }
			::= { sleBridgePortEntry 7 }

		
--  1.3.6.1.4.1.6296.9.8.2.1.1.6
		-- 1.3.6.1.4.1.6296.101.3.2.1.1.8
		sleBridgePortIngMirrorStatus OBJECT-TYPE
			SYNTAX INTEGER
				{
				disable(0),
				enable(1)
				}
			MAX-ACCESS read-only
			STATUS current
			DESCRIPTION
				"Mirroring on ingress packets. 
				Valid only for physical ports. "
			DEFVAL { 0 }
			::= { sleBridgePortEntry 8 }

		
--  1.3.6.1.4.1.6296.9.8.2.1.1.7
		-- 1.3.6.1.4.1.6296.101.3.2.1.1.9
		sleBridgePortEgMirrorStatus OBJECT-TYPE
			SYNTAX INTEGER
				{
				disable(0),
				enable(1)
				}
			MAX-ACCESS read-only
			STATUS current
			DESCRIPTION
				"Mirroring on egress packets. 
				Valid only for physical ports. "
			DEFVAL { 0 }
			::= { sleBridgePortEntry 9 }

		
--  1.3.6.1.4.1.6296.9.8.2.1.1.8
		-- 1.3.6.1.4.1.6296.101.3.2.1.1.10
		sleBridgePortBcastThreshold OBJECT-TYPE
			SYNTAX INTEGER (0..2097150)
			MAX-ACCESS read-only
			STATUS current
			DESCRIPTION
				"Broadcast packet rate limit(unit: packets/s),
				Valid only for physical ports. 
				Default value is 0: it means BCSC clear-state.
				Value Range: 0-262142(TX/FX),0-2097150(GBIC)."
			DEFVAL { 0 }
			::= { sleBridgePortEntry 10 }

		
--  1.3.6.1.4.1.6296.9.8.2.1.1.9
		-- 1.3.6.1.4.1.6296.101.3.2.1.1.11
		sleBridgePortMcastThreshold OBJECT-TYPE
			SYNTAX INTEGER (0..2097150)
			MAX-ACCESS read-only
			STATUS current
			DESCRIPTION
				"Multicast packet rate limit.(unit: packets/s), 
				Valid only for physical ports. 
				Default value is 0: it means BCSC clear-state.
				Value Range: 0-262142(TX/FX),0-2097150(GBIC)."
			DEFVAL { 0 }
			::= { sleBridgePortEntry 11 }

		
--  1.3.6.1.4.1.6296.9.8.2.1.1.10
		-- 1.3.6.1.4.1.6296.101.3.2.1.1.12
		sleBridgePortDlfThreshold OBJECT-TYPE
			SYNTAX INTEGER (0..2097150)
			MAX-ACCESS read-only
			STATUS current
			DESCRIPTION
				"DLF packet rate limit(unit: packets/s), 
				Valid only for physical ports.
				Default value is 0: it means BCSC clear-state.
				Value Range: 0-262142(TX/FX),0-2097150(GBIC)."
			DEFVAL { 0 }
			::= { sleBridgePortEntry 12 }

		
--  1.3.6.1.4.1.6296.9.8.2.1.1.11
		-- 1.3.6.1.4.1.6296.101.3.2.1.1.13
		sleBridgePortQinQStatus OBJECT-TYPE
			SYNTAX INTEGER
				{
				disable(0),
				enable(1)
				}
			MAX-ACCESS read-only
			STATUS current
			DESCRIPTION
				"QinQ Status of the port. 
				Valid only for physical ports. "
			DEFVAL { 0 }
			::= { sleBridgePortEntry 13 }

		
--  1.3.6.1.4.1.6296.9.8.2.1.1.12
		-- 1.3.6.1.4.1.6296.101.3.2.1.1.14
		sleBridgePortAdminLinktype OBJECT-TYPE
			SYNTAX INTEGER
				{
				shared(0),
				pointTopoint(1),
				automatic(2)
				}
			MAX-ACCESS read-only
			STATUS current
			DESCRIPTION
				"The administrative link-type of port on the xSTP."
			DEFVAL { 2 }
			::= { sleBridgePortEntry 14 }

		
--  1.3.6.1.4.1.6296.9.8.2.1.1.13
		-- 1.3.6.1.4.1.6296.101.3.2.1.1.15
		sleBridgePortAdminEdgemode OBJECT-TYPE
			SYNTAX INTEGER
				{
				disable(0),
				enable(1)
				}
			MAX-ACCESS read-only
			STATUS current
			DESCRIPTION
				"The administrative edgemode of port on the xSTP."
			DEFVAL { 0 }
			::= { sleBridgePortEntry 15 }

		
--  1.3.6.1.4.1.6296.9.8.2.1.1.14
		-- 1.3.6.1.4.1.6296.101.3.2.1.1.16
		sleBridgePortOperLinktype OBJECT-TYPE
			SYNTAX INTEGER
				{
				shared(0),
				pointTopoint(1)
				}
			MAX-ACCESS read-only
			STATUS current
			DESCRIPTION
				"The link-type of the port on the xSTP."
			::= { sleBridgePortEntry 16 }

		
--  1.3.6.1.4.1.6296.9.8.2.1.1.15
		-- 1.3.6.1.4.1.6296.101.3.2.1.1.17
		sleBridgePortOperEdgemode OBJECT-TYPE
			SYNTAX INTEGER
				{
				disabled(0),
				enabled(1)
				}
			MAX-ACCESS read-only
			STATUS current
			DESCRIPTION
				"The edge-mode of the port on the xSTP."
			::= { sleBridgePortEntry 17 }

		
		-- 1.3.6.1.4.1.6296.101.3.2.1.1.18
		sleBridgePortStpBpduFilter OBJECT-TYPE
			SYNTAX INTEGER
				{
				disable(0),
				enable(1)
				}
			MAX-ACCESS read-only
			STATUS current
			DESCRIPTION
				"Description."
			::= { sleBridgePortEntry 18 }

		
		-- 1.3.6.1.4.1.6296.101.3.2.1.1.19
		sleBridgePortPvlanIsolatedStatus OBJECT-TYPE
			SYNTAX INTEGER
				{
				disable(0),
				enable(1)
				}
			MAX-ACCESS read-only
			STATUS current
			DESCRIPTION
				"Description."
			DEFVAL { 0 }
			::= { sleBridgePortEntry 19 }

		
		-- 1.3.6.1.4.1.6296.101.3.2.1.1.20
		sleBridgePortPvlanPromPorts OBJECT-TYPE
			SYNTAX OCTET STRING
			MAX-ACCESS read-only
			STATUS current
			DESCRIPTION
				"Description."
			::= { sleBridgePortEntry 20 }

		
		-- 1.3.6.1.4.1.6296.101.3.2.1.1.21
		sleBridgePortDhcpFilterServer OBJECT-TYPE
			SYNTAX INTEGER
				{
				disable(0),
				enable(1)
				}
			MAX-ACCESS read-only
			STATUS current
			DESCRIPTION
				"Description."
			::= { sleBridgePortEntry 21 }

		
		-- 1.3.6.1.4.1.6296.101.3.2.1.1.22
		sleBridgePortLoopDetectStatus OBJECT-TYPE
			SYNTAX INTEGER
				{
				enable(1),
				disable(2)
				}
			MAX-ACCESS read-only
			STATUS current
			DESCRIPTION
				"Description."
			::= { sleBridgePortEntry 22 }

		
		-- 1.3.6.1.4.1.6296.101.3.2.1.1.23
		sleBridgePortLoopDetectBlock OBJECT-TYPE
			SYNTAX INTEGER
				{
				enable(1),
				disable(2)
				}
			MAX-ACCESS read-only
			STATUS current
			DESCRIPTION
				"Description."
			::= { sleBridgePortEntry 23 }

		
		-- 1.3.6.1.4.1.6296.101.3.2.1.1.24
		sleBridgePortLoopDetectPeriod OBJECT-TYPE
			SYNTAX INTEGER (1..60)
			MAX-ACCESS read-only
			STATUS current
			DESCRIPTION
				"Description."
			::= { sleBridgePortEntry 24 }

		
		-- 1.3.6.1.4.1.6296.101.3.2.1.1.25
		sleBridgePortLoopDetectTimer OBJECT-TYPE
			SYNTAX INTEGER (0 | 1..86400)
			MAX-ACCESS read-only
			STATUS current
			DESCRIPTION
				"Description."
			::= { sleBridgePortEntry 25 }

		
		-- 1.3.6.1.4.1.6296.101.3.2.1.1.26
		sleBridgePortLoopDetectBlockStatus OBJECT-TYPE
			SYNTAX INTEGER
				{
				block(1),
				unblock(2)
				}
			MAX-ACCESS read-only
			STATUS current
			DESCRIPTION
				"Description."
			::= { sleBridgePortEntry 26 }

		
		-- 1.3.6.1.4.1.6296.101.3.2.1.1.27
		sleBridgePortNetBIOSFilter OBJECT-TYPE
			SYNTAX INTEGER
				{
				disable(0),
				enable(1)
				}
			MAX-ACCESS read-only
			STATUS current
			DESCRIPTION
				"Description."
			::= { sleBridgePortEntry 27 }

		
		-- 1.3.6.1.4.1.6296.101.3.2.1.1.28
		sleBridgePortPushInnertag OBJECT-TYPE
			SYNTAX INTEGER
				{
				disable(0),
				enable(1)
				}
			MAX-ACCESS read-write
			STATUS current
			DESCRIPTION
				"The ingress port that push inner-tag"
			::= { sleBridgePortEntry 28 }

		
		-- 1.3.6.1.4.1.6296.101.3.2.1.1.29
		sleBridgePortPopInnertag OBJECT-TYPE
			SYNTAX INTEGER
				{
				disable(0),
				enable(1)
				}
			MAX-ACCESS read-write
			STATUS current
			DESCRIPTION
				"The egress port that pop inner-tag"
			::= { sleBridgePortEntry 29 }

		
		-- 1.3.6.1.4.1.6296.101.3.2.1.1.30
		sleBridgePortInnertag OBJECT-TYPE
			SYNTAX INTEGER
			MAX-ACCESS read-write
			STATUS current
			DESCRIPTION
				"The inner-tag value to push for incoming untagged packet"
			::= { sleBridgePortEntry 30 }

		
		-- 1.3.6.1.4.1.6296.101.3.2.1.1.31
		sleBridgePortPriority OBJECT-TYPE
			SYNTAX INTEGER (0..7)
			MAX-ACCESS read-write
			STATUS current
			DESCRIPTION
				"The port priority value for incoming untagged packet"
			::= { sleBridgePortEntry 31 }

		
		-- 1.3.6.1.4.1.6296.101.3.2.1.1.32
		sleBridgePortInner2outerPri OBJECT-TYPE
			SYNTAX INTEGER
				{
				disable(0),
				enable(1)
				}
			MAX-ACCESS read-write
			STATUS current
			DESCRIPTION
				"Use inner-tag’s priority as outer-tag’s priority."
			::= { sleBridgePortEntry 32 }

		
		-- 1.3.6.1.4.1.6296.101.3.2.1.1.33
		sleBridgePortInner2outerVid OBJECT-TYPE
			SYNTAX INTEGER
				{
				disable(0),
				enable(1)
				}
			MAX-ACCESS read-write
			STATUS current
			DESCRIPTION
				"Use inner-tag’s vlan-id as outer-tag’s vlan-id."
			::= { sleBridgePortEntry 33 }

		
--   Node definitions
-- 
-- 1.3.6.1.4.1.6296.9.8.2.2
		-- 1.3.6.1.4.1.6296.101.3.2.2
		sleBridgePortControl OBJECT IDENTIFIER ::= { sleBridgePort 2 }

		
--  1.3.6.1.4.1.6296.9.8.2.2.1
		-- 1.3.6.1.4.1.6296.101.3.2.2.1
		sleBridgePortControlRequest OBJECT-TYPE
			SYNTAX INTEGER
				{
				setBridgePortPVid(1),
				setBridgePortMaxHosts(2),
				setBridgePortMaxLearnPerUnit(3),
				setBridgePortMACFilterPermission(4),
				setBridgePortMirrorProfile(5),
				setBridgePortBcscThresholdProfile(6),
				setBridgePortQinQStatus(7),
				setBridgePortLinktype(8),
				setBridgePortEdgemode(9),
				setBridgePortStpBpduFilter(10),
				setBridgePortIsolatedStatus(11),
				setBridgePortStpBpduGuardErrRcv(12),
				setBridgePortDhcpFilterServer(13),
				setBridgePortLoopDetectProfile(14),
				setBridgePortLoopDetectUnblock(15),
				setBridgePortNetBIOSFilter(16),
				setBridgePortPushInnertag(17),
				setBridgePortPopInnertag(18),
				setBridgePortInnertag(19),
				setBridgePortPriority(20),
				setBridgePortInner2outerPri(21),
				setBridgePortInner2outerVid(22)
				}
			MAX-ACCESS read-write
			STATUS current
			DESCRIPTION
				"
				setBridgePortPVid:
				sleBridgePortControlIndex
				sleBridgePortControlPVid
				
				setBridgePortMaxHosts:
				sleBridgePortControlIndex
				sleBridgePortControlMaxHosts
				
				setBridgePortMACFilterPermission:
				sleBridgePortControlIndex
				sleBridgePortControlMACFilterPermission
				
				setBridgePortMirrorProfile:
				sleBridgePortControlIndex
				sleBridgePortControlIngMirrorStatus
				sleBridgePortControlEgMirrorStatus
				            
				setBridgePortBcscThresholdProfile:
				sleBridgePortControlIndex
				sleBridgePortControlBcastThreshold
				sleBridgePortControlMcastThreshold
				sleBridgePortControlDlfThreshold
				            
				setBridgePortQinQStatus:
				sleBridgePortControlIndex
				sleBridgePortControlQinQStatus
				            
				setBridgePortLinktype:
				sleBridgePortControlIndex
				sleBridgePortControlAdminLinktype
				            
				setBridgePortEdgemode:
				sleBridgePortControlIndex
				sleBridgePortControlAdminEdgemode
				
				setBridgePortNetBIOSFilter:
				sleBridgePortControlIndex
				sleBridgePortControlNetBIOSFilter
				"
			::= { sleBridgePortControl 1 }

		
--  1.3.6.1.4.1.6296.9.8.2.2.3
		-- 1.3.6.1.4.1.6296.101.3.2.2.2
		sleBridgePortControlStatus OBJECT-TYPE
			SYNTAX SleControlStatusType
			MAX-ACCESS read-only
			STATUS current
			DESCRIPTION
				"The status of a user command."
			::= { sleBridgePortControl 2 }

		
--  1.3.6.1.4.1.6296.9.8.2.2.4
		-- 1.3.6.1.4.1.6296.101.3.2.2.3
		sleBridgePortControlTimer OBJECT-TYPE
			SYNTAX Gauge32
			MAX-ACCESS read-write
			STATUS current
			DESCRIPTION
				"The maximum wait time for the manager for a long running user command."
			::= { sleBridgePortControl 3 }

		
--  1.3.6.1.4.1.6296.9.8.2.2.6
		-- 1.3.6.1.4.1.6296.101.3.2.2.4
		sleBridgePortControlTimeStamp OBJECT-TYPE
			SYNTAX TimeTicks
			MAX-ACCESS read-only
			STATUS current
			DESCRIPTION
				"The time stamp of the last command (end of command)."
			::= { sleBridgePortControl 4 }

		
--  1.3.6.1.4.1.6296.9.8.2.2.5
		-- 1.3.6.1.4.1.6296.101.3.2.2.5
		sleBridgePortControlReqResult OBJECT-TYPE
			SYNTAX SleControlRequestResultType
			MAX-ACCESS read-only
			STATUS current
			DESCRIPTION
				"The result of the last user command."
			::= { sleBridgePortControl 5 }

		
--  1.3.6.1.4.1.6296.9.8.2.2.2
		-- 1.3.6.1.4.1.6296.101.3.2.2.6
		sleBridgePortControlIndex OBJECT-TYPE
			SYNTAX INTEGER (1..255)
			MAX-ACCESS read-write
			STATUS current
			DESCRIPTION
				"sleBridgePortIndex"
			::= { sleBridgePortControl 6 }

		
--  1.3.6.1.4.1.6296.9.8.2.2.7
		-- 1.3.6.1.4.1.6296.101.3.2.2.7
		sleBridgePortControlPVid OBJECT-TYPE
			SYNTAX INTEGER (1..4094)
			MAX-ACCESS read-write
			STATUS current
			DESCRIPTION
				"The PVID of port. 
				Taken if no other rule given for VLAN association. 
				If aggregated: only for group."
			::= { sleBridgePortControl 7 }

		
--  1.3.6.1.4.1.6296.9.8.2.2.8
		-- 1.3.6.1.4.1.6296.101.3.2.2.8
		sleBridgePortControlMaxHosts OBJECT-TYPE
			SYNTAX INTEGER (-1..2147483647)
			MAX-ACCESS read-write
			STATUS current
			DESCRIPTION
				"The maximum number of hosts allowed. 
				Aggregation group available. Value 0 is allowed,
				Value -1 is used to clear."
			DEFVAL { -1 }
			::= { sleBridgePortControl 8 }

		
		-- 1.3.6.1.4.1.6296.101.3.2.2.9
		sleBridgePortControlMaxLearnPerUnit OBJECT-TYPE
			SYNTAX INTEGER (-1..2147483647)
			MAX-ACCESS read-write
			STATUS current
			DESCRIPTION
				"Description."
			::= { sleBridgePortControl 9 }

		
--  1.3.6.1.4.1.6296.9.8.2.2.9
		-- 1.3.6.1.4.1.6296.101.3.2.2.10
		sleBridgePortControlMACFilterPermission OBJECT-TYPE
			SYNTAX INTEGER
				{
				deny(0),
				permit(1)
				}
			MAX-ACCESS read-write
			STATUS current
			DESCRIPTION
				"The default permission for mac filtering. 
				Valid only for physical ports, 
				use values from MFDB  Table."
			DEFVAL { 1 }
			::= { sleBridgePortControl 10 }

		
--  1.3.6.1.4.1.6296.9.8.2.2.10
		-- 1.3.6.1.4.1.6296.101.3.2.2.11
		sleBridgePortControlIngMirrorStatus OBJECT-TYPE
			SYNTAX INTEGER
				{
				disable(0),
				enable(1)
				}
			MAX-ACCESS read-write
			STATUS current
			DESCRIPTION
				"Mirroring on ingress packets. 
				Valid only for physical ports. "
			DEFVAL { 0 }
			::= { sleBridgePortControl 11 }

		
--  1.3.6.1.4.1.6296.9.8.2.2.11
		-- 1.3.6.1.4.1.6296.101.3.2.2.12
		sleBridgePortControlEgMirrorStatus OBJECT-TYPE
			SYNTAX INTEGER
				{
				disable(0),
				enable(1)
				}
			MAX-ACCESS read-write
			STATUS current
			DESCRIPTION
				"Mirroring on egress packets. 
				Valid only for physical ports. "
			DEFVAL { 0 }
			::= { sleBridgePortControl 12 }

		
--  1.3.6.1.4.1.6296.9.8.2.2.12
		-- 1.3.6.1.4.1.6296.101.3.2.2.13
		sleBridgePortControlBcastThreshold OBJECT-TYPE
			SYNTAX INTEGER (0..2097150)
			MAX-ACCESS read-write
			STATUS current
			DESCRIPTION
				"Broadcast packet rate limit (unit: packets/s), 
				Valid only for physical ports. Value 0 is used to clear.
				Value Range: 0-262142(TX/FX),0-2097150(GBIC)."
			DEFVAL { 0 }
			::= { sleBridgePortControl 13 }

		
--  1.3.6.1.4.1.6296.9.8.2.2.13
		-- 1.3.6.1.4.1.6296.101.3.2.2.14
		sleBridgePortControlMcastThreshold OBJECT-TYPE
			SYNTAX INTEGER (0..2097150)
			MAX-ACCESS read-write
			STATUS current
			DESCRIPTION
				"Multicast packet rate limit (unit: packets/s), 
				Valid only for physical ports. Value 0 is used to clear.
				Value Range: 0-262142(TX/FX),0-2097150(GBIC)."
			DEFVAL { 0 }
			::= { sleBridgePortControl 14 }

		
--  1.3.6.1.4.1.6296.9.8.2.2.14
		-- 1.3.6.1.4.1.6296.101.3.2.2.15
		sleBridgePortControlDlfThreshold OBJECT-TYPE
			SYNTAX INTEGER (0..2097150)
			MAX-ACCESS read-write
			STATUS current
			DESCRIPTION
				"DLF packet rate limit (unit: packets/s), 
				Valid only for physical ports. Value 0 is used to clear.
				Value Range: 0-262142(TX/FX),0-2097150(GBIC)."
			DEFVAL { 0 }
			::= { sleBridgePortControl 15 }

		
--  1.3.6.1.4.1.6296.9.8.2.2.15
		-- 1.3.6.1.4.1.6296.101.3.2.2.16
		sleBridgePortControlQinQStatus OBJECT-TYPE
			SYNTAX INTEGER
				{
				disable(0),
				enable(1)
				}
			MAX-ACCESS read-write
			STATUS current
			DESCRIPTION
				"QinQ Status of the port. 
				Valid only for physical ports. "
			DEFVAL { 0 }
			::= { sleBridgePortControl 16 }

		
--  1.3.6.1.4.1.6296.9.8.2.2.16
		-- 1.3.6.1.4.1.6296.101.3.2.2.17
		sleBridgePortControlAdminLinktype OBJECT-TYPE
			SYNTAX INTEGER
				{
				shared(0),
				pointTopoint(1),
				automatic(2)
				}
			MAX-ACCESS read-write
			STATUS current
			DESCRIPTION
				"The administrative link-type of port on the xSTP. "
			DEFVAL { 2 }
			::= { sleBridgePortControl 17 }

		
--  1.3.6.1.4.1.6296.9.8.2.2.17
		-- 1.3.6.1.4.1.6296.101.3.2.2.18
		sleBridgePortControlAdminEdgemode OBJECT-TYPE
			SYNTAX INTEGER
				{
				disable(0),
				enable(1)
				}
			MAX-ACCESS read-write
			STATUS current
			DESCRIPTION
				"The administrative edgemode of port on the xSTP. "
			DEFVAL { 0 }
			::= { sleBridgePortControl 18 }

		
		-- 1.3.6.1.4.1.6296.101.3.2.2.19
		sleBridgePortControlStpBpduFilter OBJECT-TYPE
			SYNTAX INTEGER
				{
				disable(0),
				enable(1)
				}
			MAX-ACCESS read-write
			STATUS current
			DESCRIPTION
				"Description."
			DEFVAL { 0 }
			::= { sleBridgePortControl 19 }

		
		-- 1.3.6.1.4.1.6296.101.3.2.2.20
		sleBridgePortControlPvlanIsolatedStatus OBJECT-TYPE
			SYNTAX INTEGER
				{
				disable(0),
				enable(1)
				}
			MAX-ACCESS read-write
			STATUS current
			DESCRIPTION
				"Description."
			DEFVAL { 0 }
			::= { sleBridgePortControl 20 }

		
		-- 1.3.6.1.4.1.6296.101.3.2.2.21
		sleBridgePortControlPvlanPromPort OBJECT-TYPE
			SYNTAX INTEGER (1..65535)
			MAX-ACCESS read-write
			STATUS current
			DESCRIPTION
				"Description."
			::= { sleBridgePortControl 21 }

		
		-- 1.3.6.1.4.1.6296.101.3.2.2.22
		sleBridgePortControlStpBpduGuardErrRcv OBJECT-TYPE
			SYNTAX TruthValue
			MAX-ACCESS read-write
			STATUS current
			DESCRIPTION
				"Trigger manual recovery for the port disabled by Bpdu Guard.
				 false : sustain current state.
				 true  : trigger recovery."
			DEFVAL { false }
			::= { sleBridgePortControl 22 }

		
		-- 1.3.6.1.4.1.6296.101.3.2.2.23
		sleBridgePortControlDhcpFilterServer OBJECT-TYPE
			SYNTAX INTEGER
				{
				disable(0),
				enable(1)
				}
			MAX-ACCESS read-write
			STATUS current
			DESCRIPTION
				"Description."
			::= { sleBridgePortControl 23 }

		
		-- 1.3.6.1.4.1.6296.101.3.2.2.24
		sleBridgePortControlLoopDetectStatus OBJECT-TYPE
			SYNTAX INTEGER
				{
				enable(1),
				disable(2)
				}
			MAX-ACCESS read-write
			STATUS current
			DESCRIPTION
				"Description."
			::= { sleBridgePortControl 24 }

		
		-- 1.3.6.1.4.1.6296.101.3.2.2.25
		sleBridgePortControlLoopDetectBlock OBJECT-TYPE
			SYNTAX INTEGER
				{
				enable(1),
				disable(2)
				}
			MAX-ACCESS read-only
			STATUS current
			DESCRIPTION
				"Description."
			::= { sleBridgePortControl 25 }

		
		-- 1.3.6.1.4.1.6296.101.3.2.2.26
		sleBridgePortControlLoopDetectPeriod OBJECT-TYPE
			SYNTAX INTEGER (1..60)
			MAX-ACCESS read-write
			STATUS current
			DESCRIPTION
				"Description."
			::= { sleBridgePortControl 26 }

		
		-- 1.3.6.1.4.1.6296.101.3.2.2.27
		sleBridgePortControlLoopDetectTimer OBJECT-TYPE
			SYNTAX INTEGER (0 | 1..86400)
			MAX-ACCESS read-write
			STATUS current
			DESCRIPTION
				"Description."
			::= { sleBridgePortControl 27 }

		
		-- 1.3.6.1.4.1.6296.101.3.2.2.28
		sleBridgePortControlNetBIOSFilter OBJECT-TYPE
			SYNTAX INTEGER
				{
				disable(0),
				enable(1)
				}
			MAX-ACCESS read-write
			STATUS current
			DESCRIPTION
				"Description."
			::= { sleBridgePortControl 28 }

		
		-- 1.3.6.1.4.1.6296.101.3.2.2.29
		sleBridgePortControlPushInnertag OBJECT-TYPE
			SYNTAX INTEGER
				{
				disable(0),
				enable(1)
				}
			MAX-ACCESS read-write
			STATUS current
			DESCRIPTION
				"Push inner-tag for incoming untagged packet."
			::= { sleBridgePortControl 29 }

		
		-- 1.3.6.1.4.1.6296.101.3.2.2.30
		sleBridgePortControlPopInnertag OBJECT-TYPE
			SYNTAX INTEGER
				{
				disable(0),
				enable(1)
				}
			MAX-ACCESS read-write
			STATUS current
			DESCRIPTION
				"Pop inner-tag for double tagged packet."
			::= { sleBridgePortControl 30 }

		
		-- 1.3.6.1.4.1.6296.101.3.2.2.31
		sleBridgePortControlInnertag OBJECT-TYPE
			SYNTAX INTEGER
			MAX-ACCESS read-write
			STATUS current
			DESCRIPTION
				"Inner-tag value to push for incoming untagged packet."
			::= { sleBridgePortControl 31 }

		
		-- 1.3.6.1.4.1.6296.101.3.2.2.32
		sleBridgePortControlPriority OBJECT-TYPE
			SYNTAX INTEGER (0..7)
			MAX-ACCESS read-write
			STATUS current
			DESCRIPTION
				"The priority value per port.
				Assign priority for untagged packet from port.
				"
			::= { sleBridgePortControl 32 }

		
		-- 1.3.6.1.4.1.6296.101.3.2.2.33
		sleBridgePortControlInner2outerPri OBJECT-TYPE
			SYNTAX INTEGER
				{
				disable(0),
				enable(1)
				}
			MAX-ACCESS read-write
			STATUS current
			DESCRIPTION
				"If enable, use inner-tag's priority as outer-tag's priority.
				Otherwise, use outer-tag's priority"
			::= { sleBridgePortControl 33 }

		
		-- 1.3.6.1.4.1.6296.101.3.2.2.34
		sleBridgePortControlInner2outerVid OBJECT-TYPE
			SYNTAX INTEGER
				{
				disable(0),
				enable(1)
				}
			MAX-ACCESS read-write
			STATUS current
			DESCRIPTION
				"If enable, use inner-tag's vlan-id as outer-tag's vlan-id.
				Otherwise, use outer-tag's vlan-id"
			::= { sleBridgePortControl 34 }

		
--   Node definitions
-- 
-- 1.3.6.1.4.1.6296.9.8.2.3
		-- 1.3.6.1.4.1.6296.101.3.2.3
		sleBridgePortNotification OBJECT IDENTIFIER ::= { sleBridgePort 3 }

		
--  1.3.6.1.4.1.6296.9.8.2.3.1
		-- 1.3.6.1.4.1.6296.101.3.2.3.1
		sleBridgePortPVidChanged NOTIFICATION-TYPE
			OBJECTS { sleBridgePortPVid, sleBridgePortControlRequest, sleBridgePortControlTimeStamp, sleBridgePortControlReqResult }
			STATUS current
			DESCRIPTION 
				"PVid changed"
			::= { sleBridgePortNotification 1 }

		
--  1.3.6.1.4.1.6296.9.8.2.3.2
		-- 1.3.6.1.4.1.6296.101.3.2.3.2
		sleBridgePortMaxHostsChanged NOTIFICATION-TYPE
			OBJECTS { sleBridgePortMaxHosts, sleBridgePortControlRequest, sleBridgePortControlTimeStamp, sleBridgePortControlReqResult }
			STATUS current
			DESCRIPTION 
				"MaxHosts changed"
			::= { sleBridgePortNotification 2 }

		
		-- 1.3.6.1.4.1.6296.101.3.2.3.3
		sleBridgePortMaxLearnPerUnitChanged NOTIFICATION-TYPE
			OBJECTS { sleBridgePortControlRequest, sleBridgePortControlTimeStamp, sleBridgePortControlReqResult, sleBridgePortMaxLearnPerUnit }
			STATUS current
			DESCRIPTION 
				"Description."
			::= { sleBridgePortNotification 3 }

		
--  1.3.6.1.4.1.6296.9.8.2.3.3
		-- 1.3.6.1.4.1.6296.101.3.2.3.4
		sleBridgePortMACFilterPermissionChanged NOTIFICATION-TYPE
			OBJECTS { sleBridgePortMACFilterPermission, sleBridgePortControlRequest, sleBridgePortControlTimeStamp, sleBridgePortControlReqResult }
			STATUS current
			DESCRIPTION 
				"MAC filter permission changed"
			::= { sleBridgePortNotification 4 }

		
--  1.3.6.1.4.1.6296.9.8.2.3.4
		-- 1.3.6.1.4.1.6296.101.3.2.3.5
		sleBridgePortMirrorProfileChanged NOTIFICATION-TYPE
			OBJECTS { sleBridgePortIngMirrorStatus, sleBridgePortEgMirrorStatus, sleBridgePortControlRequest, sleBridgePortControlTimeStamp, sleBridgePortControlReqResult
				 }
			STATUS current
			DESCRIPTION 
				"Mirror profile changed"
			::= { sleBridgePortNotification 5 }

		
--  1.3.6.1.4.1.6296.9.8.2.3.5
		-- 1.3.6.1.4.1.6296.101.3.2.3.6
		sleBridgePortBcscThresholdProfileChanged NOTIFICATION-TYPE
			OBJECTS { sleBridgePortBcastThreshold, sleBridgePortMcastThreshold, sleBridgePortDlfThreshold, sleBridgePortControlRequest, sleBridgePortControlTimeStamp, 
				sleBridgePortControlReqResult }
			STATUS current
			DESCRIPTION 
				"BCSC threshold profile changed"
			::= { sleBridgePortNotification 6 }

		
--  1.3.6.1.4.1.6296.9.8.2.3.6
		-- 1.3.6.1.4.1.6296.101.3.2.3.7
		sleBridgePortQinQStatusChanged NOTIFICATION-TYPE
			OBJECTS { sleBridgePortQinQStatus, sleBridgePortControlRequest, sleBridgePortControlTimeStamp, sleBridgePortControlReqResult }
			STATUS current
			DESCRIPTION 
				"QinQ status changed"
			::= { sleBridgePortNotification 7 }

		
--  1.3.6.1.4.1.6296.9.8.2.3.7
		-- 1.3.6.1.4.1.6296.101.3.2.3.8
		sleBridgePortLinktypeChanged NOTIFICATION-TYPE
			OBJECTS { sleBridgePortAdminLinktype, sleBridgePortControlRequest, sleBridgePortControlTimeStamp, sleBridgePortControlReqResult }
			STATUS current
			DESCRIPTION 
				"Admin link-type changed"
			::= { sleBridgePortNotification 8 }

		
--  1.3.6.1.4.1.6296.9.8.2.3.8
		-- 1.3.6.1.4.1.6296.101.3.2.3.9
		sleBridgePortEdgemodeChanged NOTIFICATION-TYPE
			OBJECTS { sleBridgePortAdminEdgemode, sleBridgePortControlRequest, sleBridgePortControlTimeStamp, sleBridgePortControlReqResult }
			STATUS current
			DESCRIPTION 
				"Admin edge-mode changed"
			::= { sleBridgePortNotification 9 }

		
		-- 1.3.6.1.4.1.6296.101.3.2.3.10
		sleBridgePortStpBpduFilterChanged NOTIFICATION-TYPE
			OBJECTS { sleBridgePortStpBpduFilter, sleBridgePortControlTimeStamp, sleBridgePortControlReqResult, sleBridgePortControlRequest }
			STATUS current
			DESCRIPTION 
				"Description."
			::= { sleBridgePortNotification 10 }

		
		-- 1.3.6.1.4.1.6296.101.3.2.3.11
		sleBridgePortPvlanIsolatedStatusChanged NOTIFICATION-TYPE
			OBJECTS { sleBridgePortPvlanIsolatedStatus, sleBridgePortPvlanPromPorts, sleBridgePortControlRequest, sleBridgePortControlTimeStamp, sleBridgePortControlReqResult
				 }
			STATUS current
			DESCRIPTION 
				"Description."
			::= { sleBridgePortNotification 11 }

		
		-- 1.3.6.1.4.1.6296.101.3.2.3.12
		sleBridgePortStpBpduGuardErrRcvChanged NOTIFICATION-TYPE
			OBJECTS { sleBridgePortControlRequest, sleBridgePortControlTimeStamp, sleBridgePortControlReqResult }
			STATUS current
			DESCRIPTION 
				"Description."
			::= { sleBridgePortNotification 12 }

		
		-- 1.3.6.1.4.1.6296.101.3.2.3.13
		sleBridgePortDhcpFilterServerChanged NOTIFICATION-TYPE
			OBJECTS { sleBridgePortControlRequest, sleBridgePortControlTimeStamp, sleBridgePortControlReqResult, sleBridgePortDhcpFilterServer }
			STATUS current
			DESCRIPTION 
				"Description."
			::= { sleBridgePortNotification 13 }

		
		-- 1.3.6.1.4.1.6296.101.3.2.3.14
		sleBridgePortLoopDetectProfileChanged NOTIFICATION-TYPE
			OBJECTS { sleBridgePortControlRequest, sleBridgePortControlTimeStamp, sleBridgePortControlReqResult, sleBridgePortLoopDetectStatus, sleBridgePortLoopDetectBlock, 
				sleBridgePortLoopDetectPeriod, sleBridgePortLoopDetectTimer }
			STATUS current
			DESCRIPTION 
				"Description."
			::= { sleBridgePortNotification 14 }

		
		-- 1.3.6.1.4.1.6296.101.3.2.3.15
		sleBridgePortLoopDetectUnblock NOTIFICATION-TYPE
			OBJECTS { sleBridgePortControlRequest, sleBridgePortControlTimeStamp, sleBridgePortControlReqResult, sleBridgePortLoopDetectBlockStatus }
			STATUS current
			DESCRIPTION 
				"Description."
			::= { sleBridgePortNotification 15 }

		
		-- 1.3.6.1.4.1.6296.101.3.2.3.16
		sleBridgePortNetBIOSFilterChanged NOTIFICATION-TYPE
			OBJECTS { sleBridgePortControlRequest, sleBridgePortControlTimeStamp, sleBridgePortControlReqResult, sleBridgePortNetBIOSFilter }
			STATUS current
			DESCRIPTION 
				"Description."
			::= { sleBridgePortNotification 16 }

		
		-- 1.3.6.1.4.1.6296.101.3.2.3.17
		sleBridgePortPushInnertagChanged NOTIFICATION-TYPE
			OBJECTS { sleBridgePortControlRequest, sleBridgePortControlReqResult, sleBridgePortControlTimeStamp, sleBridgePortControlIndex, sleBridgePortControlPushInnertag
				 }
			STATUS current
			DESCRIPTION 
				"setBridgePortPushInnertag"
			::= { sleBridgePortNotification 17 }

		
		-- 1.3.6.1.4.1.6296.101.3.2.3.18
		sleBridgePortPopInnertagChanged NOTIFICATION-TYPE
			OBJECTS { sleBridgePortControlRequest, sleBridgePortControlReqResult, sleBridgePortControlTimeStamp, sleBridgePortControlIndex, sleBridgePortControlPopInnertag
				 }
			STATUS current
			DESCRIPTION 
				"setBridgePortPopInnertag"
			::= { sleBridgePortNotification 18 }

		
		-- 1.3.6.1.4.1.6296.101.3.2.3.19
		sleBridgePortInnertagChanged NOTIFICATION-TYPE
			OBJECTS { sleBridgePortControlRequest, sleBridgePortControlReqResult, sleBridgePortControlTimeStamp, sleBridgePortControlIndex, sleBridgePortControlInnertag
				 }
			STATUS current
			DESCRIPTION 
				"setBridgePortInnertag"
			::= { sleBridgePortNotification 19 }

		
		-- 1.3.6.1.4.1.6296.101.3.2.3.20
		sleBridgePortPriorityChanged NOTIFICATION-TYPE
			OBJECTS { sleBridgePortControlRequest, sleBridgePortControlReqResult, sleBridgePortControlTimeStamp, sleBridgePortControlIndex, sleBridgePortControlPriority
				 }
			STATUS current
			DESCRIPTION 
				"setBridgePortPriority"
			::= { sleBridgePortNotification 20 }

		
		-- 1.3.6.1.4.1.6296.101.3.2.3.21
		sleBridgePortInner2outerPriChanged NOTIFICATION-TYPE
			OBJECTS { sleBridgePortControlRequest, sleBridgePortControlReqResult, sleBridgePortControlTimeStamp, sleBridgePortControlIndex, sleBridgePortControlInner2outerPri
				 }
			STATUS current
			DESCRIPTION 
				"setBridgePortInner2outerPri"
			::= { sleBridgePortNotification 21 }

		
		-- 1.3.6.1.4.1.6296.101.3.2.3.22
		sleBridgePortInner2outerVidChanged NOTIFICATION-TYPE
			OBJECTS { sleBridgePortControlRequest, sleBridgePortControlReqResult, sleBridgePortControlTimeStamp, sleBridgePortControlIndex, sleBridgePortControlInner2outerVid
				 }
			STATUS current
			DESCRIPTION 
				"setBridgePortInner2outerVid"
			::= { sleBridgePortNotification 22 }

		
--  			::= { sle 4 }
-- 
-- Node definitions
-- 
-- 1.3.6.1.4.1.6296.9.8.3
		-- 1.3.6.1.4.1.6296.101.3.3
		sleVlan OBJECT IDENTIFIER ::= { sleBridge 3 }

		
--  1.3.6.1.4.1.6296.9.8.3.1
		-- 1.3.6.1.4.1.6296.101.3.3.1
		sleVlanTable OBJECT-TYPE
			SYNTAX SEQUENCE OF SleVlanEntry
			MAX-ACCESS not-accessible
			STATUS current
			DESCRIPTION
				" "
			::= { sleVlan 1 }

		
--  1.3.6.1.4.1.6296.9.8.3.1.1
		-- 1.3.6.1.4.1.6296.101.3.3.1.1
		sleVlanEntry OBJECT-TYPE
			SYNTAX SleVlanEntry
			MAX-ACCESS not-accessible
			STATUS current
			DESCRIPTION
				" "
			INDEX { sleVlanIndex }
			::= { sleVlanTable 1 }

		
		SleVlanEntry ::=
			SEQUENCE { 
				sleVlanIndex
					INTEGER,
				sleVlanIfIndex
					Integer32,
				sleVlanName
					OCTET STRING,
				sleVlanStatus
					INTEGER,
				sleVlanEgressPorts
					OCTET STRING,
				sleVlanUnTaggedPorts
					OCTET STRING,
				sleVlanCreationTime
					TimeTicks,
				sleVlanAgeingTime
					INTEGER
			 }

--  1.3.6.1.4.1.6296.9.8.3.1.1.1
		-- 1.3.6.1.4.1.6296.101.3.3.1.1.1
		sleVlanIndex OBJECT-TYPE
			SYNTAX INTEGER (1..4094)
			MAX-ACCESS read-only
			STATUS current
			DESCRIPTION
				"A vlan-identifier."
			::= { sleVlanEntry 1 }

		
		-- 1.3.6.1.4.1.6296.101.3.3.1.1.2
		sleVlanIfIndex OBJECT-TYPE
			SYNTAX Integer32
			MAX-ACCESS read-only
			STATUS current
			DESCRIPTION
				"Description."
			::= { sleVlanEntry 2 }

		
--  1.3.6.1.4.1.6296.9.8.3.1.1.2
		-- 1.3.6.1.4.1.6296.101.3.3.1.1.3
		sleVlanName OBJECT-TYPE
			SYNTAX OCTET STRING
			MAX-ACCESS read-only
			STATUS current
			DESCRIPTION
				"A descriptional name for that vlan."
			::= { sleVlanEntry 3 }

		
--  1.3.6.1.4.1.6296.9.8.3.1.1.3
		-- 1.3.6.1.4.1.6296.101.3.3.1.1.4
		sleVlanStatus OBJECT-TYPE
			SYNTAX INTEGER
				{
				static(1),
				dynamic(2)
				}
			MAX-ACCESS read-only
			STATUS current
			DESCRIPTION
				"static, in future gvrp"
			::= { sleVlanEntry 4 }

		
--  1.3.6.1.4.1.6296.9.8.3.1.1.4
		-- 1.3.6.1.4.1.6296.101.3.3.1.1.5
		sleVlanEgressPorts OBJECT-TYPE
			SYNTAX OCTET STRING
			MAX-ACCESS read-only
			STATUS current
			DESCRIPTION
				"Portlist for all member of this VLAN, they will send tagged or untagged frames.
				The octet string is a list of pairs of octets each identify
				an sleBridgePortIndex. The least significant byte is the
				second octet."
			::= { sleVlanEntry 5 }

		
--  1.3.6.1.4.1.6296.9.8.3.1.1.5
		-- 1.3.6.1.4.1.6296.101.3.3.1.1.6
		sleVlanUnTaggedPorts OBJECT-TYPE
			SYNTAX OCTET STRING
			MAX-ACCESS read-only
			STATUS current
			DESCRIPTION
				"Portlist for members of this Vlan they will send only untagged frames.
				The octet string is a list of pairs of octets each identify
				an sleBridgePortIndex. The least significant byte is the second
				octet."
			::= { sleVlanEntry 6 }

		
--  1.3.6.1.4.1.6296.9.8.3.1.1.8
		-- 1.3.6.1.4.1.6296.101.3.3.1.1.7
		sleVlanCreationTime OBJECT-TYPE
			SYNTAX TimeTicks
			MAX-ACCESS read-only
			STATUS current
			DESCRIPTION
				"Only useful in case of gvrp."
			::= { sleVlanEntry 7 }

		
		-- 1.3.6.1.4.1.6296.101.3.3.1.1.8
		sleVlanAgeingTime OBJECT-TYPE
			SYNTAX INTEGER (-1 | 0 | 10..21474830)
			MAX-ACCESS read-only
			STATUS current
			DESCRIPTION
				"The ageing time per vlan"
			::= { sleVlanEntry 8 }

		
--  1.3.6.1.4.1.6296.9.8.3.2
		-- 1.3.6.1.4.1.6296.101.3.3.2
		sleVlanControl OBJECT IDENTIFIER ::= { sleVlan 2 }

		
--   Node definitions
-- 
-- 1.3.6.1.4.1.6296.9.8.3.2.1
		-- 1.3.6.1.4.1.6296.101.3.3.2.1
		sleVlanControlRequest OBJECT-TYPE
			SYNTAX INTEGER
				{
				createVlan(1),
				destroyVlan(2),
				setVlanPortProfile(3),
				setVlanAgeingTime(4)
				}
			MAX-ACCESS read-write
			STATUS current
			DESCRIPTION
				"
				createVlan:
				(sleVlanControlIndex)
				sleVlanControlName
				sleVlanControlMulticastPermision
				
				destroyVlan:
				sleVlanControlIndex
				
				setVlanPortProfile:
				sleVlanControlIndex
				sleVlanControlEgressPorts
				sleVlanControlUnTaggedPorts
				
				setVlanMulticastPermission:
				sleVlanControlIndex
				sleVlanControlMulticastPermission
				
				"
			::= { sleVlanControl 1 }

		
--  1.3.6.1.4.1.6296.9.8.3.2.3
		-- 1.3.6.1.4.1.6296.101.3.3.2.2
		sleVlanControlStatus OBJECT-TYPE
			SYNTAX SleControlStatusType
			MAX-ACCESS read-only
			STATUS current
			DESCRIPTION
				"The status of a user command. 
				"
			::= { sleVlanControl 2 }

		
--  1.3.6.1.4.1.6296.9.8.3.2.4
		-- 1.3.6.1.4.1.6296.101.3.3.2.3
		sleVlanControlTimer OBJECT-TYPE
			SYNTAX Gauge32
			MAX-ACCESS read-write
			STATUS current
			DESCRIPTION
				"The maximum wait time for the manager for a long running user command. 
				"
			::= { sleVlanControl 3 }

		
--  1.3.6.1.4.1.6296.9.8.3.2.6
		-- 1.3.6.1.4.1.6296.101.3.3.2.4
		sleVlanControlTimeStamp OBJECT-TYPE
			SYNTAX TimeTicks
			MAX-ACCESS read-only
			STATUS current
			DESCRIPTION
				"The time stamp of the last command (end of command)."
			::= { sleVlanControl 4 }

		
--  1.3.6.1.4.1.6296.9.8.3.2.5
		-- 1.3.6.1.4.1.6296.101.3.3.2.5
		sleVlanControlReqResult OBJECT-TYPE
			SYNTAX SleControlRequestResultType
			MAX-ACCESS read-only
			STATUS current
			DESCRIPTION
				"The result of the last user command."
			::= { sleVlanControl 5 }

		
--  1.3.6.1.4.1.6296.9.8.3.2.2
		-- 1.3.6.1.4.1.6296.101.3.3.2.6
		sleVlanControlIndex OBJECT-TYPE
			SYNTAX Integer32 (1..4094)
			MAX-ACCESS read-write
			STATUS current
			DESCRIPTION
				"Vlan's ID
				"
			::= { sleVlanControl 6 }

		
--  1.3.6.1.4.1.6296.9.8.3.2.7
		-- 1.3.6.1.4.1.6296.101.3.3.2.7
		sleVlanControlName OBJECT-TYPE
			SYNTAX OCTET STRING
			MAX-ACCESS read-write
			STATUS current
			DESCRIPTION
				"Vlan's name."
			::= { sleVlanControl 7 }

		
--  1.3.6.1.4.1.6296.9.8.3.2.8
		-- 1.3.6.1.4.1.6296.101.3.3.2.8
		sleVlanControlEgressPorts OBJECT-TYPE
			SYNTAX OCTET STRING
			MAX-ACCESS read-write
			STATUS current
			DESCRIPTION
				" "
			::= { sleVlanControl 8 }

		
--  1.3.6.1.4.1.6296.9.8.3.2.9
		-- 1.3.6.1.4.1.6296.101.3.3.2.9
		sleVlanControlUnTaggedPorts OBJECT-TYPE
			SYNTAX OCTET STRING
			MAX-ACCESS read-write
			STATUS current
			DESCRIPTION
				" "
			::= { sleVlanControl 9 }

		
		-- 1.3.6.1.4.1.6296.101.3.3.2.10
		sleVlanControlAgeingTime OBJECT-TYPE
			SYNTAX INTEGER (-1 | 0 | 10..21474830)
			MAX-ACCESS read-write
			STATUS current
			DESCRIPTION
				"Description."
			::= { sleVlanControl 10 }

		
--  1.3.6.1.4.1.6296.9.8.3.3
		-- 1.3.6.1.4.1.6296.101.3.3.3
		sleVlanNotification OBJECT IDENTIFIER ::= { sleVlan 3 }

		
--  1.3.6.1.4.1.6296.9.8.3.3.1
		-- 1.3.6.1.4.1.6296.101.3.3.3.1
		sleVlanCreated NOTIFICATION-TYPE
			OBJECTS { sleVlanName, sleVlanEgressPorts, sleVlanUnTaggedPorts, sleVlanControlRequest, sleVlanControlTimeStamp, 
				sleVlanControlReqResult, sleVlanIfIndex, sleVlanStatus }
			STATUS current
			DESCRIPTION 
				"Description."
			::= { sleVlanNotification 1 }

		
--  1.3.6.1.4.1.6296.9.8.3.3.2
		-- 1.3.6.1.4.1.6296.101.3.3.3.2
		sleVlanDestroyed NOTIFICATION-TYPE
			OBJECTS { sleVlanIndex, sleVlanControlRequest, sleVlanControlTimeStamp, sleVlanControlReqResult }
			STATUS current
			DESCRIPTION 
				" "
			::= { sleVlanNotification 2 }

		
--  1.3.6.1.4.1.6296.9.8.3.3.3
		-- 1.3.6.1.4.1.6296.101.3.3.3.3
		sleVlanPortProfileChanged NOTIFICATION-TYPE
			OBJECTS { sleVlanEgressPorts, sleVlanUnTaggedPorts, sleVlanControlRequest, sleVlanControlTimeStamp, sleVlanControlReqResult
				 }
			STATUS current
			DESCRIPTION 
				" "
			::= { sleVlanNotification 3 }

		
		-- 1.3.6.1.4.1.6296.101.3.3.3.4
		sleVlanAgeingTimeChanged NOTIFICATION-TYPE
			OBJECTS { sleVlanControlRequest, sleVlanControlTimeStamp, sleVlanControlReqResult, sleVlanIndex, sleVlanAgeingTime
				 }
			STATUS current
			DESCRIPTION 
				"Description."
			::= { sleVlanNotification 4 }

		
--   sleVlanMap Group
-- 1.3.6.1.4.1.6296.9.8.4
		-- 1.3.6.1.4.1.6296.101.3.4
		sleVlanMap OBJECT IDENTIFIER ::= { sleBridge 4 }

		
--  1.3.6.1.4.1.6296.9.8.4.1
		-- 1.3.6.1.4.1.6296.101.3.4.1
		sleVlanMapTable OBJECT-TYPE
			SYNTAX SEQUENCE OF SleVlanMapEntry
			MAX-ACCESS not-accessible
			STATUS current
			DESCRIPTION
				" "
			::= { sleVlanMap 1 }

		
--  1.3.6.1.4.1.6296.9.8.4.1.1
		-- 1.3.6.1.4.1.6296.101.3.4.1.1
		sleVlanMapEntry OBJECT-TYPE
			SYNTAX SleVlanMapEntry
			MAX-ACCESS not-accessible
			STATUS current
			DESCRIPTION
				" "
			INDEX { sleVlanIndex }
			::= { sleVlanMapTable 1 }

		
		SleVlanMapEntry ::=
			SEQUENCE { 
				sleVlanMapFid
					Unsigned32,
				sleVlanMapStpId
					Unsigned32,
				sleVlanMapErpDomainId
					Unsigned32
			 }

--  1.3.6.1.4.1.6296.9.8.4.1.1.2
		-- 1.3.6.1.4.1.6296.101.3.4.1.1.1
		sleVlanMapFid OBJECT-TYPE
			SYNTAX Unsigned32
			MAX-ACCESS read-only
			STATUS current
			DESCRIPTION
				"Index of the used Filtering Table entry."
			::= { sleVlanMapEntry 1 }

		
--  1.3.6.1.4.1.6296.9.8.4.1.1.3
		-- 1.3.6.1.4.1.6296.101.3.4.1.1.2
		sleVlanMapStpId OBJECT-TYPE
			SYNTAX Unsigned32
			MAX-ACCESS read-only
			STATUS current
			DESCRIPTION
				"Index of the used STP instance."
			::= { sleVlanMapEntry 2 }

		
--  1.3.6.1.4.1.6296.9.8.4.1.1.4
		-- 1.3.6.1.4.1.6296.101.3.4.1.1.3
		sleVlanMapErpDomainId OBJECT-TYPE
			SYNTAX Unsigned32
			MAX-ACCESS read-only
			STATUS current
			DESCRIPTION
				"Index of the used Erp Domain."
			::= { sleVlanMapEntry 3 }

		
--  1.3.6.1.4.1.6296.9.8.4.2
		-- 1.3.6.1.4.1.6296.101.3.4.2
		sleVlanMapControl OBJECT IDENTIFIER ::= { sleVlanMap 2 }

		
--   Node definitions
-- 
-- 1.3.6.1.4.1.6296.9.8.4.2.1
		-- 1.3.6.1.4.1.6296.101.3.4.2.1
		sleVlanMapControlRequest OBJECT-TYPE
			SYNTAX INTEGER
				{
				setVlanMapFid(1),
				setVlanMapStpId(2),
				setVlanMapErpDomainId(3)
				}
			MAX-ACCESS read-write
			STATUS current
			DESCRIPTION
				"
				setVlanMapFid:
				sleVlanMapControlIndex
				sleVlanMapFid
				
				setVlanMapStpId:
				sleVlanMapControlIndex
				sleVlanMapStpId
				
				setVlanMapErpDomainId:
				sleVlanMapControlIndex
				sleVlanMapErpDomainId
				
				"
			::= { sleVlanMapControl 1 }

		
--  1.3.6.1.4.1.6296.9.8.4.2.3
		-- 1.3.6.1.4.1.6296.101.3.4.2.2
		sleVlanMapControlStatus OBJECT-TYPE
			SYNTAX SleControlStatusType
			MAX-ACCESS read-only
			STATUS current
			DESCRIPTION
				"The status of a user command. 
				"
			::= { sleVlanMapControl 2 }

		
--  1.3.6.1.4.1.6296.9.8.4.2.4
		-- 1.3.6.1.4.1.6296.101.3.4.2.3
		sleVlanMapControlTimer OBJECT-TYPE
			SYNTAX Gauge32
			MAX-ACCESS read-write
			STATUS current
			DESCRIPTION
				"The maximum wait time for the manager for a long running user command. 
				"
			::= { sleVlanMapControl 3 }

		
--  1.3.6.1.4.1.6296.9.8.4.2.6
		-- 1.3.6.1.4.1.6296.101.3.4.2.4
		sleVlanMapControlTimeStamp OBJECT-TYPE
			SYNTAX TimeTicks
			MAX-ACCESS read-only
			STATUS current
			DESCRIPTION
				"The time stamp of the last command (end of command)."
			::= { sleVlanMapControl 4 }

		
--  1.3.6.1.4.1.6296.9.8.4.2.5
		-- 1.3.6.1.4.1.6296.101.3.4.2.5
		sleVlanMapControlReqResult OBJECT-TYPE
			SYNTAX SleControlRequestResultType
			MAX-ACCESS read-only
			STATUS current
			DESCRIPTION
				"The result of the last user command."
			::= { sleVlanMapControl 5 }

		
--  1.3.6.1.4.1.6296.9.8.4.2.2
		-- 1.3.6.1.4.1.6296.101.3.4.2.6
		sleVlanMapControlIndex OBJECT-TYPE
			SYNTAX Integer32 (1..4094)
			MAX-ACCESS read-write
			STATUS current
			DESCRIPTION
				" "
			::= { sleVlanMapControl 6 }

		
--  1.3.6.1.4.1.6296.9.8.4.2.7
		-- 1.3.6.1.4.1.6296.101.3.4.2.7
		sleVlanMapControlFid OBJECT-TYPE
			SYNTAX Unsigned32
			MAX-ACCESS read-write
			STATUS current
			DESCRIPTION
				" "
			::= { sleVlanMapControl 7 }

		
--  1.3.6.1.4.1.6296.9.8.4.2.8
		-- 1.3.6.1.4.1.6296.101.3.4.2.8
		sleVlanMapControlStpId OBJECT-TYPE
			SYNTAX Unsigned32
			MAX-ACCESS read-write
			STATUS current
			DESCRIPTION
				" "
			::= { sleVlanMapControl 8 }

		
--  1.3.6.1.4.1.6296.9.8.4.2.9
		-- 1.3.6.1.4.1.6296.101.3.4.2.9
		sleVlanMapControlErpDomainId OBJECT-TYPE
			SYNTAX Unsigned32
			MAX-ACCESS read-write
			STATUS current
			DESCRIPTION
				" "
			::= { sleVlanMapControl 9 }

		
--  1.3.6.1.4.1.6296.9.8.4.3
		-- 1.3.6.1.4.1.6296.101.3.4.3
		sleVlanMapNotification OBJECT IDENTIFIER ::= { sleVlanMap 3 }

		
--  1.3.6.1.4.1.6296.9.8.4.3.1
		-- 1.3.6.1.4.1.6296.101.3.4.3.1
		sleVlanMapFidChanged NOTIFICATION-TYPE
			OBJECTS { sleVlanMapControlTimeStamp, sleVlanMapControlReqResult, sleVlanMapControlRequest, sleVlanMapFid }
			STATUS current
			DESCRIPTION 
				" "
			::= { sleVlanMapNotification 1 }

		
--  1.3.6.1.4.1.6296.9.8.4.3.2
		-- 1.3.6.1.4.1.6296.101.3.4.3.2
		sleVlanMapStpIdChanged NOTIFICATION-TYPE
			OBJECTS { sleVlanMapStpId, sleVlanMapControlRequest, sleVlanMapControlTimeStamp, sleVlanMapControlReqResult }
			STATUS current
			DESCRIPTION 
				" "
			::= { sleVlanMapNotification 2 }

		
--  1.3.6.1.4.1.6296.9.8.4.3.3
		-- 1.3.6.1.4.1.6296.101.3.4.3.3
		sleVlanMapErpDomainIdChanged NOTIFICATION-TYPE
			OBJECTS { sleVlanMapErpDomainId, sleVlanMapControlRequest, sleVlanMapControlTimeStamp, sleVlanMapControlReqResult }
			STATUS current
			DESCRIPTION 
				" "
			::= { sleVlanMapNotification 3 }

		
-- 
--   Node definitions
-- 
		-- 1.3.6.1.4.1.6296.101.3.5
		sleStp OBJECT IDENTIFIER ::= { sleBridge 5 }

		
		-- 1.3.6.1.4.1.6296.101.3.5.1
		sleStpInfo OBJECT IDENTIFIER ::= { sleStp 1 }

		
		-- 1.3.6.1.4.1.6296.101.3.5.1.1
		sleStpOperationMode OBJECT-TYPE
			SYNTAX INTEGER
				{
				stp(0),
				rstp(1),
				mstp(3),
				pvstp(4),
				pvrstp(5)
				}
			MAX-ACCESS read-only
			STATUS current
			DESCRIPTION
				"The operation mode of running the STP at the switch."
			::= { sleStpInfo 1 }

		
		-- 1.3.6.1.4.1.6296.101.3.5.1.2
		sleStpFormatSelector OBJECT-TYPE
			SYNTAX INTEGER (0..65535)
			MAX-ACCESS read-only
			STATUS current
			DESCRIPTION
				"The MST configuration format selector."
			::= { sleStpInfo 2 }

		
		-- 1.3.6.1.4.1.6296.101.3.5.1.3
		sleStpConfigureName OBJECT-TYPE
			SYNTAX OCTET STRING (SIZE (0..32))
			MAX-ACCESS read-write
			STATUS current
			DESCRIPTION
				"Descriptrion."
			::= { sleStpInfo 3 }

		
		-- 1.3.6.1.4.1.6296.101.3.5.1.4
		sleStpRevisionLevel OBJECT-TYPE
			SYNTAX INTEGER (0..65535)
			MAX-ACCESS read-only
			STATUS current
			DESCRIPTION
				"The MST configuration revision."
			::= { sleStpInfo 4 }

		
		-- 1.3.6.1.4.1.6296.101.3.5.1.5
		sleStpFwdDelay OBJECT-TYPE
			SYNTAX INTEGER (4..300)
			MAX-ACCESS read-only
			STATUS current
			DESCRIPTION
				"The STP bridge forward delay."
			::= { sleStpInfo 5 }

		
		-- 1.3.6.1.4.1.6296.101.3.5.1.6
		sleStpHelloTime OBJECT-TYPE
			SYNTAX INTEGER (1..10)
			MAX-ACCESS read-only
			STATUS current
			DESCRIPTION
				"The STP bridge hello time."
			::= { sleStpInfo 6 }

		
		-- 1.3.6.1.4.1.6296.101.3.5.1.7
		sleStpMaxAge OBJECT-TYPE
			SYNTAX INTEGER (6..40)
			MAX-ACCESS read-only
			STATUS current
			DESCRIPTION
				"The STP bridge max age."
			::= { sleStpInfo 7 }

		
		-- 1.3.6.1.4.1.6296.101.3.5.1.8
		sleStpMaxHops OBJECT-TYPE
			SYNTAX INTEGER (1..40)
			MAX-ACCESS read-only
			STATUS current
			DESCRIPTION
				"The MST bridge max hops."
			::= { sleStpInfo 8 }

		
		-- 1.3.6.1.4.1.6296.101.3.5.1.9
		sleStpExtRootBridgeId OBJECT-TYPE
			SYNTAX OCTET STRING (SIZE (8))
			MAX-ACCESS read-only
			STATUS current
			DESCRIPTION
				"The MST CST root identifier."
			::= { sleStpInfo 9 }

		
		-- 1.3.6.1.4.1.6296.101.3.5.1.10
		sleStpExtPathcost OBJECT-TYPE
			SYNTAX Unsigned32
			MAX-ACCESS read-only
			STATUS current
			DESCRIPTION
				"The MST CST root path cost."
			::= { sleStpInfo 10 }

		
		-- 1.3.6.1.4.1.6296.101.3.5.1.11
		sleStpBpduGuardMode OBJECT-TYPE
			SYNTAX INTEGER
				{
				disable(0),
				enable(1)
				}
			MAX-ACCESS read-only
			STATUS current
			DESCRIPTION
				"Indicates the mode of Bpdu Guard Feature on the switch. 
				 	When the system with Bpdu Guard enabled 
				 	receives a BPDU from any port, that port is 
				 	immediately disabled.  	 
				 	
				 	disable -- the Bpdu Guard feature is disabled on this
					           switch.
				 	
				 	enable -- the Bpdu Guard feature is enabled on this
					           switch. 
				 	
				 	           Whether the Bpdu Guard feature is enabled
				 	           or not on this switch depends on the object
				 	           value of sleStpControlBpduGuardMode."
			DEFVAL { 0 }
			::= { sleStpInfo 11 }

		
		-- 1.3.6.1.4.1.6296.101.3.5.1.12
		sleStpBpduGuardAutoRcvMode OBJECT-TYPE
			SYNTAX INTEGER
				{
				disable(0),
				enable(1)
				}
			MAX-ACCESS read-only
			STATUS current
			DESCRIPTION
				"Indicates the automatic recovery mode for the ports disabled by Bpdu Guard.
				 	
				 	disable -- the Bpdu Guard Auto Recovery feature is disabled on this
					           switch.
				 	
				 	enable -- the Bpdu Guard Auto Recovery feature is enabled on this
					           switch. 
				 	
				 	           Whether the Bpdu Guard Auto Recovery feature is enabled
				 	           or not on this switch depends on the object
				 	           value of sleStpControlBpduGuardAutoRcvMode."
			DEFVAL { 0 }
			::= { sleStpInfo 12 }

		
		-- 1.3.6.1.4.1.6296.101.3.5.1.13
		sleStpBpduGuardAutoRcvTime OBJECT-TYPE
			SYNTAX INTEGER (10..1000000)
			MAX-ACCESS read-only
			STATUS current
			DESCRIPTION
				"Indicates the automatic recovery time for the ports disabled by Bpdu Guard.
				 	Unit: second
				 	
				The Bpdu Guard Auto Recovery time depends on the object value 
				 	of sleStpControlBpduGuardAutoRcvTime."
			DEFVAL { 300 }
			::= { sleStpInfo 13 }

		
		-- 1.3.6.1.4.1.6296.101.3.5.2
		sleStpControl OBJECT IDENTIFIER ::= { sleStp 2 }

		
		-- 1.3.6.1.4.1.6296.101.3.5.2.1
		sleStpControlRequest OBJECT-TYPE
			SYNTAX INTEGER
				{
				setStpOperationMode(1),
				setStpConfigureProfile(2),
				setStpTimerProfile(3),
				setStpBpduGuardProfile(4)
				}
			MAX-ACCESS read-write
			STATUS current
			DESCRIPTION
				"
				setStpOperationMode:
				sleStpControlOperationMode
				
				setStpConfigureProfile:
				sleStpControlConfigureName
				sleStpControlRevisionLevel
				
				setStpTimerProfile
				sleStpControlFwdDelay
				sleStpControlHelloTime
				sleStpControlMaxAge
				sleStpControlMaxHops
				"
			::= { sleStpControl 1 }

		
		-- 1.3.6.1.4.1.6296.101.3.5.2.2
		sleStpControlStatus OBJECT-TYPE
			SYNTAX SleControlStatusType
			MAX-ACCESS read-only
			STATUS current
			DESCRIPTION
				"The status of a user command. 
				"
			::= { sleStpControl 2 }

		
		-- 1.3.6.1.4.1.6296.101.3.5.2.3
		sleStpControlTimer OBJECT-TYPE
			SYNTAX Gauge32
			MAX-ACCESS read-write
			STATUS current
			DESCRIPTION
				"The maximum wait time for the manager for a long running user command. 
				"
			::= { sleStpControl 3 }

		
		-- 1.3.6.1.4.1.6296.101.3.5.2.4
		sleStpControlTimeStamp OBJECT-TYPE
			SYNTAX TimeTicks
			MAX-ACCESS read-only
			STATUS current
			DESCRIPTION
				"The time stamp of the last command (end of command)."
			::= { sleStpControl 4 }

		
		-- 1.3.6.1.4.1.6296.101.3.5.2.5
		sleStpControlReqResult OBJECT-TYPE
			SYNTAX SleControlRequestResultType
			MAX-ACCESS read-only
			STATUS current
			DESCRIPTION
				"The result of the last user command."
			::= { sleStpControl 5 }

		
		-- 1.3.6.1.4.1.6296.101.3.5.2.6
		sleStpControlOperationMode OBJECT-TYPE
			SYNTAX INTEGER
				{
				stp(0),
				rstp(1),
				mstp(3),
				pvstp(4),
				pvrstp(5)
				}
			MAX-ACCESS read-write
			STATUS current
			DESCRIPTION
				" "
			::= { sleStpControl 6 }

		
		-- 1.3.6.1.4.1.6296.101.3.5.2.7
		sleStpControlConfigureName OBJECT-TYPE
			SYNTAX OCTET STRING (SIZE (0..32))
			MAX-ACCESS read-write
			STATUS current
			DESCRIPTION
				" "
			::= { sleStpControl 7 }

		
		-- 1.3.6.1.4.1.6296.101.3.5.2.8
		sleStpControlRevisionLevel OBJECT-TYPE
			SYNTAX INTEGER (0..65535)
			MAX-ACCESS read-write
			STATUS current
			DESCRIPTION
				" "
			::= { sleStpControl 8 }

		
		-- 1.3.6.1.4.1.6296.101.3.5.2.9
		sleStpControlFwdDelay OBJECT-TYPE
			SYNTAX INTEGER (4..30)
			MAX-ACCESS read-write
			STATUS current
			DESCRIPTION
				" "
			::= { sleStpControl 9 }

		
		-- 1.3.6.1.4.1.6296.101.3.5.2.10
		sleStpControlHelloTime OBJECT-TYPE
			SYNTAX INTEGER (1..10)
			MAX-ACCESS read-write
			STATUS current
			DESCRIPTION
				" "
			::= { sleStpControl 10 }

		
		-- 1.3.6.1.4.1.6296.101.3.5.2.11
		sleStpControlMaxAge OBJECT-TYPE
			SYNTAX INTEGER (4..60)
			MAX-ACCESS read-write
			STATUS current
			DESCRIPTION
				" "
			::= { sleStpControl 11 }

		
		-- 1.3.6.1.4.1.6296.101.3.5.2.12
		sleStpControlMaxHops OBJECT-TYPE
			SYNTAX INTEGER (1..40)
			MAX-ACCESS read-write
			STATUS current
			DESCRIPTION
				" "
			::= { sleStpControl 12 }

		
		-- 1.3.6.1.4.1.6296.101.3.5.2.13
		sleStpControlBpduGuardMode OBJECT-TYPE
			SYNTAX INTEGER
				{
				disable(0),
				enable(1)
				}
			MAX-ACCESS read-write
			STATUS current
			DESCRIPTION
				"Configures the mode of Bpdu Guard Feature on the switch. 
				 	When the system with Bpdu Guard enabled 
				 	receives a BPDU from any port, that port is 
				 	immediately disabled.  	 
				 	
				 	disable -- the Bpdu Guard feature is disabled on this
					           switch.
				 	
				 	enable -- the Bpdu Guard feature is enabled on this
					           switch. 
				"
			DEFVAL { 0 }
			::= { sleStpControl 13 }

		
		-- 1.3.6.1.4.1.6296.101.3.5.2.14
		sleStpControlBpduGuardAutoRcvMode OBJECT-TYPE
			SYNTAX INTEGER
				{
				disable(0),
				enable(1)
				}
			MAX-ACCESS read-write
			STATUS current
			DESCRIPTION
				"Configures the automatic recovery mode for the ports disabled by Bpdu Guard.
				 	
				 	disable -- the Bpdu Guard Auto Recovery feature is disabled on this
					           switch.
				 	
				 	enable -- the Bpdu Guard Auto Recovery feature is enabled on this
					           switch. "
			DEFVAL { 0 }
			::= { sleStpControl 14 }

		
		-- 1.3.6.1.4.1.6296.101.3.5.2.15
		sleStpControlBpduGuardAutoRcvTime OBJECT-TYPE
			SYNTAX INTEGER (10..1000000)
			MAX-ACCESS read-write
			STATUS current
			DESCRIPTION
				"Configures the automatic recovery time for the ports disabled by Bpdu Guard.
				 	Unit: second"
			DEFVAL { 300 }
			::= { sleStpControl 15 }

		
		-- 1.3.6.1.4.1.6296.101.3.5.3
		sleStpNotification OBJECT IDENTIFIER ::= { sleStp 3 }

		
		-- 1.3.6.1.4.1.6296.101.3.5.3.1
		sleStpOperationModeChanged NOTIFICATION-TYPE
			OBJECTS { sleStpControlRequest, sleStpControlReqResult, sleStpControlTimeStamp, sleStpOperationMode }
			STATUS current
			DESCRIPTION 
				" "
			::= { sleStpNotification 1 }

		
		-- 1.3.6.1.4.1.6296.101.3.5.3.2
		sleStpConfigureProfileChanged NOTIFICATION-TYPE
			OBJECTS { sleStpControlRequest, sleStpControlReqResult, sleStpControlTimeStamp, sleStpRevisionLevel, sleStpConfigureName
				 }
			STATUS current
			DESCRIPTION 
				" "
			::= { sleStpNotification 2 }

		
		-- 1.3.6.1.4.1.6296.101.3.5.3.3
		sleStpTimerProfileChanged NOTIFICATION-TYPE
			OBJECTS { sleStpControlRequest, sleStpControlReqResult, sleStpControlTimeStamp, sleStpFwdDelay, sleStpHelloTime, 
				sleStpMaxAge, sleStpMaxHops }
			STATUS current
			DESCRIPTION 
				" "
			::= { sleStpNotification 3 }

		
		-- 1.3.6.1.4.1.6296.101.3.5.3.4
		sleStpBpduGuardProfileChanged NOTIFICATION-TYPE
			OBJECTS { sleStpControlRequest, sleStpControlReqResult, sleStpControlTimeStamp, sleStpBpduGuardMode, sleStpBpduGuardAutoRcvMode, 
				sleStpBpduGuardAutoRcvTime }
			STATUS current
			DESCRIPTION 
				" "
			::= { sleStpNotification 4 }

		
		-- 1.3.6.1.4.1.6296.101.3.6
		sleStpInstance OBJECT IDENTIFIER ::= { sleBridge 6 }

		
		-- 1.3.6.1.4.1.6296.101.3.6.1
		sleStpInstanceTable OBJECT-TYPE
			SYNTAX SEQUENCE OF SleStpInstanceEntry
			MAX-ACCESS not-accessible
			STATUS current
			DESCRIPTION
				" "
			::= { sleStpInstance 1 }

		
		-- 1.3.6.1.4.1.6296.101.3.6.1.1
		sleStpInstanceEntry OBJECT-TYPE
			SYNTAX SleStpInstanceEntry
			MAX-ACCESS not-accessible
			STATUS current
			DESCRIPTION
				" "
			INDEX { sleStpInstanceIndex }
			::= { sleStpInstanceTable 1 }

		
		SleStpInstanceEntry ::=
			SEQUENCE { 
				sleStpInstanceIndex
					INTEGER,
				sleStpInstanceEnable
					INTEGER,
				sleStpInstancePriority
					INTEGER,
				sleStpInstanceRootBridgeId
					OCTET STRING,
				sleStpInstanceRootPathcost
					Integer32,
				sleStpInstanceDesignatedBridgeId
					OCTET STRING,
				sleStpInstanceDesignatedPortId
					INTEGER,
				sleStpInstanceRootPortId
					INTEGER,
				sleStpInstanceFwdDelay
					INTEGER,
				sleStpInstanceHelloTime
					INTEGER,
				sleStpInstanceMaxAge
					INTEGER,
				sleStpInstanceRemainHops
					Integer32,
				sleStpInstanceBrFwdDelay
					INTEGER,
				sleStpInstanceBrHelloTime
					INTEGER,
				sleStpInstanceBrMaxAge
					INTEGER
			 }

		-- 1.3.6.1.4.1.6296.101.3.6.1.1.1
		sleStpInstanceIndex OBJECT-TYPE
			SYNTAX INTEGER (0..4096)
			MAX-ACCESS read-only
			STATUS current
			DESCRIPTION
				"The STP instance ID."
			::= { sleStpInstanceEntry 1 }

		
		-- 1.3.6.1.4.1.6296.101.3.6.1.1.2
		sleStpInstanceEnable OBJECT-TYPE
			SYNTAX INTEGER
				{
				enable(0),
				disable(1)
				}
			MAX-ACCESS read-only
			STATUS current
			DESCRIPTION
				"The enabled/disabled status of the pvst."
			::= { sleStpInstanceEntry 2 }

		
		-- 1.3.6.1.4.1.6296.101.3.6.1.1.3
		sleStpInstancePriority OBJECT-TYPE
			SYNTAX INTEGER (0..16)
			MAX-ACCESS read-only
			STATUS current
			DESCRIPTION
				"The Setting bridge priority in a specific instance."
			::= { sleStpInstanceEntry 3 }

		
		-- 1.3.6.1.4.1.6296.101.3.6.1.1.4
		sleStpInstanceRootBridgeId OBJECT-TYPE
			SYNTAX OCTET STRING (SIZE (8))
			MAX-ACCESS read-only
			STATUS current
			DESCRIPTION
				"The STP designated root bridge identifier in a specific instance. Size: 8."
			::= { sleStpInstanceEntry 4 }

		
		-- 1.3.6.1.4.1.6296.101.3.6.1.1.5
		sleStpInstanceRootPathcost OBJECT-TYPE
			SYNTAX Integer32
			MAX-ACCESS read-only
			STATUS current
			DESCRIPTION
				"The STP root path cost in a specific instance."
			::= { sleStpInstanceEntry 5 }

		
		-- 1.3.6.1.4.1.6296.101.3.6.1.1.6
		sleStpInstanceDesignatedBridgeId OBJECT-TYPE
			SYNTAX OCTET STRING (SIZE (8))
			MAX-ACCESS read-only
			STATUS current
			DESCRIPTION
				"TThe STP designated bridge identifier."
			::= { sleStpInstanceEntry 6 }

		
		-- 1.3.6.1.4.1.6296.101.3.6.1.1.7
		sleStpInstanceDesignatedPortId OBJECT-TYPE
			SYNTAX INTEGER (0..256)
			MAX-ACCESS read-only
			STATUS current
			DESCRIPTION
				"The STP designated port identifier."
			::= { sleStpInstanceEntry 7 }

		
		-- 1.3.6.1.4.1.6296.101.3.6.1.1.8
		sleStpInstanceRootPortId OBJECT-TYPE
			SYNTAX INTEGER (0..256)
			MAX-ACCESS read-only
			STATUS current
			DESCRIPTION
				"The port number of the port which offers the lowest
				cost path from the this STP instance of this bridge
				to the root bridge."
			::= { sleStpInstanceEntry 8 }

		
		-- 1.3.6.1.4.1.6296.101.3.6.1.1.9
		sleStpInstanceFwdDelay OBJECT-TYPE
			SYNTAX INTEGER (4..30)
			MAX-ACCESS read-only
			STATUS current
			DESCRIPTION
				"The current forward delay of the STP Instance."
			::= { sleStpInstanceEntry 9 }

		
		-- 1.3.6.1.4.1.6296.101.3.6.1.1.10
		sleStpInstanceHelloTime OBJECT-TYPE
			SYNTAX INTEGER (1..10)
			MAX-ACCESS read-only
			STATUS current
			DESCRIPTION
				"The current hello time of the STP Instance."
			::= { sleStpInstanceEntry 10 }

		
		-- 1.3.6.1.4.1.6296.101.3.6.1.1.11
		sleStpInstanceMaxAge OBJECT-TYPE
			SYNTAX INTEGER (4..60)
			MAX-ACCESS read-only
			STATUS current
			DESCRIPTION
				"The current max age of the STP Instance."
			::= { sleStpInstanceEntry 11 }

		
		-- 1.3.6.1.4.1.6296.101.3.6.1.1.12
		sleStpInstanceRemainHops OBJECT-TYPE
			SYNTAX Integer32
			MAX-ACCESS read-only
			STATUS current
			DESCRIPTION
				"The current hello time of the STP Instance."
			::= { sleStpInstanceEntry 12 }

		
		-- 1.3.6.1.4.1.6296.101.3.6.1.1.13
		sleStpInstanceBrFwdDelay OBJECT-TYPE
			SYNTAX INTEGER (4..30)
			MAX-ACCESS read-only
			STATUS current
			DESCRIPTION
				"The Setting forward delay of the STP Instance."
			::= { sleStpInstanceEntry 13 }

		
		-- 1.3.6.1.4.1.6296.101.3.6.1.1.14
		sleStpInstanceBrHelloTime OBJECT-TYPE
			SYNTAX INTEGER (1..10)
			MAX-ACCESS read-only
			STATUS current
			DESCRIPTION
				"The current hello time of the STP Instance."
			::= { sleStpInstanceEntry 14 }

		
		-- 1.3.6.1.4.1.6296.101.3.6.1.1.15
		sleStpInstanceBrMaxAge OBJECT-TYPE
			SYNTAX INTEGER (4..60)
			MAX-ACCESS read-only
			STATUS current
			DESCRIPTION
				"The Setting max age of the STP Instance."
			::= { sleStpInstanceEntry 15 }

		
		-- 1.3.6.1.4.1.6296.101.3.6.2
		sleStpInstanceControl OBJECT IDENTIFIER ::= { sleStpInstance 2 }

		
		-- 1.3.6.1.4.1.6296.101.3.6.2.1
		sleStpInstanceControlRequest OBJECT-TYPE
			SYNTAX INTEGER
				{
				setStpInstanceEnable(1),
				setStpInstanceConfigProfile(2)
				}
			MAX-ACCESS read-write
			STATUS current
			DESCRIPTION
				"
				createStpInstance:
				sleStpInstanceControlIndex
				sleStpInstanceControlEnable
				sleStpInstanceControlPriority
				sleStpInstanceControlBrFwdDelay
				sleStpInstanceControlBrHelloTime
				sleStpInstanceControlBrMaxAge
				
				destroyStpInstance:
				sleStpInstanceControlIndex
				
				setStpInstanceEnable:
				sleStpInstanceControlIndex
				sleStpInstanceControlEnable
				
				setStpInstanceConfigProfile:
				sleStpInstanceControlIndex
				sleStpInstanceControlPriority
				sleStpInstanceControlBrFwdDelay
				sleStpInstanceControlBrHelloTime
				sleStpInstanceControlBrMaxAge
				"
			::= { sleStpInstanceControl 1 }

		
		-- 1.3.6.1.4.1.6296.101.3.6.2.2
		sleStpInstanceControlStatus OBJECT-TYPE
			SYNTAX SleControlStatusType
			MAX-ACCESS read-only
			STATUS current
			DESCRIPTION
				"The status of a user command. 
				"
			::= { sleStpInstanceControl 2 }

		
		-- 1.3.6.1.4.1.6296.101.3.6.2.3
		sleStpInstanceControlTimer OBJECT-TYPE
			SYNTAX Gauge32
			MAX-ACCESS read-write
			STATUS current
			DESCRIPTION
				"The maximum wait time for the manager for a long running user command. 
				"
			::= { sleStpInstanceControl 3 }

		
		-- 1.3.6.1.4.1.6296.101.3.6.2.4
		sleStpInstanceControlTimeStamp OBJECT-TYPE
			SYNTAX TimeTicks
			MAX-ACCESS read-only
			STATUS current
			DESCRIPTION
				"The time stamp of the last command (end of command)."
			::= { sleStpInstanceControl 4 }

		
		-- 1.3.6.1.4.1.6296.101.3.6.2.5
		sleStpInstanceControlReqResult OBJECT-TYPE
			SYNTAX SleControlRequestResultType
			MAX-ACCESS read-only
			STATUS current
			DESCRIPTION
				"The result of the last user command."
			::= { sleStpInstanceControl 5 }

		
		-- 1.3.6.1.4.1.6296.101.3.6.2.6
		sleStpInstanceControlIndex OBJECT-TYPE
			SYNTAX INTEGER (0..4096)
			MAX-ACCESS read-write
			STATUS current
			DESCRIPTION
				" "
			::= { sleStpInstanceControl 6 }

		
		-- 1.3.6.1.4.1.6296.101.3.6.2.7
		sleStpInstanceControlEnable OBJECT-TYPE
			SYNTAX INTEGER
				{
				disable(0),
				enable(1)
				}
			MAX-ACCESS read-write
			STATUS current
			DESCRIPTION
				" "
			::= { sleStpInstanceControl 7 }

		
		-- 1.3.6.1.4.1.6296.101.3.6.2.8
		sleStpInstanceControlPriority OBJECT-TYPE
			SYNTAX INTEGER (0..16)
			MAX-ACCESS read-write
			STATUS current
			DESCRIPTION
				" "
			DEFVAL { 8 }
			::= { sleStpInstanceControl 8 }

		
		-- 1.3.6.1.4.1.6296.101.3.6.2.9
		sleStpInstanceControlBrFwdDelay OBJECT-TYPE
			SYNTAX INTEGER (4..30)
			MAX-ACCESS read-write
			STATUS current
			DESCRIPTION
				" "
			DEFVAL { 15 }
			::= { sleStpInstanceControl 9 }

		
		-- 1.3.6.1.4.1.6296.101.3.6.2.10
		sleStpInstanceControlBrHelloTime OBJECT-TYPE
			SYNTAX INTEGER (1..10)
			MAX-ACCESS read-write
			STATUS current
			DESCRIPTION
				" "
			DEFVAL { 2 }
			::= { sleStpInstanceControl 10 }

		
		-- 1.3.6.1.4.1.6296.101.3.6.2.11
		sleStpInstanceControlBrMaxAge OBJECT-TYPE
			SYNTAX INTEGER (4..60)
			MAX-ACCESS read-write
			STATUS current
			DESCRIPTION
				" "
			DEFVAL { 30 }
			::= { sleStpInstanceControl 11 }

		
		-- 1.3.6.1.4.1.6296.101.3.6.3
		sleStpInstanceNotification OBJECT IDENTIFIER ::= { sleStpInstance 3 }

		
		-- 1.3.6.1.4.1.6296.101.3.6.3.1
		sleStpInstanceEnableChanged NOTIFICATION-TYPE
			OBJECTS { sleStpInstanceControlRequest, sleStpInstanceControlReqResult, sleStpInstanceControlTimeStamp, sleStpInstanceIndex, sleStpInstanceEnable
				 }
			STATUS current
			DESCRIPTION 
				" "
			::= { sleStpInstanceNotification 1 }

		
		-- 1.3.6.1.4.1.6296.101.3.6.3.2
		sleStpInstanceConfigProfileChanged NOTIFICATION-TYPE
			OBJECTS { sleStpInstanceControlRequest, sleStpInstanceControlReqResult, sleStpInstanceControlTimeStamp, sleStpInstanceIndex, sleStpInstancePriority, 
				sleStpInstanceBrFwdDelay, sleStpInstanceBrHelloTime, sleStpInstanceBrMaxAge }
			STATUS current
			DESCRIPTION 
				" "
			::= { sleStpInstanceNotification 2 }

		
		-- 1.3.6.1.4.1.6296.101.3.7
		sleStpInstancePort OBJECT IDENTIFIER ::= { sleBridge 7 }

		
		-- 1.3.6.1.4.1.6296.101.3.7.1
		sleStpInstancePortTable OBJECT-TYPE
			SYNTAX SEQUENCE OF SleStpInstancePortEntry
			MAX-ACCESS not-accessible
			STATUS current
			DESCRIPTION
				" "
			::= { sleStpInstancePort 1 }

		
		-- 1.3.6.1.4.1.6296.101.3.7.1.1
		sleStpInstancePortEntry OBJECT-TYPE
			SYNTAX SleStpInstancePortEntry
			MAX-ACCESS not-accessible
			STATUS current
			DESCRIPTION
				" "
			INDEX { sleStpInstanceIndex, sleStpInstancePortIndex }
			::= { sleStpInstancePortTable 1 }

		
		SleStpInstancePortEntry ::=
			SEQUENCE { 
				sleStpInstancePortIndex
					InterfaceIndex,
				sleStpInstancePortPathcost
					INTEGER,
				sleStpInstancePortPriority
					INTEGER,
				sleStpInstancePortRole
					INTEGER,
				sleStpInstancePortState
					INTEGER,
				sleStpInstancePortRootBridgeId
					OCTET STRING,
				sleStpInstancePortRootPathcost
					Integer32,
				sleStpInstancePortDesignateBridgeId
					OCTET STRING,
				sleStpInstancePortDesignatePortId
					INTEGER,
				sleStpInstancePortRootGuardMode
					INTEGER
			 }

		-- 1.3.6.1.4.1.6296.101.3.7.1.1.1
		sleStpInstancePortIndex OBJECT-TYPE
			SYNTAX InterfaceIndex
			MAX-ACCESS read-only
			STATUS current
			DESCRIPTION
				"The Port ID."
			::= { sleStpInstancePortEntry 1 }

		
		-- 1.3.6.1.4.1.6296.101.3.7.1.1.2
		sleStpInstancePortPathcost OBJECT-TYPE
			SYNTAX INTEGER (0..200000000)
			MAX-ACCESS read-write
			STATUS current
			DESCRIPTION
				"The STP port path cost."
			::= { sleStpInstancePortEntry 2 }

		
		-- 1.3.6.1.4.1.6296.101.3.7.1.1.3
		sleStpInstancePortPriority OBJECT-TYPE
			SYNTAX INTEGER (0..255)
			MAX-ACCESS read-only
			STATUS current
			DESCRIPTION
				"The STP port priority."
			::= { sleStpInstancePortEntry 3 }

		
		-- 1.3.6.1.4.1.6296.101.3.7.1.1.4
		sleStpInstancePortRole OBJECT-TYPE
			SYNTAX INTEGER
				{
				disable(0),
				designated(1),
				root(2),
				master(3),
				alternate(4),
				backup(5)
				}
			MAX-ACCESS read-only
			STATUS current
			DESCRIPTION
				"The current STP Role of the Port."
			::= { sleStpInstancePortEntry 4 }

		
		-- 1.3.6.1.4.1.6296.101.3.7.1.1.5
		sleStpInstancePortState OBJECT-TYPE
			SYNTAX INTEGER
				{
				disabled(0),
				listening(1),
				learning(2),
				forwarding(3),
				blocking(4)
				}
			MAX-ACCESS read-only
			STATUS current
			DESCRIPTION
				"The STP forwarding state of a specific port."
			::= { sleStpInstancePortEntry 5 }

		
		-- 1.3.6.1.4.1.6296.101.3.7.1.1.6
		sleStpInstancePortRootBridgeId OBJECT-TYPE
			SYNTAX OCTET STRING (SIZE (8))
			MAX-ACCESS read-only
			STATUS current
			DESCRIPTION
				"The unique Bridge Identifier of the Bridge recorded
				as the Root in the Configuration BPDUs transmitted
				by the Designated Bridge for the segment to which
				the port is attached."
			::= { sleStpInstancePortEntry 6 }

		
		-- 1.3.6.1.4.1.6296.101.3.7.1.1.7
		sleStpInstancePortRootPathcost OBJECT-TYPE
			SYNTAX Integer32
			MAX-ACCESS read-only
			STATUS current
			DESCRIPTION
				"The path cost of the Designated Port of the segment
				connected to this port."
			::= { sleStpInstancePortEntry 7 }

		
		-- 1.3.6.1.4.1.6296.101.3.7.1.1.8
		sleStpInstancePortDesignateBridgeId OBJECT-TYPE
			SYNTAX OCTET STRING (SIZE (8))
			MAX-ACCESS read-only
			STATUS current
			DESCRIPTION
				"The Bridge Identifier of the bridge which this port
				considers to be the Designated Bridge for this
				port's segment."
			::= { sleStpInstancePortEntry 8 }

		
		-- 1.3.6.1.4.1.6296.101.3.7.1.1.9
		sleStpInstancePortDesignatePortId OBJECT-TYPE
			SYNTAX INTEGER (0..256)
			MAX-ACCESS read-only
			STATUS current
			DESCRIPTION
				"The Port Identifier of the port on the Designated
				Bridge for this port's segment."
			::= { sleStpInstancePortEntry 9 }

		
		-- 1.3.6.1.4.1.6296.101.3.7.1.1.10
		sleStpInstancePortRootGuardMode OBJECT-TYPE
			SYNTAX INTEGER
				{
				disable(0),
				enable(1)
				}
			MAX-ACCESS read-only
			STATUS current
			DESCRIPTION
				"An indication of whether the RootGuard capability is enabled
					on this port or not.
				 This configuration will be applied to the VLAN or MSTP instance
					in which this port exists.
				
				 Whether the RootGuard capability is enabled or not 
					on this switch depends on the object value of 
					sleStpInstancePortControlRootGuardMode."
			DEFVAL { 0 }
			::= { sleStpInstancePortEntry 10 }

		
		-- 1.3.6.1.4.1.6296.101.3.7.2
		sleStpInstancePortControl OBJECT IDENTIFIER ::= { sleStpInstancePort 2 }

		
		-- 1.3.6.1.4.1.6296.101.3.7.2.1
		sleStpInstancePortControlRequest OBJECT-TYPE
			SYNTAX INTEGER { setStpInstancePortProfile(1) }
			MAX-ACCESS read-write
			STATUS current
			DESCRIPTION
				"
				setStpInstancePortProfile:
				sleStpInstancePortControlIndex
				sleStpInstancePortControlInstanceId
				sleStpInstancePortControlPathcost
				sleStpInstancePortControlPriority
				"
			::= { sleStpInstancePortControl 1 }

		
		-- 1.3.6.1.4.1.6296.101.3.7.2.2
		sleStpInstancePortControlStatus OBJECT-TYPE
			SYNTAX SleControlStatusType
			MAX-ACCESS read-only
			STATUS current
			DESCRIPTION
				"The status of a user command. 
				"
			::= { sleStpInstancePortControl 2 }

		
		-- 1.3.6.1.4.1.6296.101.3.7.2.3
		sleStpInstancePortControlTimer OBJECT-TYPE
			SYNTAX Gauge32
			MAX-ACCESS read-write
			STATUS current
			DESCRIPTION
				"The maximum wait time for the manager for a long running user command. 
				"
			::= { sleStpInstancePortControl 3 }

		
		-- 1.3.6.1.4.1.6296.101.3.7.2.4
		sleStpInstancePortControlTimeStamp OBJECT-TYPE
			SYNTAX TimeTicks
			MAX-ACCESS read-only
			STATUS current
			DESCRIPTION
				"The time stamp of the last command (end of command)."
			::= { sleStpInstancePortControl 4 }

		
		-- 1.3.6.1.4.1.6296.101.3.7.2.5
		sleStpInstancePortControlReqResult OBJECT-TYPE
			SYNTAX SleControlRequestResultType
			MAX-ACCESS read-only
			STATUS current
			DESCRIPTION
				"The result of the last user command."
			::= { sleStpInstancePortControl 5 }

		
		-- 1.3.6.1.4.1.6296.101.3.7.2.6
		sleStpInstancePortControlIndex OBJECT-TYPE
			SYNTAX INTEGER (0..65535)
			MAX-ACCESS read-write
			STATUS current
			DESCRIPTION
				" "
			::= { sleStpInstancePortControl 6 }

		
		-- 1.3.6.1.4.1.6296.101.3.7.2.7
		sleStpInstancePortControlInstanceId OBJECT-TYPE
			SYNTAX INTEGER (0..4096)
			MAX-ACCESS read-write
			STATUS current
			DESCRIPTION
				" "
			::= { sleStpInstancePortControl 7 }

		
		-- 1.3.6.1.4.1.6296.101.3.7.2.8
		sleStpInstancePortControlPathcost OBJECT-TYPE
			SYNTAX INTEGER (0..200000000)
			MAX-ACCESS read-write
			STATUS current
			DESCRIPTION
				" "
			::= { sleStpInstancePortControl 8 }

		
		-- 1.3.6.1.4.1.6296.101.3.7.2.9
		sleStpInstancePortControlPriority OBJECT-TYPE
			SYNTAX INTEGER (0..255)
			MAX-ACCESS read-write
			STATUS current
			DESCRIPTION
				" "
			DEFVAL { 128 }
			::= { sleStpInstancePortControl 9 }

		
		-- 1.3.6.1.4.1.6296.101.3.7.2.10
		sleStpInstancePortControlRootGuardMode OBJECT-TYPE
			SYNTAX INTEGER
				{
				disable(0),
				enable(1)
				}
			MAX-ACCESS read-write
			STATUS current
			DESCRIPTION
				"Enable or disable RootGuard capability on this port.
				 This configuration will be applied to the VLAN or MSTP instance
					in which this port exists."
			DEFVAL { 0 }
			::= { sleStpInstancePortControl 10 }

		
		-- 1.3.6.1.4.1.6296.101.3.7.3
		sleStpInstancePortNotification OBJECT IDENTIFIER ::= { sleStpInstancePort 3 }

		
		-- 1.3.6.1.4.1.6296.101.3.7.3.1
		sleStpInstancePortProfileChanged NOTIFICATION-TYPE
			OBJECTS { sleStpInstancePortControlRequest, sleStpInstancePortControlReqResult, sleStpInstancePortControlTimeStamp, sleStpInstancePortPathcost, sleStpInstancePortPriority, 
				sleStpInstancePortRootGuardMode }
			STATUS current
			DESCRIPTION 
				" "
			::= { sleStpInstancePortNotification 1 }

		
--   sleSubnetVlan Group
-- 1.3.6.1.4.1.6296.9.8.8
		-- 1.3.6.1.4.1.6296.101.3.8
		sleSubnetVlan OBJECT IDENTIFIER ::= { sleBridge 8 }

		
--  1.3.6.1.4.1.6296.9.8.8.1
		-- 1.3.6.1.4.1.6296.101.3.8.1
		sleSubnetVlanTable OBJECT-TYPE
			SYNTAX SEQUENCE OF SleSubnetVlanEntry
			MAX-ACCESS not-accessible
			STATUS current
			DESCRIPTION
				" "
			::= { sleSubnetVlan 1 }

		
--  1.3.6.1.4.1.6296.9.8.8.1.1
		-- 1.3.6.1.4.1.6296.101.3.8.1.1
		sleSubnetVlanEntry OBJECT-TYPE
			SYNTAX SleSubnetVlanEntry
			MAX-ACCESS not-accessible
			STATUS current
			DESCRIPTION
				" "
			INDEX { sleSubnetVlanIp, sleSubnetVlanMask }
			::= { sleSubnetVlanTable 1 }

		
		SleSubnetVlanEntry ::=
			SEQUENCE { 
				sleSubnetVlanIp
					IpAddress,
				sleSubnetVlanMask
					Integer32,
				sleSubnetVlanVid
					Integer32
			 }

--  1.3.6.1.4.1.6296.9.8.8.1.1.2
		-- 1.3.6.1.4.1.6296.101.3.8.1.1.1
		sleSubnetVlanIp OBJECT-TYPE
			SYNTAX IpAddress
			MAX-ACCESS read-only
			STATUS current
			DESCRIPTION
				"Ip address of Subnet"
			::= { sleSubnetVlanEntry 1 }

		
--  1.3.6.1.4.1.6296.9.8.8.1.1.3
		-- 1.3.6.1.4.1.6296.101.3.8.1.1.2
		sleSubnetVlanMask OBJECT-TYPE
			SYNTAX Integer32 (1..32)
			MAX-ACCESS read-only
			STATUS current
			DESCRIPTION
				"Mask bit."
			::= { sleSubnetVlanEntry 2 }

		
--  1.3.6.1.4.1.6296.9.8.8.1.1.4
		-- 1.3.6.1.4.1.6296.101.3.8.1.1.3
		sleSubnetVlanVid OBJECT-TYPE
			SYNTAX Integer32 (1..4094)
			MAX-ACCESS read-only
			STATUS current
			DESCRIPTION
				"Index of the VLAN."
			::= { sleSubnetVlanEntry 3 }

		
--  1.3.6.1.4.1.6296.9.8.8.2
		-- 1.3.6.1.4.1.6296.101.3.8.2
		sleSubnetVlanControl OBJECT IDENTIFIER ::= { sleSubnetVlan 2 }

		
--   Node definitions
-- 
-- 1.3.6.1.4.1.6296.9.8.8.2.1
		-- 1.3.6.1.4.1.6296.101.3.8.2.1
		sleSubnetVlanControlRequest OBJECT-TYPE
			SYNTAX INTEGER
				{
				createSubnetVlan(1),
				destorySubnetVlan(2)
				}
			MAX-ACCESS read-write
			STATUS current
			DESCRIPTION
				"
				createSubnetVlan:
				sleSubnetVlanControlPortIndex
				sleSubnetVlanControlIp
				sleSubnetVlanControlMask
				sleSubnetVlanControlVid
				
				destorySubnetVlan:
				sleSubnetVlanControlPortIndex
				
				"
			::= { sleSubnetVlanControl 1 }

		
--  1.3.6.1.4.1.6296.9.8.8.2.3
		-- 1.3.6.1.4.1.6296.101.3.8.2.2
		sleSubnetVlanControlStatus OBJECT-TYPE
			SYNTAX SleControlStatusType
			MAX-ACCESS read-only
			STATUS current
			DESCRIPTION
				"The status of a user command. 
				"
			::= { sleSubnetVlanControl 2 }

		
--  1.3.6.1.4.1.6296.9.8.8.2.4
		-- 1.3.6.1.4.1.6296.101.3.8.2.3
		sleSubnetVlanControlTimer OBJECT-TYPE
			SYNTAX Gauge32
			MAX-ACCESS read-write
			STATUS current
			DESCRIPTION
				"The maximum wait time for the manager for a long running user command. 
				"
			::= { sleSubnetVlanControl 3 }

		
--  1.3.6.1.4.1.6296.9.8.8.2.6
		-- 1.3.6.1.4.1.6296.101.3.8.2.4
		sleSubnetVlanControlTimeStamp OBJECT-TYPE
			SYNTAX TimeTicks
			MAX-ACCESS read-only
			STATUS current
			DESCRIPTION
				"The time stamp of the last command (end of command)."
			::= { sleSubnetVlanControl 4 }

		
--  1.3.6.1.4.1.6296.9.8.8.2.5
		-- 1.3.6.1.4.1.6296.101.3.8.2.5
		sleSubnetVlanControlReqResult OBJECT-TYPE
			SYNTAX SleControlRequestResultType
			MAX-ACCESS read-only
			STATUS current
			DESCRIPTION
				"The result of the last user command."
			::= { sleSubnetVlanControl 5 }

		
--  1.3.6.1.4.1.6296.9.8.8.2.7
		-- 1.3.6.1.4.1.6296.101.3.8.2.6
		sleSubnetVlanControlIp OBJECT-TYPE
			SYNTAX IpAddress
			MAX-ACCESS read-write
			STATUS current
			DESCRIPTION
				"IP address"
			::= { sleSubnetVlanControl 6 }

		
--  1.3.6.1.4.1.6296.9.8.8.2.8
		-- 1.3.6.1.4.1.6296.101.3.8.2.7
		sleSubnetVlanControlMask OBJECT-TYPE
			SYNTAX Integer32 (1..32)
			MAX-ACCESS read-write
			STATUS current
			DESCRIPTION
				"Mask bit
				"
			::= { sleSubnetVlanControl 7 }

		
--  1.3.6.1.4.1.6296.9.8.8.2.9
		-- 1.3.6.1.4.1.6296.101.3.8.2.8
		sleSubnetVlanControlVid OBJECT-TYPE
			SYNTAX Integer32 (1..4094)
			MAX-ACCESS read-write
			STATUS current
			DESCRIPTION
				"Vlan's ID"
			::= { sleSubnetVlanControl 8 }

		
--  1.3.6.1.4.1.6296.9.8.8.3
		-- 1.3.6.1.4.1.6296.101.3.8.3
		sleSubnetVlanNotification OBJECT IDENTIFIER ::= { sleSubnetVlan 3 }

		
--  1.3.6.1.4.1.6296.9.8.8.3.1
		-- 1.3.6.1.4.1.6296.101.3.8.3.1
		sleSubnetVlanCreated NOTIFICATION-TYPE
			OBJECTS { sleSubnetVlanControlTimeStamp, sleSubnetVlanControlReqResult, sleSubnetVlanControlRequest, sleSubnetVlanVid }
			STATUS current
			DESCRIPTION 
				" "
			::= { sleSubnetVlanNotification 1 }

		
--  1.3.6.1.4.1.6296.9.8.8.3.2
		-- 1.3.6.1.4.1.6296.101.3.8.3.2
		sleSubnetVlanDestroyed NOTIFICATION-TYPE
			OBJECTS { sleSubnetVlanControlRequest, sleSubnetVlanControlTimeStamp, sleSubnetVlanControlReqResult, sleSubnetVlanVid }
			STATUS current
			DESCRIPTION 
				" "
			::= { sleSubnetVlanNotification 2 }

		
--   sleProtocolVlan Group
-- 1.3.6.1.4.1.6296.9.8.9
		-- 1.3.6.1.4.1.6296.101.3.9
		sleProtocolVlan OBJECT IDENTIFIER ::= { sleBridge 9 }

		
--  1.3.6.1.4.1.6296.9.8.9.1
		-- 1.3.6.1.4.1.6296.101.3.9.1
		sleProtocolVlanTable OBJECT-TYPE
			SYNTAX SEQUENCE OF SleProtocolVlanEntry
			MAX-ACCESS not-accessible
			STATUS current
			DESCRIPTION
				" "
			::= { sleProtocolVlan 1 }

		
--  1.3.6.1.4.1.6296.9.8.9.1.1
		-- 1.3.6.1.4.1.6296.101.3.9.1.1
		sleProtocolVlanEntry OBJECT-TYPE
			SYNTAX SleProtocolVlanEntry
			MAX-ACCESS not-accessible
			STATUS current
			DESCRIPTION
				" "
			INDEX { sleBridgePortIndex, sleProtocolVlanEtype }
			::= { sleProtocolVlanTable 1 }

		
		SleProtocolVlanEntry ::=
			SEQUENCE { 
				sleProtocolVlanEtype
					Unsigned32,
				sleProtocolVlanVid
					Integer32
			 }

--  1.3.6.1.4.1.6296.9.8.9.1.1.2
		-- 1.3.6.1.4.1.6296.101.3.9.1.1.1
		sleProtocolVlanEtype OBJECT-TYPE
			SYNTAX Unsigned32 (1..65535)
			MAX-ACCESS read-only
			STATUS current
			DESCRIPTION
				"Ethernet type"
			::= { sleProtocolVlanEntry 1 }

		
--  1.3.6.1.4.1.6296.9.8.9.1.1.3
		-- 1.3.6.1.4.1.6296.101.3.9.1.1.2
		sleProtocolVlanVid OBJECT-TYPE
			SYNTAX Integer32 (1..4094)
			MAX-ACCESS read-only
			STATUS current
			DESCRIPTION
				"Index of the VLAN."
			::= { sleProtocolVlanEntry 2 }

		
--  1.3.6.1.4.1.6296.9.8.9.2
		-- 1.3.6.1.4.1.6296.101.3.9.2
		sleProtocolVlanControl OBJECT IDENTIFIER ::= { sleProtocolVlan 2 }

		
--   Node definitions
-- 
-- 1.3.6.1.4.1.6296.9.8.9.2.1
		-- 1.3.6.1.4.1.6296.101.3.9.2.1
		sleProtocolVlanControlRequest OBJECT-TYPE
			SYNTAX INTEGER
				{
				createProtocolVlan(1),
				destoryProtocolVlan(2)
				}
			MAX-ACCESS read-write
			STATUS current
			DESCRIPTION
				"
				createProtocolVlan:
				sleProtocolVlanControlPortIndex
				sleProtocolVlanControlEtype
				sleProtocolVlanControlVid
				
				destoryProtocolVlan:
				sleProtocolVlanControlPortIndex
				
				"
			::= { sleProtocolVlanControl 1 }

		
--  1.3.6.1.4.1.6296.9.8.9.2.3
		-- 1.3.6.1.4.1.6296.101.3.9.2.2
		sleProtocolVlanControlStatus OBJECT-TYPE
			SYNTAX SleControlStatusType
			MAX-ACCESS read-only
			STATUS current
			DESCRIPTION
				"The status of a user command. 
				"
			::= { sleProtocolVlanControl 2 }

		
--  1.3.6.1.4.1.6296.9.8.9.2.4
		-- 1.3.6.1.4.1.6296.101.3.9.2.3
		sleProtocolVlanControlTimer OBJECT-TYPE
			SYNTAX Gauge32
			MAX-ACCESS read-write
			STATUS current
			DESCRIPTION
				"The maximum wait time for the manager for a long running user command. 
				"
			::= { sleProtocolVlanControl 3 }

		
--  1.3.6.1.4.1.6296.9.8.9.2.6
		-- 1.3.6.1.4.1.6296.101.3.9.2.4
		sleProtocolVlanControlTimeStamp OBJECT-TYPE
			SYNTAX TimeTicks
			MAX-ACCESS read-only
			STATUS current
			DESCRIPTION
				"The time stamp of the last command (end of command)."
			::= { sleProtocolVlanControl 4 }

		
--  1.3.6.1.4.1.6296.9.8.9.2.5
		-- 1.3.6.1.4.1.6296.101.3.9.2.5
		sleProtocolVlanControlReqResult OBJECT-TYPE
			SYNTAX SleControlRequestResultType
			MAX-ACCESS read-only
			STATUS current
			DESCRIPTION
				"The result of the last user command."
			::= { sleProtocolVlanControl 5 }

		
--  1.3.6.1.4.1.6296.9.8.9.2.2
		-- 1.3.6.1.4.1.6296.101.3.9.2.6
		sleProtocolVlanControlPortIndex OBJECT-TYPE
			SYNTAX InterfaceIndex
			MAX-ACCESS read-write
			STATUS current
			DESCRIPTION
				" "
			::= { sleProtocolVlanControl 6 }

		
--  1.3.6.1.4.1.6296.9.8.9.2.7
		-- 1.3.6.1.4.1.6296.101.3.9.2.7
		sleProtocolVlanControlEtype OBJECT-TYPE
			SYNTAX Unsigned32
			MAX-ACCESS read-write
			STATUS current
			DESCRIPTION
				"Ethernet Type"
			::= { sleProtocolVlanControl 7 }

		
--  1.3.6.1.4.1.6296.9.8.9.2.8
		-- 1.3.6.1.4.1.6296.101.3.9.2.8
		sleProtocolVlanControlVid OBJECT-TYPE
			SYNTAX Integer32 (1..4094)
			MAX-ACCESS read-write
			STATUS current
			DESCRIPTION
				" "
			::= { sleProtocolVlanControl 8 }

		
--  1.3.6.1.4.1.6296.9.8.9.3
		-- 1.3.6.1.4.1.6296.101.3.9.3
		sleProtocolVlanNotification OBJECT IDENTIFIER ::= { sleProtocolVlan 3 }

		
--  1.3.6.1.4.1.6296.9.8.9.3.1
		-- 1.3.6.1.4.1.6296.101.3.9.3.1
		sleProtocolVlanCreated NOTIFICATION-TYPE
			OBJECTS { sleProtocolVlanVid, sleProtocolVlanControlRequest, sleProtocolVlanControlTimeStamp, sleProtocolVlanControlReqResult }
			STATUS current
			DESCRIPTION 
				" "
			::= { sleProtocolVlanNotification 1 }

		
--  1.3.6.1.4.1.6296.9.8.9.3.2
		-- 1.3.6.1.4.1.6296.101.3.9.3.2
		sleProtocolVlanDestroyed NOTIFICATION-TYPE
			OBJECTS { sleProtocolVlanControlRequest, sleProtocolVlanControlTimeStamp, sleProtocolVlanControlReqResult, sleProtocolVlanVid }
			STATUS current
			DESCRIPTION 
				" "
			::= { sleProtocolVlanNotification 2 }

		
--  1.3.6.1.4.1.6296.9.8.10
		-- 1.3.6.1.4.1.6296.101.3.10
		sleLag OBJECT IDENTIFIER ::= { sleBridge 10 }

		
--  1.3.6.1.4.1.6296.9.8.10.1
		-- 1.3.6.1.4.1.6296.101.3.10.1
		sleLagTable OBJECT-TYPE
			SYNTAX SEQUENCE OF SleLagEntry
			MAX-ACCESS not-accessible
			STATUS current
			DESCRIPTION
				" "
			::= { sleLag 1 }

		
--  1.3.6.1.4.1.6296.9.8.10.1.1
		-- 1.3.6.1.4.1.6296.101.3.10.1.1
		sleLagEntry OBJECT-TYPE
			SYNTAX SleLagEntry
			MAX-ACCESS not-accessible
			STATUS current
			DESCRIPTION
				" "
			INDEX { sleLagIndex }
			::= { sleLagTable 1 }

		
		SleLagEntry ::=
			SEQUENCE { 
				sleLagIndex
					Integer32,
				sleLagPortId
					InterfaceIndex,
				sleLagDistMode
					INTEGER,
				sleLagPortMap
					OCTET STRING,
				sleLagMode
					INTEGER
			 }

--  1.3.6.1.4.1.6296.9.8.10.1.1.1
		-- 1.3.6.1.4.1.6296.101.3.10.1.1.1
		sleLagIndex OBJECT-TYPE
			SYNTAX Integer32 (0..13)
			MAX-ACCESS read-only
			STATUS current
			DESCRIPTION
				"This value assigned to the aggregation ID."
			::= { sleLagEntry 1 }

		
--  1.3.6.1.4.1.6296.9.8.10.1.1.2
		-- 1.3.6.1.4.1.6296.101.3.10.1.1.2
		sleLagPortId OBJECT-TYPE
			SYNTAX InterfaceIndex
			MAX-ACCESS read-only
			STATUS current
			DESCRIPTION
				"Port ID of aggregation."
			::= { sleLagEntry 2 }

		
--  1.3.6.1.4.1.6296.9.8.10.1.1.3
		-- 1.3.6.1.4.1.6296.101.3.10.1.1.3
		sleLagDistMode OBJECT-TYPE
			SYNTAX INTEGER
				{
				srcmac(1),
				dstmac(2),
				srcdstmac(3),
				srcip(4),
				dstip(5),
				srcdstip(6)
				}
			MAX-ACCESS read-only
			STATUS current
			DESCRIPTION
				"This value assigned to the distributing 
				mode of link aggregation."
			::= { sleLagEntry 3 }

		
--  1.3.6.1.4.1.6296.9.8.10.1.1.4
		-- 1.3.6.1.4.1.6296.101.3.10.1.1.4
		sleLagPortMap OBJECT-TYPE
			SYNTAX OCTET STRING
			MAX-ACCESS read-only
			STATUS current
			DESCRIPTION
				"The value assigned to the port list of  the aggregation."
			::= { sleLagEntry 4 }

		
--  1.3.6.1.4.1.6296.9.8.10.1.1.5
		-- 1.3.6.1.4.1.6296.101.3.10.1.1.5
		sleLagMode OBJECT-TYPE
			SYNTAX INTEGER
				{
				trunk(1),
				lacp(2)
				}
			MAX-ACCESS read-only
			STATUS current
			DESCRIPTION
				"The operation mode of  link aggregation."
			::= { sleLagEntry 5 }

		
--  1.3.6.1.4.1.6296.9.8.10.2
		-- 1.3.6.1.4.1.6296.101.3.10.2
		sleLagControl OBJECT IDENTIFIER ::= { sleLag 2 }

		
--  1.3.6.1.4.1.6296.9.8.10.2.1
		-- 1.3.6.1.4.1.6296.101.3.10.2.1
		sleLagControlRequest OBJECT-TYPE
			SYNTAX INTEGER { setLagProfile(1) }
			MAX-ACCESS read-write
			STATUS current
			DESCRIPTION
				"The MIB object for the user command.."
			::= { sleLagControl 1 }

		
--  1.3.6.1.4.1.6296.9.8.10.2.2
		-- 1.3.6.1.4.1.6296.101.3.10.2.2
		sleLagControlStatus OBJECT-TYPE
			SYNTAX SleControlStatusType
			MAX-ACCESS read-only
			STATUS current
			DESCRIPTION
				"Describes the status of a user command group, 
				used for block commands while a command execution in process."
			::= { sleLagControl 2 }

		
--  1.3.6.1.4.1.6296.9.8.10.2.3
		-- 1.3.6.1.4.1.6296.101.3.10.2.3
		sleLagControlTimer OBJECT-TYPE
			SYNTAX Gauge32
			MAX-ACCESS read-write
			STATUS current
			DESCRIPTION
				"Maximum command duration time in case of long running"
			::= { sleLagControl 3 }

		
--  1.3.6.1.4.1.6296.9.8.10.2.5
		-- 1.3.6.1.4.1.6296.101.3.10.2.4
		sleLagControlTimeStamp OBJECT-TYPE
			SYNTAX SleControlRequestResultType
			MAX-ACCESS read-only
			STATUS current
			DESCRIPTION
				"Command result attribute"
			::= { sleLagControl 4 }

		
--  1.3.6.1.4.1.6296.9.8.10.2.4
		-- 1.3.6.1.4.1.6296.101.3.10.2.5
		sleLagControlReqResult OBJECT-TYPE
			SYNTAX TimeStamp
			MAX-ACCESS read-only
			STATUS current
			DESCRIPTION
				"Time stamp attribute set at end of command."
			::= { sleLagControl 5 }

		
--  1.3.6.1.4.1.6296.9.8.10.2.6
		-- 1.3.6.1.4.1.6296.101.3.10.2.6
		sleLagControlIndex OBJECT-TYPE
			SYNTAX Integer32
			MAX-ACCESS read-write
			STATUS current
			DESCRIPTION
				"This value assigned to the aggregation ID."
			::= { sleLagControl 6 }

		
--  1.3.6.1.4.1.6296.9.8.10.2.7
		-- 1.3.6.1.4.1.6296.101.3.10.2.7
		sleLagControlDistMode OBJECT-TYPE
			SYNTAX INTEGER
				{
				srcmac(1),
				dstmac(2),
				srcdstmac(3),
				srcip(4),
				dstip(5),
				srcdstip(6)
				}
			MAX-ACCESS read-write
			STATUS current
			DESCRIPTION
				"This value assigned to the distributing mode of link aggregation."
			::= { sleLagControl 7 }

		
--  1.3.6.1.4.1.6296.9.8.10.2.8
		-- 1.3.6.1.4.1.6296.101.3.10.2.8
		sleLagControlPortMap OBJECT-TYPE
			SYNTAX OCTET STRING
			MAX-ACCESS read-write
			STATUS current
			DESCRIPTION
				"Port ID of aggregation."
			::= { sleLagControl 8 }

		
--  1.3.6.1.4.1.6296.9.8.10.2.9
		-- 1.3.6.1.4.1.6296.101.3.10.2.9
		sleLagControlMode OBJECT-TYPE
			SYNTAX INTEGER
				{
				trunk(1),
				lacp(2)
				}
			MAX-ACCESS read-write
			STATUS current
			DESCRIPTION
				"The operation mode of  link aggregation."
			::= { sleLagControl 9 }

		
--  1.3.6.1.4.1.6296.9.8.10.3
		-- 1.3.6.1.4.1.6296.101.3.10.3
		sleLagNotification OBJECT IDENTIFIER ::= { sleLag 3 }

		
--  1.3.6.1.4.1.6296.9.8.10.3.1
		-- 1.3.6.1.4.1.6296.101.3.10.3.1
		sleLagProfileChanged NOTIFICATION-TYPE
			OBJECTS { sleLagControlRequest, sleLagControlReqResult, sleLagControlTimeStamp, sleLagPortMap, sleLagDistMode, 
				sleLagMode }
			STATUS current
			DESCRIPTION 
				" "
			::= { sleLagNotification 1 }

		
--  1.3.6.1.4.1.6296.9.8.11
		-- 1.3.6.1.4.1.6296.101.3.11
		sleLagLacp OBJECT IDENTIFIER ::= { sleBridge 11 }

		
--  1.3.6.1.4.1.6296.9.8.11.1
		-- 1.3.6.1.4.1.6296.101.3.11.1
		sleLagLacpTable OBJECT-TYPE
			SYNTAX SEQUENCE OF SleLagLacpEntry
			MAX-ACCESS not-accessible
			STATUS current
			DESCRIPTION
				" "
			::= { sleLagLacp 1 }

		
--  1.3.6.1.4.1.6296.9.8.11.1.1
		-- 1.3.6.1.4.1.6296.101.3.11.1.1
		sleLagLacpEntry OBJECT-TYPE
			SYNTAX SleLagLacpEntry
			MAX-ACCESS not-accessible
			STATUS current
			DESCRIPTION
				" "
			INDEX { sleLagLacpIndex }
			::= { sleLagLacpTable 1 }

		
		SleLagLacpEntry ::=
			SEQUENCE { 
				sleLagLacpIndex
					Integer32,
				sleLagLacpActorAggregatorKey
					Integer32,
				sleLagLacpActorSystemMAC
					OCTET STRING,
				sleLagLacpPartnerSystemMAC
					OCTET STRING,
				sleLagLacpPartnerSystemPriority
					Integer32,
				sleLagLacpPartnerAggregatorKey
					Integer32
			 }

--  1.3.6.1.4.1.6296.9.8.11.1.1.1
		-- 1.3.6.1.4.1.6296.101.3.11.1.1.1
		sleLagLacpIndex OBJECT-TYPE
			SYNTAX Integer32 (0..13)
			MAX-ACCESS read-only
			STATUS current
			DESCRIPTION
				"Location of authentication."
			::= { sleLagLacpEntry 1 }

		
--  1.3.6.1.4.1.6296.9.8.11.1.1.2
		-- 1.3.6.1.4.1.6296.101.3.11.1.1.2
		sleLagLacpActorAggregatorKey OBJECT-TYPE
			SYNTAX Integer32 (1..65535)
			MAX-ACCESS read-only
			STATUS current
			DESCRIPTION
				"The kind of authentication."
			::= { sleLagLacpEntry 2 }

		
		-- 1.3.6.1.4.1.6296.101.3.11.1.1.3
		sleLagLacpActorSystemMAC OBJECT-TYPE
			SYNTAX OCTET STRING
			MAX-ACCESS read-write
			STATUS current
			DESCRIPTION
				"Description."
			::= { sleLagLacpEntry 3 }

		
--  1.3.6.1.4.1.6296.9.8.11.1.1.3
		-- 1.3.6.1.4.1.6296.101.3.11.1.1.4
		sleLagLacpPartnerSystemMAC OBJECT-TYPE
			SYNTAX OCTET STRING
			MAX-ACCESS read-only
			STATUS current
			DESCRIPTION
				"Enable or disable the corresponding authen method."
			::= { sleLagLacpEntry 4 }

		
--  1.3.6.1.4.1.6296.9.8.11.1.1.4
		-- 1.3.6.1.4.1.6296.101.3.11.1.1.5
		sleLagLacpPartnerSystemPriority OBJECT-TYPE
			SYNTAX Integer32 (1..65535)
			MAX-ACCESS read-only
			STATUS current
			DESCRIPTION
				"The primary priority of the corresponding authen method."
			::= { sleLagLacpEntry 5 }

		
--  1.3.6.1.4.1.6296.9.8.11.1.1.5
		-- 1.3.6.1.4.1.6296.101.3.11.1.1.6
		sleLagLacpPartnerAggregatorKey OBJECT-TYPE
			SYNTAX Integer32 (1..65535)
			MAX-ACCESS read-only
			STATUS current
			DESCRIPTION
				" "
			::= { sleLagLacpEntry 6 }

		
--  1.3.6.1.4.1.6296.9.8.12
		-- 1.3.6.1.4.1.6296.101.3.12
		sleLagLacpPort OBJECT IDENTIFIER ::= { sleBridge 12 }

		
--  1.3.6.1.4.1.6296.9.8.12.1
		-- 1.3.6.1.4.1.6296.101.3.12.1
		sleLagLacpPortTable OBJECT-TYPE
			SYNTAX SEQUENCE OF SleLagLacpPortEntry
			MAX-ACCESS not-accessible
			STATUS current
			DESCRIPTION
				" "
			::= { sleLagLacpPort 1 }

		
--  1.3.6.1.4.1.6296.9.8.12.1.1
		-- 1.3.6.1.4.1.6296.101.3.12.1.1
		sleLagLacpPortEntry OBJECT-TYPE
			SYNTAX SleLagLacpPortEntry
			MAX-ACCESS not-accessible
			STATUS current
			DESCRIPTION
				" "
			INDEX { sleLagLacpPortIndex }
			::= { sleLagLacpPortTable 1 }

		
		SleLagLacpPortEntry ::=
			SEQUENCE { 
				sleLagLacpPortIndex
					InterfaceIndex,
				sleLagLacpPortActivity
					INTEGER,
				sleLagLacpPortActorPriority
					INTEGER,
				sleLagLacpPortActorAggregatorId
					Integer32,
				sleLagLacpPortActorAdminKey
					INTEGER,
				sleLagLacpPortActorAdminState
					BITS,
				sleLagLacpPortActorOperKey
					Integer32,
				sleLagLacpPortActorOperState
					BITS,
				sleLagLacpPortPartnerAdminSystemMAC
					OCTET STRING,
				sleLagLacpPortPartnerAdminSystemPriority
					Integer32,
				sleLagLacpPortPartnerAdminKey
					Integer32,
				sleLagLacpPortPartnerAdminNum
					InterfaceIndex,
				sleLagLacpPortPartnerAdminPriority
					Integer32,
				sleLagLacpPortPartnerAdminState
					BITS,
				sleLagLacpPortPartnerOperSystemMAC
					OCTET STRING,
				sleLagLacpPortPartnerOperSystemPriority
					Integer32,
				sleLagLacpPortPartnerOperKey
					Integer32,
				sleLagLacpPortPartnerOperNum
					InterfaceIndex,
				sleLagLacpPortPartnerOperPriority
					Integer32,
				sleLagLacpPortPartnerOperState
					BITS
			 }

--  1.3.6.1.4.1.6296.9.8.12.1.1.1
		-- 1.3.6.1.4.1.6296.101.3.12.1.1.1
		sleLagLacpPortIndex OBJECT-TYPE
			SYNTAX InterfaceIndex
			MAX-ACCESS read-only
			STATUS current
			DESCRIPTION
				"The IP address of the RADIUS server referred 
				to in this table entry."
			::= { sleLagLacpPortEntry 1 }

		
		-- 1.3.6.1.4.1.6296.101.3.12.1.1.2
		sleLagLacpPortActivity OBJECT-TYPE
			SYNTAX INTEGER
				{
				disable(0),
				enable(1)
				}
			MAX-ACCESS read-only
			STATUS current
			DESCRIPTION
				"Description."
			::= { sleLagLacpPortEntry 2 }

		
--  1.3.6.1.4.1.6296.9.8.12.1.1.2
		-- 1.3.6.1.4.1.6296.101.3.12.1.1.3
		sleLagLacpPortActorPriority OBJECT-TYPE
			SYNTAX INTEGER (1..65535)
			MAX-ACCESS read-only
			STATUS current
			DESCRIPTION
				"The priority assigned to the port by Actor."
			::= { sleLagLacpPortEntry 3 }

		
--  1.3.6.1.4.1.6296.9.8.12.1.1.3
		-- 1.3.6.1.4.1.6296.101.3.12.1.1.4
		sleLagLacpPortActorAggregatorId OBJECT-TYPE
			SYNTAX Integer32
			MAX-ACCESS read-only
			STATUS current
			DESCRIPTION
				" "
			::= { sleLagLacpPortEntry 4 }

		
--  1.3.6.1.4.1.6296.9.8.12.1.1.4
		-- 1.3.6.1.4.1.6296.101.3.12.1.1.5
		sleLagLacpPortActorAdminKey OBJECT-TYPE
			SYNTAX INTEGER (1..65535)
			MAX-ACCESS read-only
			STATUS current
			DESCRIPTION
				"The administrable Key value assigned to the 
				port by the Actor."
			::= { sleLagLacpPortEntry 5 }

		
--  1.3.6.1.4.1.6296.9.8.12.1.1.5
		-- 1.3.6.1.4.1.6296.101.3.12.1.1.6
		sleLagLacpPortActorAdminState OBJECT-TYPE
			SYNTAX BITS
				{
				expired(0),
				defaulted(1),
				destributing(2),
				collecting(3),
				synchronization(4),
				aggregation(5),
				lacpTimeout(6),
				lacpActivity(7)
				}
			MAX-ACCESS read-only
			STATUS current
			DESCRIPTION
				"The Actor's administrable state variables for the port."
			::= { sleLagLacpPortEntry 6 }

		
--  1.3.6.1.4.1.6296.9.8.12.1.1.6
		-- 1.3.6.1.4.1.6296.101.3.12.1.1.7
		sleLagLacpPortActorOperKey OBJECT-TYPE
			SYNTAX Integer32 (1..65535)
			MAX-ACCESS read-only
			STATUS current
			DESCRIPTION
				"The operational Key value assigned to the 
				port by the Actor."
			::= { sleLagLacpPortEntry 7 }

		
--  1.3.6.1.4.1.6296.9.8.12.1.1.7
		-- 1.3.6.1.4.1.6296.101.3.12.1.1.8
		sleLagLacpPortActorOperState OBJECT-TYPE
			SYNTAX BITS
				{
				expired(0),
				defaulted(1),
				destributing(2),
				collecting(3),
				synchronization(4),
				aggregation(5),
				lacpTmeout(6),
				lacpActivity(7)
				}
			MAX-ACCESS read-only
			STATUS current
			DESCRIPTION
				"The Actor's operational state variables for the port."
			::= { sleLagLacpPortEntry 8 }

		
--  1.3.6.1.4.1.6296.9.8.12.1.1.8
		-- 1.3.6.1.4.1.6296.101.3.12.1.1.9
		sleLagLacpPortPartnerAdminSystemMAC OBJECT-TYPE
			SYNTAX OCTET STRING
			MAX-ACCESS read-only
			STATUS current
			DESCRIPTION
				"The Partner's Administrable System ID, 
				encoded as a MAC address."
			::= { sleLagLacpPortEntry 9 }

		
--  1.3.6.1.4.1.6296.9.8.12.1.1.9
		-- 1.3.6.1.4.1.6296.101.3.12.1.1.10
		sleLagLacpPortPartnerAdminSystemPriority OBJECT-TYPE
			SYNTAX Integer32 (1..65535)
			MAX-ACCESS read-only
			STATUS current
			DESCRIPTION
				"The administrable priority assigned to the 
				Partner System."
			::= { sleLagLacpPortEntry 10 }

		
--  1.3.6.1.4.1.6296.9.8.12.1.1.10
		-- 1.3.6.1.4.1.6296.101.3.12.1.1.11
		sleLagLacpPortPartnerAdminKey OBJECT-TYPE
			SYNTAX Integer32 (1..65535)
			MAX-ACCESS read-only
			STATUS current
			DESCRIPTION
				"The administrable Key value assigned to 
				the port by the Partner."
			::= { sleLagLacpPortEntry 11 }

		
--  1.3.6.1.4.1.6296.9.8.12.1.1.11
		-- 1.3.6.1.4.1.6296.101.3.12.1.1.12
		sleLagLacpPortPartnerAdminNum OBJECT-TYPE
			SYNTAX InterfaceIndex
			MAX-ACCESS read-only
			STATUS current
			DESCRIPTION
				"The administrable number value assigned 
				to the port by the Partner."
			::= { sleLagLacpPortEntry 12 }

		
--  1.3.6.1.4.1.6296.9.8.12.1.1.12
		-- 1.3.6.1.4.1.6296.101.3.12.1.1.13
		sleLagLacpPortPartnerAdminPriority OBJECT-TYPE
			SYNTAX Integer32 (1..65535)
			MAX-ACCESS read-only
			STATUS current
			DESCRIPTION
				"The administrable priority assigned to 
				this port by the Partner."
			::= { sleLagLacpPortEntry 13 }

		
--  1.3.6.1.4.1.6296.9.8.12.1.1.13
		-- 1.3.6.1.4.1.6296.101.3.12.1.1.14
		sleLagLacpPortPartnerAdminState OBJECT-TYPE
			SYNTAX BITS
				{
				expired(0),
				defaulted(1),
				destributing(2),
				collecting(3),
				synchronization(4),
				aggregation(5),
				lacpTmeout(6),
				lacpActivity(7)
				}
			MAX-ACCESS read-only
			STATUS current
			DESCRIPTION
				"The administrable state assigned to this 
				port by the Partner."
			::= { sleLagLacpPortEntry 14 }

		
--  1.3.6.1.4.1.6296.9.8.12.1.1.14
		-- 1.3.6.1.4.1.6296.101.3.12.1.1.15
		sleLagLacpPortPartnerOperSystemMAC OBJECT-TYPE
			SYNTAX OCTET STRING
			MAX-ACCESS read-only
			STATUS current
			DESCRIPTION
				"The Partner's operational System ID, 
				encoded as a MAC address."
			::= { sleLagLacpPortEntry 15 }

		
--  1.3.6.1.4.1.6296.9.8.12.1.1.15
		-- 1.3.6.1.4.1.6296.101.3.12.1.1.16
		sleLagLacpPortPartnerOperSystemPriority OBJECT-TYPE
			SYNTAX Integer32 (1..65535)
			MAX-ACCESS read-only
			STATUS current
			DESCRIPTION
				"The operational priority assigned to 
				the Partner System."
			::= { sleLagLacpPortEntry 16 }

		
--  1.3.6.1.4.1.6296.9.8.12.1.1.16
		-- 1.3.6.1.4.1.6296.101.3.12.1.1.17
		sleLagLacpPortPartnerOperKey OBJECT-TYPE
			SYNTAX Integer32 (1..65535)
			MAX-ACCESS read-only
			STATUS current
			DESCRIPTION
				"The operational Key value assigned to the 
				port by the Partner."
			::= { sleLagLacpPortEntry 17 }

		
--  1.3.6.1.4.1.6296.9.8.12.1.1.17
		-- 1.3.6.1.4.1.6296.101.3.12.1.1.18
		sleLagLacpPortPartnerOperNum OBJECT-TYPE
			SYNTAX InterfaceIndex
			MAX-ACCESS read-only
			STATUS current
			DESCRIPTION
				"The operational number value assigned to 
				the port by the Partner."
			::= { sleLagLacpPortEntry 18 }

		
--  1.3.6.1.4.1.6296.9.8.12.1.1.18
		-- 1.3.6.1.4.1.6296.101.3.12.1.1.19
		sleLagLacpPortPartnerOperPriority OBJECT-TYPE
			SYNTAX Integer32 (1..65535)
			MAX-ACCESS read-only
			STATUS current
			DESCRIPTION
				"The operational priority assigned to 
				this port by the Partner."
			::= { sleLagLacpPortEntry 19 }

		
--  1.3.6.1.4.1.6296.9.8.12.1.1.19
		-- 1.3.6.1.4.1.6296.101.3.12.1.1.20
		sleLagLacpPortPartnerOperState OBJECT-TYPE
			SYNTAX BITS
				{
				expired(0),
				defaulted(1),
				destributing(2),
				collecting(3),
				synchronization(4),
				aggregation(5),
				lacpTimeout(6),
				lacpActivity(7)
				}
			MAX-ACCESS read-only
			STATUS current
			DESCRIPTION
				"The operational state assigned to this 
				port by the Partner."
			::= { sleLagLacpPortEntry 20 }

		
--  1.3.6.1.4.1.6296.9.8.12.2
		-- 1.3.6.1.4.1.6296.101.3.12.2
		sleLagLacpPortControl OBJECT IDENTIFIER ::= { sleLagLacpPort 2 }

		
--  1.3.6.1.4.1.6296.9.8.12.2.1
		-- 1.3.6.1.4.1.6296.101.3.12.2.1
		sleLagLacpPortControlRequest OBJECT-TYPE
			SYNTAX INTEGER { setLagLacpPortProfile(1) }
			MAX-ACCESS read-write
			STATUS current
			DESCRIPTION
				"The MIB object for the user command."
			::= { sleLagLacpPortControl 1 }

		
--  1.3.6.1.4.1.6296.9.8.12.2.2
		-- 1.3.6.1.4.1.6296.101.3.12.2.2
		sleLagLacpPortControlStatus OBJECT-TYPE
			SYNTAX SleControlStatusType
			MAX-ACCESS read-only
			STATUS current
			DESCRIPTION
				"Describes the status of a user command group, 
				used for block commands while a command execution in process."
			::= { sleLagLacpPortControl 2 }

		
--  1.3.6.1.4.1.6296.9.8.12.2.3
		-- 1.3.6.1.4.1.6296.101.3.12.2.3
		sleLagLacpPortControlTimer OBJECT-TYPE
			SYNTAX Gauge32
			MAX-ACCESS read-write
			STATUS current
			DESCRIPTION
				"Maximum command duration time in case of long running"
			::= { sleLagLacpPortControl 3 }

		
--  1.3.6.1.4.1.6296.9.8.12.2.5
		-- 1.3.6.1.4.1.6296.101.3.12.2.4
		sleLagLacpPortControlTimeStamp OBJECT-TYPE
			SYNTAX TimeStamp
			MAX-ACCESS read-only
			STATUS current
			DESCRIPTION
				"Time stamp attribute set at end of command."
			::= { sleLagLacpPortControl 4 }

		
--  1.3.6.1.4.1.6296.9.8.12.2.4
		-- 1.3.6.1.4.1.6296.101.3.12.2.5
		sleLagLacpPortControlReqResult OBJECT-TYPE
			SYNTAX SleControlRequestResultType
			MAX-ACCESS read-only
			STATUS current
			DESCRIPTION
				"Command result attribute."
			::= { sleLagLacpPortControl 5 }

		
--  1.3.6.1.4.1.6296.9.8.12.2.6
		-- 1.3.6.1.4.1.6296.101.3.12.2.6
		sleLagLacpPortControlIndex OBJECT-TYPE
			SYNTAX InterfaceIndex
			MAX-ACCESS read-write
			STATUS current
			DESCRIPTION
				"The IP address of the RADIUS server referred to 
				in this table entry."
			::= { sleLagLacpPortControl 6 }

		
		-- 1.3.6.1.4.1.6296.101.3.12.2.7
		sleLagLacpPortControlActivity OBJECT-TYPE
			SYNTAX INTEGER
				{
				disable(0),
				enable(1)
				}
			MAX-ACCESS read-write
			STATUS current
			DESCRIPTION
				"Description."
			::= { sleLagLacpPortControl 7 }

		
--  1.3.6.1.4.1.6296.9.8.12.2.7
		-- 1.3.6.1.4.1.6296.101.3.12.2.8
		sleLagLacpPortControlMode OBJECT-TYPE
			SYNTAX INTEGER
				{
				active(1),
				passive(2)
				}
			MAX-ACCESS read-write
			STATUS current
			DESCRIPTION
				"set LACP_Activity in sleLagLacpPortActorAdminState"
			::= { sleLagLacpPortControl 8 }

		
--  1.3.6.1.4.1.6296.9.8.12.2.8
		-- 1.3.6.1.4.1.6296.101.3.12.2.9
		sleLagLacpPortControlAdminKey OBJECT-TYPE
			SYNTAX Integer32 (0..15)
			MAX-ACCESS read-write
			STATUS current
			DESCRIPTION
				"The administrable Key value assigned to the 
				port by the Actor."
			::= { sleLagLacpPortControl 9 }

		
--  1.3.6.1.4.1.6296.9.8.12.2.9
		-- 1.3.6.1.4.1.6296.101.3.12.2.10
		sleLagLacpPortControlAggregation OBJECT-TYPE
			SYNTAX INTEGER
				{
				aggregatable(1),
				individual(2)
				}
			MAX-ACCESS read-write
			STATUS current
			DESCRIPTION
				"set Aggregation in sleLagLacpPortActorAdminState."
			::= { sleLagLacpPortControl 10 }

		
--  Radius Server operation mode: if set bit 0, is used 
-- in login, and if set bit 1, is used in 802.1X (dot1x).
-- 1.3.6.1.4.1.6296.9.8.12.2.10
		-- 1.3.6.1.4.1.6296.101.3.12.2.11
		sleLagLacpPortControlPriority OBJECT-TYPE
			SYNTAX Integer32 (1..65535)
			MAX-ACCESS read-write
			STATUS current
			DESCRIPTION
				"The priority assigned to the port by Actor."
			::= { sleLagLacpPortControl 11 }

		
--  1.3.6.1.4.1.6296.9.8.12.2.11
		-- 1.3.6.1.4.1.6296.101.3.12.2.12
		sleLagLacpPortControlTimeout OBJECT-TYPE
			SYNTAX INTEGER
				{
				short(1),
				long(2)
				}
			MAX-ACCESS read-write
			STATUS current
			DESCRIPTION
				"set LACP_Timeout in sleLagLacpPortActorAdminState."
			::= { sleLagLacpPortControl 12 }

		
--  1.3.6.1.4.1.6296.9.8.12.3
		-- 1.3.6.1.4.1.6296.101.3.12.3
		sleLagLacpPortNotification OBJECT IDENTIFIER ::= { sleLagLacpPort 3 }

		
--  1.3.6.1.4.1.6296.9.8.12.3.1
		-- 1.3.6.1.4.1.6296.101.3.12.3.1
		sleLagLacpPortProfileChanged NOTIFICATION-TYPE
			OBJECTS { sleLagLacpPortControlRequest, sleLagLacpPortControlReqResult, sleLagLacpPortControlTimeStamp, sleLagLacpPortActorAdminKey, sleLagLacpPortActorPriority, 
				sleLagLacpPortActorAdminState }
			STATUS current
			DESCRIPTION 
				" "
			::= { sleLagLacpPortNotification 1 }

		
--  1.3.6.1.4.1.6296.9.8.12.3.2
		-- 1.3.6.1.4.1.6296.101.3.12.3.2
		sleLagLacpPortAggreChanged NOTIFICATION-TYPE
			OBJECTS { sleLagLacpPortControlRequest, sleLagLacpPortControlReqResult, sleLagLacpPortControlTimeStamp, sleLagLacpPortActorAggregatorId }
			STATUS current
			DESCRIPTION 
				" "
			::= { sleLagLacpPortNotification 2 }

		
--  1.3.6.1.4.1.6296.9.8.13
		-- 1.3.6.1.4.1.6296.101.3.13
		sleFdb OBJECT IDENTIFIER ::= { sleBridge 13 }

		
--  1.3.6.1.4.1.6296.9.8.13.2
		-- 1.3.6.1.4.1.6296.101.3.13.1
		sleFdbTable OBJECT-TYPE
			SYNTAX SEQUENCE OF SleFdbEntry
			MAX-ACCESS not-accessible
			STATUS current
			DESCRIPTION
				"The table of FDB entries."
			::= { sleFdb 1 }

		
--  1.3.6.1.4.1.6296.9.8.13.2.1
		-- 1.3.6.1.4.1.6296.101.3.13.1.1
		sleFdbEntry OBJECT-TYPE
			SYNTAX SleFdbEntry
			MAX-ACCESS not-accessible
			STATUS current
			DESCRIPTION
				"The table entry of FDB table."
			INDEX { sleFdbEntryFid, sleFdbEntryPort, sleFdbEntryMacAddress }
			::= { sleFdbTable 1 }

		
		SleFdbEntry ::=
			SEQUENCE { 
				sleFdbEntryFid
					INTEGER,
				sleFdbEntryPort
					INTEGER,
				sleFdbEntryMacAddress
					OCTET STRING,
				sleFdbEntryVid
					INTEGER,
				sleFdbEntryMode
					INTEGER,
				sleFdbEntryPermission
					INTEGER,
				sleFdbEntryElapsedTime
					Unsigned32
			 }

--  1.3.6.1.4.1.6296.9.8.13.2.1.1
		-- 1.3.6.1.4.1.6296.101.3.13.1.1.1
		sleFdbEntryFid OBJECT-TYPE
			SYNTAX INTEGER (1..4094)
			MAX-ACCESS read-only
			STATUS current
			DESCRIPTION
				"FDB identify."
			::= { sleFdbEntry 1 }

		
--  1.3.6.1.4.1.6296.9.8.13.2.1.2
		-- 1.3.6.1.4.1.6296.101.3.13.1.1.2
		sleFdbEntryPort OBJECT-TYPE
			SYNTAX INTEGER (1..255)
			MAX-ACCESS read-only
			STATUS current
			DESCRIPTION
				"The port number of the port on which 
				a frame having a source address equal 
				to the value of the corresponding instance 
				of dasanFdbAddress has been seen."
			::= { sleFdbEntry 2 }

		
--  1.3.6.1.4.1.6296.9.8.13.2.1.3
		-- 1.3.6.1.4.1.6296.101.3.13.1.1.3
		sleFdbEntryMacAddress OBJECT-TYPE
			SYNTAX OCTET STRING (SIZE (0..6))
			MAX-ACCESS read-only
			STATUS current
			DESCRIPTION
				"A unicast MAC address for which the device has
				forwarding or filtering information."
			::= { sleFdbEntry 3 }

		
--  1.3.6.1.4.1.6296.9.8.13.2.1.5
		-- 1.3.6.1.4.1.6296.101.3.13.1.1.4
		sleFdbEntryVid OBJECT-TYPE
			SYNTAX INTEGER (1..4094)
			MAX-ACCESS read-only
			STATUS current
			DESCRIPTION
				"VLAN ID."
			::= { sleFdbEntry 4 }

		
--  1.3.6.1.4.1.6296.9.8.13.2.1.4
		-- 1.3.6.1.4.1.6296.101.3.13.1.1.5
		sleFdbEntryMode OBJECT-TYPE
			SYNTAX INTEGER
				{
				local(0),
				static(1),
				dynamic(2)
				}
			MAX-ACCESS read-only
			STATUS current
			DESCRIPTION
				"FDB Entry's mode.
				The status of this entry.  The meanings of the values
				are:
				    local(0)   - the value of the corresponding instance 
				                 of sleFdbMacAddress was own.
				    static(1)  - the value of the corresponding instance 
				                 of sleFdbMacAddress was specified by management. 
				    dynamic(2) - the value of the corresponding instance
				                 of sleFdbMacAddress was learned."
			::= { sleFdbEntry 5 }

		
--  1.3.6.1.4.1.6296.9.8.13.2.1.6
		-- 1.3.6.1.4.1.6296.101.3.13.1.1.6
		sleFdbEntryPermission OBJECT-TYPE
			SYNTAX INTEGER
				{
				deny(0),
				permit(1)
				}
			MAX-ACCESS read-only
			STATUS current
			DESCRIPTION
				"The permission of dasanFdbAddress.
				The meanings of the values are:
				    deny(0)   - the value of the corresponding instance
				                of dasanFdbAddress will be dropped.
				    permit(1) - the value of the corresponding instance
				                of dasanFdbAddress will be flooded.
				"
			::= { sleFdbEntry 6 }

		
--  1.3.6.1.4.1.6296.9.8.13.2.1.7
		-- 1.3.6.1.4.1.6296.101.3.13.1.1.7
		sleFdbEntryElapsedTime OBJECT-TYPE
			SYNTAX Unsigned32
			MAX-ACCESS read-only
			STATUS current
			DESCRIPTION
				"Elapsed time after registered"
			::= { sleFdbEntry 7 }

		
--  1.3.6.1.4.1.6296.9.8.13.3
		-- 1.3.6.1.4.1.6296.101.3.13.2
		sleFdbControl OBJECT IDENTIFIER ::= { sleFdb 2 }

		
--  1.3.6.1.4.1.6296.9.8.13.3.1
		-- 1.3.6.1.4.1.6296.101.3.13.2.1
		sleFdbEntryControlRequest OBJECT-TYPE
			SYNTAX INTEGER
				{
				createFdbEntry(1),
				destoryFdbEntry(2),
				clearFdbTableEntries(3)
				}
			MAX-ACCESS read-write
			STATUS current
			DESCRIPTION
				"Control Request."
			::= { sleFdbControl 1 }

		
--  1.3.6.1.4.1.6296.9.8.13.3.2
		-- 1.3.6.1.4.1.6296.101.3.13.2.2
		sleFdbEntryControlStatus OBJECT-TYPE
			SYNTAX SleControlStatusType
			MAX-ACCESS read-only
			STATUS current
			DESCRIPTION
				"Control Status."
			::= { sleFdbControl 2 }

		
--  1.3.6.1.4.1.6296.9.8.13.3.3
		-- 1.3.6.1.4.1.6296.101.3.13.2.3
		sleFdbEntryControlTimer OBJECT-TYPE
			SYNTAX Gauge32
			MAX-ACCESS read-write
			STATUS current
			DESCRIPTION
				"Cotrol Timer."
			::= { sleFdbControl 3 }

		
--  1.3.6.1.4.1.6296.9.8.13.3.5
		-- 1.3.6.1.4.1.6296.101.3.13.2.4
		sleFdbEntryControlTImeStamp OBJECT-TYPE
			SYNTAX TimeTicks
			MAX-ACCESS read-only
			STATUS current
			DESCRIPTION
				" "
			::= { sleFdbControl 4 }

		
--  1.3.6.1.4.1.6296.9.8.13.3.4
		-- 1.3.6.1.4.1.6296.101.3.13.2.5
		sleFdbEntryControlReqResult OBJECT-TYPE
			SYNTAX SleControlRequestResultType
			MAX-ACCESS read-only
			STATUS current
			DESCRIPTION
				" "
			::= { sleFdbControl 5 }

		
--  1.3.6.1.4.1.6296.9.8.13.3.6
		-- 1.3.6.1.4.1.6296.101.3.13.2.6
		sleFdbEntryControlFid OBJECT-TYPE
			SYNTAX Integer32 (1..4094)
			MAX-ACCESS read-write
			STATUS current
			DESCRIPTION
				"FDB identifier."
			::= { sleFdbControl 6 }

		
--  1.3.6.1.4.1.6296.9.8.13.3.7
		-- 1.3.6.1.4.1.6296.101.3.13.2.7
		sleFdbEntryControlPort OBJECT-TYPE
			SYNTAX INTEGER (0..255)
			MAX-ACCESS read-write
			STATUS current
			DESCRIPTION
				"The port number of FDB entry.
				 0 : any (all) port."
			::= { sleFdbControl 7 }

		
--  1.3.6.1.4.1.6296.9.8.13.3.8
		-- 1.3.6.1.4.1.6296.101.3.13.2.8
		sleFdbEntryControlMacAddress OBJECT-TYPE
			SYNTAX OCTET STRING (SIZE (0..6))
			MAX-ACCESS read-write
			STATUS current
			DESCRIPTION
				"MAC address of FDB entry."
			::= { sleFdbControl 8 }

		
--  1.3.6.1.4.1.6296.9.8.13.4
		-- 1.3.6.1.4.1.6296.101.3.13.3
		sleFdbNotification OBJECT IDENTIFIER ::= { sleFdb 3 }

		
--  1.3.6.1.4.1.6296.9.8.13.4.2
		-- 1.3.6.1.4.1.6296.101.3.13.3.1
		sleFdbEntryCreated NOTIFICATION-TYPE
			OBJECTS { sleFdbEntryControlRequest, sleFdbEntryControlTImeStamp, sleFdbEntryControlReqResult, sleFdbEntryPermission }
			STATUS current
			DESCRIPTION 
				"Created FDB Entry."
			::= { sleFdbNotification 1 }

		
--  1.3.6.1.4.1.6296.9.8.13.4.3
		-- 1.3.6.1.4.1.6296.101.3.13.3.2
		sleFdbEntryDestoryed NOTIFICATION-TYPE
			OBJECTS { sleFdbEntryControlRequest, sleFdbEntryControlTImeStamp, sleFdbEntryControlReqResult, sleFdbEntryMacAddress }
			STATUS current
			DESCRIPTION 
				"Destroyed FDB Entry."
			::= { sleFdbNotification 2 }

		
		-- 1.3.6.1.4.1.6296.101.3.13.3.3
		sleFdbTableEntriesCleared NOTIFICATION-TYPE
			OBJECTS { sleFdbEntryControlRequest, sleFdbEntryControlTImeStamp, sleFdbEntryControlReqResult, sleFdbEntryPort }
			STATUS current
			DESCRIPTION 
				"clearFdbTableEntries.
				 In this notification PDU, key of sleFdbEntryPort 
				 is fid.port.6.0.0.0.0.0.0.
				 If port is 0, is cleared on all ports in fid."
			::= { sleFdbNotification 3 }

		
--  1.3.6.1.4.1.6296.9.8.14
		-- 1.3.6.1.4.1.6296.101.3.14
		sleMfdb OBJECT IDENTIFIER ::= { sleBridge 14 }

		
--  1.3.6.1.4.1.6296.9.8.14.1
		-- 1.3.6.1.4.1.6296.101.3.14.1
		sleMfdbTable OBJECT-TYPE
			SYNTAX SEQUENCE OF SleMfdbEntry
			MAX-ACCESS not-accessible
			STATUS current
			DESCRIPTION
				"The table of MFDB entries."
			::= { sleMfdb 1 }

		
--  1.3.6.1.4.1.6296.9.8.14.1.1
		-- 1.3.6.1.4.1.6296.101.3.14.1.1
		sleMfdbEntry OBJECT-TYPE
			SYNTAX SleMfdbEntry
			MAX-ACCESS not-accessible
			STATUS current
			DESCRIPTION
				"Information about a specific MAC address that
				should be forwarding or dropping."
			INDEX { sleMfdbMacAddress }
			::= { sleMfdbTable 1 }

		
		SleMfdbEntry ::=
			SEQUENCE { 
				sleMfdbMacAddress
					OCTET STRING,
				sleMfdbEntryPermission
					INTEGER,
				sleMfdbVlanIndex
					INTEGER,
				sleMfdbPorts
					OCTET STRING
			 }

--  1.3.6.1.4.1.6296.9.8.14.1.1.1
		-- 1.3.6.1.4.1.6296.101.3.14.1.1.1
		sleMfdbMacAddress OBJECT-TYPE
			SYNTAX OCTET STRING (SIZE (0..6))
			MAX-ACCESS read-only
			STATUS current
			DESCRIPTION
				"A unicast MAC address for which the device has
				forwarding or filtering information."
			::= { sleMfdbEntry 1 }

		
--  1.3.6.1.4.1.6296.9.8.14.1.1.2
		-- 1.3.6.1.4.1.6296.101.3.14.1.1.2
		sleMfdbEntryPermission OBJECT-TYPE
			SYNTAX INTEGER
				{
				deny(0),
				permit(1)
				}
			MAX-ACCESS read-only
			STATUS current
			DESCRIPTION
				"The permission of sleMFdbMacAddress.
				The meanings of the values are: 
				    deny(0)   - the value of the corresponding instance
				                of sleMfdbMacAddress will be dropped.
				    permit(1) - the value of the corresponding instance
				                of sleMfdbMacAddress will be flooded.
				"
			::= { sleMfdbEntry 2 }

		
		-- 1.3.6.1.4.1.6296.101.3.14.1.1.3
		sleMfdbVlanIndex OBJECT-TYPE
			SYNTAX INTEGER (0 | 1..4094)
			MAX-ACCESS read-only
			STATUS current
			DESCRIPTION
				"vlan index
				"
			::= { sleMfdbEntry 3 }

		
		-- 1.3.6.1.4.1.6296.101.3.14.1.1.4
		sleMfdbPorts OBJECT-TYPE
			SYNTAX OCTET STRING (SIZE (0..32))
			MAX-ACCESS read-write
			STATUS current
			DESCRIPTION
				"Description."
			::= { sleMfdbEntry 4 }

		
--  1.3.6.1.4.1.6296.9.8.14.2
		-- 1.3.6.1.4.1.6296.101.3.14.2
		sleMfdbControl OBJECT IDENTIFIER ::= { sleMfdb 2 }

		
--  1.3.6.1.4.1.6296.9.8.14.2.1
		-- 1.3.6.1.4.1.6296.101.3.14.2.1
		sleMfdbControlRequest OBJECT-TYPE
			SYNTAX INTEGER
				{
				createMfdbEntry(1),
				destoryMfdbEntry(2),
				setMfdbEntryPermission(3),
				clearMfdbEntryTable(4)
				}
			MAX-ACCESS read-write
			STATUS current
			DESCRIPTION
				" "
			::= { sleMfdbControl 1 }

		
--  1.3.6.1.4.1.6296.9.8.14.2.2
		-- 1.3.6.1.4.1.6296.101.3.14.2.2
		sleMfdbControlStatus OBJECT-TYPE
			SYNTAX SleControlStatusType
			MAX-ACCESS read-only
			STATUS current
			DESCRIPTION
				" "
			::= { sleMfdbControl 2 }

		
--  1.3.6.1.4.1.6296.9.8.14.2.3
		-- 1.3.6.1.4.1.6296.101.3.14.2.3
		sleMfdbControlTimer OBJECT-TYPE
			SYNTAX Gauge32
			MAX-ACCESS read-write
			STATUS current
			DESCRIPTION
				" "
			::= { sleMfdbControl 3 }

		
--  1.3.6.1.4.1.6296.9.8.14.2.5
		-- 1.3.6.1.4.1.6296.101.3.14.2.4
		sleMfdbControlTimeStamp OBJECT-TYPE
			SYNTAX TimeTicks
			MAX-ACCESS read-only
			STATUS current
			DESCRIPTION
				" "
			::= { sleMfdbControl 4 }

		
--  1.3.6.1.4.1.6296.9.8.14.2.4
		-- 1.3.6.1.4.1.6296.101.3.14.2.5
		sleMfdbControlReqResult OBJECT-TYPE
			SYNTAX SleControlRequestResultType
			MAX-ACCESS read-only
			STATUS current
			DESCRIPTION
				" "
			::= { sleMfdbControl 5 }

		
--  1.3.6.1.4.1.6296.9.8.14.2.6
		-- 1.3.6.1.4.1.6296.101.3.14.2.6
		sleMfdbControlMacAddress OBJECT-TYPE
			SYNTAX OCTET STRING (SIZE (0..6))
			MAX-ACCESS read-write
			STATUS current
			DESCRIPTION
				"A unicast MAC address for which the device has
				forwarding or filtering information.
				  If MAC address is NULL apply mac-filter list 
				  from file '/etc/mfdb.conf'."
			::= { sleMfdbControl 6 }

		
--  1.3.6.1.4.1.6296.9.8.14.2.7
		-- 1.3.6.1.4.1.6296.101.3.14.2.7
		sleMfdbControlEntryPermission OBJECT-TYPE
			SYNTAX INTEGER
				{
				deny(0),
				permit(1)
				}
			MAX-ACCESS read-write
			STATUS current
			DESCRIPTION
				"The permission of sleMFdbControlMacAddress."
			::= { sleMfdbControl 7 }

		
		-- 1.3.6.1.4.1.6296.101.3.14.2.8
		sleMfdbControlVlanIndex OBJECT-TYPE
			SYNTAX INTEGER (0 | 1..4094)
			MAX-ACCESS read-write
			STATUS current
			DESCRIPTION
				"vlan index
				The value of 0 is all vlan"
			::= { sleMfdbControl 8 }

		
		-- 1.3.6.1.4.1.6296.101.3.14.2.9
		sleMfdbControlPorts OBJECT-TYPE
			SYNTAX OCTET STRING (SIZE (0..32))
			MAX-ACCESS read-write
			STATUS current
			DESCRIPTION
				"Port Map 
				The value of 0x00 is all port
				"
			::= { sleMfdbControl 9 }

		
--  1.3.6.1.4.1.6296.9.8.14.3
		-- 1.3.6.1.4.1.6296.101.3.14.3
		sleMfdbNotification OBJECT IDENTIFIER ::= { sleMfdb 3 }

		
--  1.3.6.1.4.1.6296.9.8.14.3.1
		-- 1.3.6.1.4.1.6296.101.3.14.3.1
		sleMfdbEntryCreated NOTIFICATION-TYPE
			OBJECTS { sleMfdbControlRequest, sleMfdbControlReqResult, sleMfdbControlTimeStamp, sleMfdbEntryPermission }
			STATUS current
			DESCRIPTION 
				"Create new MFDB entry."
			::= { sleMfdbNotification 1 }

		
--  1.3.6.1.4.1.6296.9.8.14.3.2
		-- 1.3.6.1.4.1.6296.101.3.14.3.2
		sleMfdbEntryDestoryed NOTIFICATION-TYPE
			OBJECTS { sleMfdbControlRequest, sleMfdbControlReqResult, sleMfdbControlTimeStamp, sleMfdbMacAddress }
			STATUS current
			DESCRIPTION 
				"Destroyed MFDB entry."
			::= { sleMfdbNotification 2 }

		
--  1.3.6.1.4.1.6296.9.8.14.3.3
		-- 1.3.6.1.4.1.6296.101.3.14.3.3
		sleMfdbEntryPermissionChanged NOTIFICATION-TYPE
			OBJECTS { sleMfdbControlRequest, sleMfdbControlReqResult, sleMfdbControlTimeStamp, sleMfdbEntryPermission }
			STATUS current
			DESCRIPTION 
				"Changed permission of MFDB entry."
			::= { sleMfdbNotification 3 }

		
		-- 1.3.6.1.4.1.6296.101.3.14.3.4
		sleMfdbEntryTableCleared NOTIFICATION-TYPE
			OBJECTS { sleMfdbControlRequest, sleMfdbControlReqResult, sleMfdbControlTimeStamp }
			STATUS current
			DESCRIPTION 
				"Description."
			::= { sleMfdbNotification 4 }

		
		-- 1.3.6.1.4.1.6296.101.3.15
		sleIgmpConf OBJECT IDENTIFIER ::= { sleBridge 15 }

		
		-- 1.3.6.1.4.1.6296.101.3.15.1
		sleIgmpConfTable OBJECT-TYPE
			SYNTAX SEQUENCE OF SleIgmpConfEntry
			MAX-ACCESS not-accessible
			STATUS current
			DESCRIPTION
				"Description."
			::= { sleIgmpConf 1 }

		
		-- 1.3.6.1.4.1.6296.101.3.15.1.1
		sleIgmpConfEntry OBJECT-TYPE
			SYNTAX SleIgmpConfEntry
			MAX-ACCESS not-accessible
			STATUS current
			DESCRIPTION
				"Description."
			INDEX { sleVlanIndex }
			::= { sleIgmpConfTable 1 }

		
		SleIgmpConfEntry ::=
			SEQUENCE { 
				sleIgmpConfVlanIndex
					Integer32,
				sleIgmpConfEnable
					INTEGER,
				sleIgmpConfMulticastFilter
					INTEGER,
				sleIgmpConfOutmostVlan
					INTEGER,
				sleIgmpConfSnoopEnable
					INTEGER,
				sleIgmpConfSnoopJoinDelay
					Integer32,
				sleIgmpConfSnoopQueryDelay
					Integer32,
				sleIgmpConfSnoopMrouter
					Integer32,
				sleIgmpConfSnoopFastLeave
					INTEGER,
				sleIgmpConfSnoopQuerier
					INTEGER
			 }

		-- 1.3.6.1.4.1.6296.101.3.15.1.1.1
		sleIgmpConfVlanIndex OBJECT-TYPE
			SYNTAX Integer32 (0..4094)
			MAX-ACCESS read-only
			STATUS current
			DESCRIPTION
				"Description."
			::= { sleIgmpConfEntry 1 }

		
		-- 1.3.6.1.4.1.6296.101.3.15.1.1.2
		sleIgmpConfEnable OBJECT-TYPE
			SYNTAX INTEGER
				{
				disable(0),
				enable(1)
				}
			MAX-ACCESS read-only
			STATUS current
			DESCRIPTION
				"Description."
			::= { sleIgmpConfEntry 2 }

		
		-- 1.3.6.1.4.1.6296.101.3.15.1.1.3
		sleIgmpConfMulticastFilter OBJECT-TYPE
			SYNTAX INTEGER
				{
				disable(0),
				enable(1)
				}
			MAX-ACCESS read-only
			STATUS current
			DESCRIPTION
				"Description."
			::= { sleIgmpConfEntry 3 }

		
		-- 1.3.6.1.4.1.6296.101.3.15.1.1.4
		sleIgmpConfOutmostVlan OBJECT-TYPE
			SYNTAX INTEGER
				{
				disable(0),
				enable(1)
				}
			MAX-ACCESS read-only
			STATUS current
			DESCRIPTION
				"Description."
			::= { sleIgmpConfEntry 4 }

		
		-- 1.3.6.1.4.1.6296.101.3.15.1.1.5
		sleIgmpConfSnoopEnable OBJECT-TYPE
			SYNTAX INTEGER
				{
				disable(0),
				enable(1)
				}
			MAX-ACCESS read-only
			STATUS current
			DESCRIPTION
				"Description."
			::= { sleIgmpConfEntry 5 }

		
		-- 1.3.6.1.4.1.6296.101.3.15.1.1.6
		sleIgmpConfSnoopJoinDelay OBJECT-TYPE
			SYNTAX Integer32 (0..1000)
			MAX-ACCESS read-only
			STATUS current
			DESCRIPTION
				"Description."
			::= { sleIgmpConfEntry 6 }

		
		-- 1.3.6.1.4.1.6296.101.3.15.1.1.7
		sleIgmpConfSnoopQueryDelay OBJECT-TYPE
			SYNTAX Integer32 (100..900)
			MAX-ACCESS read-only
			STATUS current
			DESCRIPTION
				"Description."
			::= { sleIgmpConfEntry 7 }

		
		-- 1.3.6.1.4.1.6296.101.3.15.1.1.8
		sleIgmpConfSnoopMrouter OBJECT-TYPE
			SYNTAX Integer32
			MAX-ACCESS read-only
			STATUS current
			DESCRIPTION
				"Description."
			::= { sleIgmpConfEntry 8 }

		
		-- 1.3.6.1.4.1.6296.101.3.15.1.1.9
		sleIgmpConfSnoopFastLeave OBJECT-TYPE
			SYNTAX INTEGER
				{
				disable(0),
				enable(1)
				}
			MAX-ACCESS read-only
			STATUS current
			DESCRIPTION
				"Description."
			::= { sleIgmpConfEntry 9 }

		
		-- 1.3.6.1.4.1.6296.101.3.15.1.1.10
		sleIgmpConfSnoopQuerier OBJECT-TYPE
			SYNTAX INTEGER
				{
				disable(0),
				enable(1)
				}
			MAX-ACCESS read-only
			STATUS current
			DESCRIPTION
				"Description."
			::= { sleIgmpConfEntry 10 }

		
		-- 1.3.6.1.4.1.6296.101.3.15.2
		sleIgmpConfControl OBJECT IDENTIFIER ::= { sleIgmpConf 2 }

		
		-- 1.3.6.1.4.1.6296.101.3.15.2.1
		sleIgmpConfControlRequest OBJECT-TYPE
			SYNTAX SleIgmpConfControlRequestType
			MAX-ACCESS read-write
			STATUS current
			DESCRIPTION
				"Description."
			::= { sleIgmpConfControl 1 }

		
		-- 1.3.6.1.4.1.6296.101.3.15.2.2
		sleIgmpConfControlStatus OBJECT-TYPE
			SYNTAX SleControlStatusType
			MAX-ACCESS read-only
			STATUS current
			DESCRIPTION
				"Description."
			::= { sleIgmpConfControl 2 }

		
		-- 1.3.6.1.4.1.6296.101.3.15.2.3
		sleIgmpConfControlTimer OBJECT-TYPE
			SYNTAX Gauge32
			MAX-ACCESS read-write
			STATUS current
			DESCRIPTION
				"Description."
			::= { sleIgmpConfControl 3 }

		
		-- 1.3.6.1.4.1.6296.101.3.15.2.4
		sleIgmpConfControlReqResult OBJECT-TYPE
			SYNTAX SleControlRequestResultType
			MAX-ACCESS read-only
			STATUS current
			DESCRIPTION
				"Description."
			::= { sleIgmpConfControl 4 }

		
		-- 1.3.6.1.4.1.6296.101.3.15.2.5
		sleIgmpConfControlTimeStamp OBJECT-TYPE
			SYNTAX TimeTicks
			MAX-ACCESS read-only
			STATUS current
			DESCRIPTION
				"Description."
			::= { sleIgmpConfControl 5 }

		
		-- 1.3.6.1.4.1.6296.101.3.15.2.6
		sleIgmpConfControlVlanIndex OBJECT-TYPE
			SYNTAX Integer32 (1..4094)
			MAX-ACCESS read-write
			STATUS current
			DESCRIPTION
				"Description."
			::= { sleIgmpConfControl 6 }

		
		-- 1.3.6.1.4.1.6296.101.3.15.2.7
		sleIgmpConfControlEnable OBJECT-TYPE
			SYNTAX INTEGER
				{
				disable(0),
				enable(1)
				}
			MAX-ACCESS read-write
			STATUS current
			DESCRIPTION
				"Description."
			::= { sleIgmpConfControl 7 }

		
		-- 1.3.6.1.4.1.6296.101.3.15.2.8
		sleIgmpConfControlMulticastFilter OBJECT-TYPE
			SYNTAX INTEGER
				{
				disable(0),
				enable(1)
				}
			MAX-ACCESS read-write
			STATUS current
			DESCRIPTION
				"Description."
			::= { sleIgmpConfControl 8 }

		
		-- 1.3.6.1.4.1.6296.101.3.15.2.9
		sleIgmpConfControlOutmostVlan OBJECT-TYPE
			SYNTAX INTEGER
				{
				disable(0),
				enable(1)
				}
			MAX-ACCESS read-write
			STATUS current
			DESCRIPTION
				"Description."
			::= { sleIgmpConfControl 9 }

		
		-- 1.3.6.1.4.1.6296.101.3.15.2.10
		sleIgmpConfControlSnoopEnable OBJECT-TYPE
			SYNTAX INTEGER
				{
				disable(0),
				enable(1)
				}
			MAX-ACCESS read-write
			STATUS current
			DESCRIPTION
				"Description."
			::= { sleIgmpConfControl 10 }

		
		-- 1.3.6.1.4.1.6296.101.3.15.2.11
		sleIgmpConfControlSnoopJoinDelay OBJECT-TYPE
			SYNTAX Integer32 (0..1000)
			MAX-ACCESS read-write
			STATUS current
			DESCRIPTION
				"Description."
			::= { sleIgmpConfControl 11 }

		
		-- 1.3.6.1.4.1.6296.101.3.15.2.12
		sleIgmpConfControlSnoopQueryDelay OBJECT-TYPE
			SYNTAX Integer32 (100..900)
			MAX-ACCESS read-write
			STATUS current
			DESCRIPTION
				"Description."
			::= { sleIgmpConfControl 12 }

		
		-- 1.3.6.1.4.1.6296.101.3.15.2.13
		sleIgmpConfControlSnoopMrouter OBJECT-TYPE
			SYNTAX Integer32 (1..255)
			MAX-ACCESS read-write
			STATUS current
			DESCRIPTION
				"Description."
			DEFVAL { -1 }
			::= { sleIgmpConfControl 13 }

		
		-- 1.3.6.1.4.1.6296.101.3.15.2.14
		sleIgmpConfControlSnoopFastLeave OBJECT-TYPE
			SYNTAX INTEGER
				{
				disable(0),
				enable(1)
				}
			MAX-ACCESS read-write
			STATUS current
			DESCRIPTION
				"Description."
			::= { sleIgmpConfControl 14 }

		
		-- 1.3.6.1.4.1.6296.101.3.15.2.15
		sleIgmpConfControlSnoopQuerier OBJECT-TYPE
			SYNTAX INTEGER
				{
				disable(0),
				enable(1)
				}
			MAX-ACCESS read-write
			STATUS current
			DESCRIPTION
				"Description."
			::= { sleIgmpConfControl 15 }

		
		-- 1.3.6.1.4.1.6296.101.3.15.3
		sleIgmpConfNotification OBJECT IDENTIFIER ::= { sleIgmpConf 3 }

		
		-- 1.3.6.1.4.1.6296.101.3.15.3.1
		sleIgmpConfProfileChanged NOTIFICATION-TYPE
			OBJECTS { sleIgmpConfControlRequest, sleIgmpConfControlReqResult, sleIgmpConfControlTimeStamp, sleIgmpConfSnoopMrouter, sleIgmpConfEnable, 
				sleIgmpConfMulticastFilter, sleIgmpConfOutmostVlan, sleIgmpConfSnoopEnable, sleIgmpConfSnoopJoinDelay, sleIgmpConfSnoopQueryDelay, 
				sleIgmpConfSnoopFastLeave, sleIgmpConfSnoopQuerier }
			STATUS current
			DESCRIPTION 
				"Description."
			::= { sleIgmpConfNotification 1 }

		
--  1.3.6.1.4.1.6296.9.8.15
		-- 1.3.6.1.4.1.6296.101.3.16
		sleIgmpMcast OBJECT IDENTIFIER ::= { sleBridge 16 }

		
--  1.3.6.1.4.1.6296.9.8.15.1
		-- 1.3.6.1.4.1.6296.101.3.16.1
		sleIgmpMcastTable OBJECT-TYPE
			SYNTAX SEQUENCE OF SleIgmpMcastEntry
			MAX-ACCESS not-accessible
			STATUS current
			DESCRIPTION
				" "
			::= { sleIgmpMcast 1 }

		
--  1.3.6.1.4.1.6296.9.8.15.1.1
		-- 1.3.6.1.4.1.6296.101.3.16.1.1
		sleIgmpMcastEntry OBJECT-TYPE
			SYNTAX SleIgmpMcastEntry
			MAX-ACCESS not-accessible
			STATUS current
			DESCRIPTION
				" "
			INDEX { sleVlanIndex, sleIgmpMcastIPAddress, sleIgmpMcastPortIndex }
			::= { sleIgmpMcastTable 1 }

		
		SleIgmpMcastEntry ::=
			SEQUENCE { 
				sleIgmpMcastVlanIndex
					Integer32,
				sleIgmpMcastIPAddress
					IpAddress,
				sleIgmpMcastPortIndex
					Integer32,
				sleIgmpMcastType
					INTEGER,
				sleIgmpMcastExpireTime
					Integer32
			 }

		-- 1.3.6.1.4.1.6296.101.3.16.1.1.1
		sleIgmpMcastVlanIndex OBJECT-TYPE
			SYNTAX Integer32 (1..4094)
			MAX-ACCESS read-only
			STATUS current
			DESCRIPTION
				"Description."
			::= { sleIgmpMcastEntry 1 }

		
--  1.3.6.1.4.1.6296.9.8.15.1.1.2
		-- 1.3.6.1.4.1.6296.101.3.16.1.1.2
		sleIgmpMcastIPAddress OBJECT-TYPE
			SYNTAX IpAddress
			MAX-ACCESS read-only
			STATUS current
			DESCRIPTION
				"IP address"
			::= { sleIgmpMcastEntry 2 }

		
		-- 1.3.6.1.4.1.6296.101.3.16.1.1.3
		sleIgmpMcastPortIndex OBJECT-TYPE
			SYNTAX Integer32 (1..255)
			MAX-ACCESS read-only
			STATUS current
			DESCRIPTION
				"Description."
			::= { sleIgmpMcastEntry 3 }

		
		-- 1.3.6.1.4.1.6296.101.3.16.1.1.4
		sleIgmpMcastType OBJECT-TYPE
			SYNTAX INTEGER
				{
				static(0),
				dynamic(1)
				}
			MAX-ACCESS read-only
			STATUS current
			DESCRIPTION
				"Description."
			::= { sleIgmpMcastEntry 4 }

		
		-- 1.3.6.1.4.1.6296.101.3.16.1.1.5
		sleIgmpMcastExpireTime OBJECT-TYPE
			SYNTAX Integer32
			MAX-ACCESS read-only
			STATUS current
			DESCRIPTION
				"Description."
			::= { sleIgmpMcastEntry 5 }

		
--  1.3.6.1.4.1.6296.9.8.15.2
		-- 1.3.6.1.4.1.6296.101.3.16.2
		sleIgmpMcastControl OBJECT IDENTIFIER ::= { sleIgmpMcast 2 }

		
--  1.3.6.1.4.1.6296.9.8.15.2.1
		-- 1.3.6.1.4.1.6296.101.3.16.2.1
		sleIgmpMcastControlReqest OBJECT-TYPE
			SYNTAX SleIgmpMcastControlRequestType
			MAX-ACCESS read-write
			STATUS current
			DESCRIPTION
				" "
			::= { sleIgmpMcastControl 1 }

		
--  1.3.6.1.4.1.6296.9.8.15.2.2
		-- 1.3.6.1.4.1.6296.101.3.16.2.2
		sleIgmpMcastControlStatus OBJECT-TYPE
			SYNTAX SleControlStatusType
			MAX-ACCESS read-only
			STATUS current
			DESCRIPTION
				"Description."
			::= { sleIgmpMcastControl 2 }

		
--  1.3.6.1.4.1.6296.9.8.15.2.3
		-- 1.3.6.1.4.1.6296.101.3.16.2.3
		sleIgmpMcastControlTimer OBJECT-TYPE
			SYNTAX Gauge32
			MAX-ACCESS read-write
			STATUS current
			DESCRIPTION
				" "
			::= { sleIgmpMcastControl 3 }

		
--  1.3.6.1.4.1.6296.9.8.15.2.4
		-- 1.3.6.1.4.1.6296.101.3.16.2.4
		sleIgmpMcastControlTimeStamp OBJECT-TYPE
			SYNTAX TimeTicks
			MAX-ACCESS read-only
			STATUS current
			DESCRIPTION
				" "
			::= { sleIgmpMcastControl 4 }

		
--  1.3.6.1.4.1.6296.9.8.15.2.5
		-- 1.3.6.1.4.1.6296.101.3.16.2.5
		sleIgmpMcastControlReqResult OBJECT-TYPE
			SYNTAX SleControlRequestResultType
			MAX-ACCESS read-only
			STATUS current
			DESCRIPTION
				" "
			::= { sleIgmpMcastControl 5 }

		
--  1.3.6.1.4.1.6296.9.8.15.2.6
		-- 1.3.6.1.4.1.6296.101.3.16.2.6
		sleIgmpMcastControlVlanIndex OBJECT-TYPE
			SYNTAX Integer32 (1..4094)
			MAX-ACCESS read-write
			STATUS current
			DESCRIPTION
				" "
			::= { sleIgmpMcastControl 6 }

		
--  Vlan ID
-- 1.3.6.1.4.1.6296.9.8.15.2.7
		-- 1.3.6.1.4.1.6296.101.3.16.2.7
		sleIgmpMcastControlIPAddress OBJECT-TYPE
			SYNTAX IpAddress
			MAX-ACCESS read-write
			STATUS current
			DESCRIPTION
				" "
			::= { sleIgmpMcastControl 7 }

		
		-- 1.3.6.1.4.1.6296.101.3.16.2.8
		sleIgmpMcastControlPortIndex OBJECT-TYPE
			SYNTAX Integer32 (1..255)
			MAX-ACCESS read-write
			STATUS current
			DESCRIPTION
				"Description."
			::= { sleIgmpMcastControl 8 }

		
--  IP address
-- 1.3.6.1.4.1.6296.9.8.15.3
		-- 1.3.6.1.4.1.6296.101.3.16.3
		sleIgmpMcastNotification OBJECT IDENTIFIER ::= { sleIgmpMcast 3 }

		
--  1.3.6.1.4.1.6296.9.8.15.3.1
		-- 1.3.6.1.4.1.6296.101.3.16.3.1
		sleIgmpStaticMcastCreated NOTIFICATION-TYPE
			OBJECTS { sleIgmpMcastControlReqest, sleIgmpMcastControlTimeStamp, sleIgmpMcastControlPortIndex, sleIgmpMcastControlReqResult }
			STATUS current
			DESCRIPTION 
				" "
			::= { sleIgmpMcastNotification 1 }

		
--  1.3.6.1.4.1.6296.9.8.15.3.2
		-- 1.3.6.1.4.1.6296.101.3.16.3.2
		sleIgmpStaticMcastDestroyed NOTIFICATION-TYPE
			OBJECTS { sleIgmpMcastControlReqest, sleIgmpMcastControlReqResult, sleIgmpMcastControlPortIndex, sleIgmpMcastControlTimeStamp }
			STATUS current
			DESCRIPTION 
				" "
			::= { sleIgmpMcastNotification 2 }

		
--  1.3.6.1.4.1.6296.9.8.17
		-- 1.3.6.1.4.1.6296.101.3.17
		sleStackDevice OBJECT IDENTIFIER ::= { sleBridge 17 }

		
--  1.3.6.1.4.1.6296.9.8.17.1
		-- 1.3.6.1.4.1.6296.101.3.17.1
		sleStackDeviceTable OBJECT-TYPE
			SYNTAX SEQUENCE OF SleStackDeviceEntry
			MAX-ACCESS not-accessible
			STATUS current
			DESCRIPTION
				"Information table of stack master/slave devices."
			::= { sleStackDevice 1 }

		
--  1.3.6.1.4.1.6296.9.8.17.1.1
		-- 1.3.6.1.4.1.6296.101.3.17.1.1
		sleStackDeviceEntry OBJECT-TYPE
			SYNTAX SleStackDeviceEntry
			MAX-ACCESS not-accessible
			STATUS current
			DESCRIPTION
				"Information table entry of stack master/slave devices."
			INDEX { sleStackDeviceMacAddress }
			::= { sleStackDeviceTable 1 }

		
		SleStackDeviceEntry ::=
			SEQUENCE { 
				sleStackDeviceMacAddress
					OCTET STRING,
				sleStackDeviceNodeId
					Integer32,
				sleStackDeviceDescriptor
					OCTET STRING,
				sleStackDeviceMode
					INTEGER,
				sleStackDeviceStatus
					INTEGER,
				sleStackDeviceType
					OCTET STRING,
				sleStackDeviceHostName
					OCTET STRING,
				sleStackDevicePortNum
					INTEGER
			 }

--  1.3.6.1.4.1.6296.9.8.17.1.1.1
		-- 1.3.6.1.4.1.6296.101.3.17.1.1.1
		sleStackDeviceMacAddress OBJECT-TYPE
			SYNTAX OCTET STRING (SIZE (0..6))
			MAX-ACCESS read-only
			STATUS current
			DESCRIPTION
				"MAC address of stack device."
			::= { sleStackDeviceEntry 1 }

		
--  1.3.6.1.4.1.6296.9.8.17.1.1.2
		-- 1.3.6.1.4.1.6296.101.3.17.1.1.2
		sleStackDeviceNodeId OBJECT-TYPE
			SYNTAX Integer32
			MAX-ACCESS read-only
			STATUS current
			DESCRIPTION
				"Index stack device nodes."
			::= { sleStackDeviceEntry 2 }

		
--  1.3.6.1.4.1.6296.9.8.17.1.1.3
		-- 1.3.6.1.4.1.6296.101.3.17.1.1.3
		sleStackDeviceDescriptor OBJECT-TYPE
			SYNTAX OCTET STRING (SIZE (0..256))
			MAX-ACCESS read-only
			STATUS current
			DESCRIPTION
				"Description of stack device."
			::= { sleStackDeviceEntry 3 }

		
--  1.3.6.1.4.1.6296.9.8.17.1.1.4
		-- 1.3.6.1.4.1.6296.101.3.17.1.1.4
		sleStackDeviceMode OBJECT-TYPE
			SYNTAX INTEGER
				{
				master(1),
				slave(2)
				}
			MAX-ACCESS read-only
			STATUS current
			DESCRIPTION
				"Stack status of device."
			::= { sleStackDeviceEntry 4 }

		
--  1.3.6.1.4.1.6296.9.8.17.1.1.6
		-- 1.3.6.1.4.1.6296.101.3.17.1.1.5
		sleStackDeviceStatus OBJECT-TYPE
			SYNTAX INTEGER
				{
				inactive(0),
				active(1)
				}
			MAX-ACCESS read-only
			STATUS current
			DESCRIPTION
				"Stack status of stack device."
			::= { sleStackDeviceEntry 5 }

		
--  1.3.6.1.4.1.6296.9.8.17.1.1.7
		-- 1.3.6.1.4.1.6296.101.3.17.1.1.6
		sleStackDeviceType OBJECT-TYPE
			SYNTAX OCTET STRING (SIZE (0..16))
			MAX-ACCESS read-only
			STATUS current
			DESCRIPTION
				"Device type of stack device."
			::= { sleStackDeviceEntry 6 }

		
--  1.3.6.1.4.1.6296.9.8.17.1.1.8
		-- 1.3.6.1.4.1.6296.101.3.17.1.1.7
		sleStackDeviceHostName OBJECT-TYPE
			SYNTAX OCTET STRING (SIZE (0..32))
			MAX-ACCESS read-only
			STATUS current
			DESCRIPTION
				"Hostname of stack device."
			::= { sleStackDeviceEntry 7 }

		
--  1.3.6.1.4.1.6296.9.8.17.1.1.9
		-- 1.3.6.1.4.1.6296.101.3.17.1.1.8
		sleStackDevicePortNum OBJECT-TYPE
			SYNTAX INTEGER (0..255)
			MAX-ACCESS read-only
			STATUS current
			DESCRIPTION
				"Number of stack device's ports."
			::= { sleStackDeviceEntry 8 }

		
--  1.3.6.1.4.1.6296.9.8.17.2
		-- 1.3.6.1.4.1.6296.101.3.17.2
		sleStackDeviceControl OBJECT IDENTIFIER ::= { sleStackDevice 2 }

		
--  1.3.6.1.4.1.6296.9.8.17.2.1
		-- 1.3.6.1.4.1.6296.101.3.17.2.1
		sleStackDeviceControlRequest OBJECT-TYPE
			SYNTAX INTEGER
				{
				createStackSlaveDevice(1),
				destoryStackSlaveDevice(2)
				}
			MAX-ACCESS read-write
			STATUS current
			DESCRIPTION
				" "
			::= { sleStackDeviceControl 1 }

		
--  1.3.6.1.4.1.6296.9.8.17.2.2
		-- 1.3.6.1.4.1.6296.101.3.17.2.2
		sleStackDeviceControlStatus OBJECT-TYPE
			SYNTAX SleControlStatusType
			MAX-ACCESS read-only
			STATUS current
			DESCRIPTION
				" "
			::= { sleStackDeviceControl 2 }

		
--  1.3.6.1.4.1.6296.9.8.17.2.3
		-- 1.3.6.1.4.1.6296.101.3.17.2.3
		sleStackDeviceControlTimer OBJECT-TYPE
			SYNTAX Gauge32
			MAX-ACCESS read-write
			STATUS current
			DESCRIPTION
				" "
			::= { sleStackDeviceControl 3 }

		
--  1.3.6.1.4.1.6296.9.8.17.2.5
		-- 1.3.6.1.4.1.6296.101.3.17.2.4
		sleStackDeviceControlTImeStamp OBJECT-TYPE
			SYNTAX TimeTicks
			MAX-ACCESS read-only
			STATUS current
			DESCRIPTION
				" "
			::= { sleStackDeviceControl 4 }

		
--  1.3.6.1.4.1.6296.9.8.17.2.4
		-- 1.3.6.1.4.1.6296.101.3.17.2.5
		sleStackDeviceControlReqResult OBJECT-TYPE
			SYNTAX SleControlRequestResultType
			MAX-ACCESS read-only
			STATUS current
			DESCRIPTION
				" "
			::= { sleStackDeviceControl 5 }

		
--  1.3.6.1.4.1.6296.9.8.17.2.6
		-- 1.3.6.1.4.1.6296.101.3.17.2.6
		sleStackDeviceControlMacAddress OBJECT-TYPE
			SYNTAX OCTET STRING (SIZE (0..6))
			MAX-ACCESS read-write
			STATUS current
			DESCRIPTION
				"MAC address of slave device."
			::= { sleStackDeviceControl 6 }

		
--  1.3.6.1.4.1.6296.9.8.17.2.7
		-- 1.3.6.1.4.1.6296.101.3.17.2.7
		sleStackDeviceControlDescriptor OBJECT-TYPE
			SYNTAX OCTET STRING (SIZE (0..256))
			MAX-ACCESS read-write
			STATUS current
			DESCRIPTION
				"Description of stack slave device."
			::= { sleStackDeviceControl 7 }

		
--  1.3.6.1.4.1.6296.9.8.17.3
		-- 1.3.6.1.4.1.6296.101.3.17.3
		sleStackDeviceNotification OBJECT IDENTIFIER ::= { sleStackDevice 3 }

		
--  1.3.6.1.4.1.6296.9.8.17.3.1
		-- 1.3.6.1.4.1.6296.101.3.17.3.1
		sleStackDeviceCreated NOTIFICATION-TYPE
			OBJECTS { sleStackDeviceControlRequest, sleStackDeviceControlTImeStamp, sleStackDeviceControlReqResult, sleStackDeviceDescriptor }
			STATUS current
			DESCRIPTION 
				"Added stack slave device to master stack device."
			::= { sleStackDeviceNotification 1 }

		
--  1.3.6.1.4.1.6296.9.8.17.3.2
		-- 1.3.6.1.4.1.6296.101.3.17.3.2
		sleStackDeviceDestoryed NOTIFICATION-TYPE
			OBJECTS { sleStackDeviceControlRequest, sleStackDeviceControlTImeStamp, sleStackDeviceControlReqResult, sleStackDeviceMacAddress }
			STATUS current
			DESCRIPTION 
				"Deleted stack slave device from master stack device."
			::= { sleStackDeviceNotification 2 }

		
		-- 1.3.6.1.4.1.6296.101.3.18
		sleErpDomain OBJECT IDENTIFIER ::= { sleBridge 18 }

		
		-- 1.3.6.1.4.1.6296.101.3.18.1
		sleErpDomainTable OBJECT-TYPE
			SYNTAX SEQUENCE OF SleErpDomainEntry
			MAX-ACCESS not-accessible
			STATUS current
			DESCRIPTION
				" "
			::= { sleErpDomain 1 }

		
		-- 1.3.6.1.4.1.6296.101.3.18.1.1
		sleErpDomainEntry OBJECT-TYPE
			SYNTAX SleErpDomainEntry
			MAX-ACCESS not-accessible
			STATUS current
			DESCRIPTION
				" "
			INDEX { sleErpDomainIndex }
			::= { sleErpDomainTable 1 }

		
		SleErpDomainEntry ::=
			SEQUENCE { 
				sleErpDomainIndex
					INTEGER,
				sleErpDomainName
					OCTET STRING,
				sleErpDomainPrimaryPort
					InterfaceIndex,
				sleErpDomainSecondaryPort
					InterfaceIndex,
				sleErpDomainBridgeRole
					INTEGER,
				sleErpDomainProtectionActivation
					INTEGER,
				sleErpDomainOperatorRequest
					INTEGER,
				sleErpDomainWaitToRestoreTime
					INTEGER,
				sleErpDomainTestPacketInterval
					INTEGER,
				sleErpDomainLearningDisabledTime
					INTEGER,
				sleErpDomainNodeStatus
					INTEGER,
				sleErpDomainRingStatus
					INTEGER,
				sleErpDomainLotp
					INTEGER,
				sleErpDomainULotp
					INTEGER,
				sleErpDomainMultipleRM
					INTEGER,
				sleErpDomainRMNodeReacheablility
					INTEGER,
				sleErpDomainHoldOffTime
					INTEGER,
				sleErpDomainRingPriority
					INTEGER
			 }

		-- 1.3.6.1.4.1.6296.101.3.18.1.1.1
		sleErpDomainIndex OBJECT-TYPE
			SYNTAX INTEGER (1..4094)
			MAX-ACCESS read-only
			STATUS current
			DESCRIPTION
				"An index value that uniquely identifies an ERP domain."
			::= { sleErpDomainEntry 1 }

		
		-- 1.3.6.1.4.1.6296.101.3.18.1.1.2
		sleErpDomainName OBJECT-TYPE
			SYNTAX OCTET STRING
			MAX-ACCESS read-only
			STATUS current
			DESCRIPTION
				"Domain name."
			::= { sleErpDomainEntry 2 }

		
		-- 1.3.6.1.4.1.6296.101.3.18.1.1.3
		sleErpDomainPrimaryPort OBJECT-TYPE
			SYNTAX InterfaceIndex
			MAX-ACCESS read-write
			STATUS current
			DESCRIPTION
				"Interface index that represents the primary port of the domain."
			::= { sleErpDomainEntry 3 }

		
		-- 1.3.6.1.4.1.6296.101.3.18.1.1.4
		sleErpDomainSecondaryPort OBJECT-TYPE
			SYNTAX InterfaceIndex
			MAX-ACCESS read-only
			STATUS current
			DESCRIPTION
				"Interface index that represents the secondary port of the domain."
			::= { sleErpDomainEntry 4 }

		
		-- 1.3.6.1.4.1.6296.101.3.18.1.1.5
		sleErpDomainBridgeRole OBJECT-TYPE
			SYNTAX INTEGER
				{
				normalNode(0),
				rmNode(1)
				}
			MAX-ACCESS read-only
			STATUS current
			DESCRIPTION
				"Mode that the ERP domain may operate in."
			::= { sleErpDomainEntry 5 }

		
		-- 1.3.6.1.4.1.6296.101.3.18.1.1.6
		sleErpDomainProtectionActivation OBJECT-TYPE
			SYNTAX INTEGER
				{
				deactivated(0),
				activated(1)
				}
			MAX-ACCESS read-only
			STATUS current
			DESCRIPTION
				"Protection activation."
			::= { sleErpDomainEntry 6 }

		
		-- 1.3.6.1.4.1.6296.101.3.18.1.1.7
		sleErpDomainOperatorRequest OBJECT-TYPE
			SYNTAX INTEGER
				{
				clear(0),
				manualToSecondary(1)
				}
			MAX-ACCESS read-only
			STATUS current
			DESCRIPTION
				"Operator Request."
			::= { sleErpDomainEntry 7 }

		
		-- 1.3.6.1.4.1.6296.101.3.18.1.1.8
		sleErpDomainWaitToRestoreTime OBJECT-TYPE
			SYNTAX INTEGER (1..720)
			MAX-ACCESS read-only
			STATUS current
			DESCRIPTION
				"Time in seconds taken to verify that ring integrity is restored."
			::= { sleErpDomainEntry 8 }

		
		-- 1.3.6.1.4.1.6296.101.3.18.1.1.9
		sleErpDomainTestPacketInterval OBJECT-TYPE
			SYNTAX INTEGER (10..500)
			MAX-ACCESS read-only
			STATUS current
			DESCRIPTION
				"Time in mili seconds between consecutive transmissions of test packages."
			::= { sleErpDomainEntry 9 }

		
		-- 1.3.6.1.4.1.6296.101.3.18.1.1.10
		sleErpDomainLearningDisabledTime OBJECT-TYPE
			SYNTAX INTEGER (0..500)
			MAX-ACCESS read-only
			STATUS current
			DESCRIPTION
				"Time in mili seconds during which learning is disabled after a FDB flash."
			::= { sleErpDomainEntry 10 }

		
		-- 1.3.6.1.4.1.6296.101.3.18.1.1.11
		sleErpDomainNodeStatus OBJECT-TYPE
			SYNTAX INTEGER
				{
				rmidle(0),
				primaryProtecting(1),
				protecting(2),
				idle(3),
				failedS(4),
				failedP(5),
				preForward(6),
				isolated(7),
				deactivated(8),
				backoff(9)
				}
			MAX-ACCESS read-only
			STATUS current
			DESCRIPTION
				"Node status."
			::= { sleErpDomainEntry 11 }

		
		-- 1.3.6.1.4.1.6296.101.3.18.1.1.12
		sleErpDomainRingStatus OBJECT-TYPE
			SYNTAX INTEGER
				{
				normal(0),
				protecting(1),
				unknown(2)
				}
			MAX-ACCESS read-only
			STATUS current
			DESCRIPTION
				"Actual protection state on the ring."
			::= { sleErpDomainEntry 12 }

		
		-- 1.3.6.1.4.1.6296.101.3.18.1.1.13
		sleErpDomainLotp OBJECT-TYPE
			SYNTAX INTEGER
				{
				clear(0),
				raised(1)
				}
			MAX-ACCESS read-only
			STATUS current
			DESCRIPTION
				"Loss of Test Packet alarm status. Only meaningful in RM node."
			::= { sleErpDomainEntry 13 }

		
		-- 1.3.6.1.4.1.6296.101.3.18.1.1.14
		sleErpDomainULotp OBJECT-TYPE
			SYNTAX INTEGER
				{
				clear(0),
				raised(1)
				}
			MAX-ACCESS read-only
			STATUS current
			DESCRIPTION
				"Unidirectional Detection of  Loss of Test Packet alarm status.
				Only meaningful in RM node."
			::= { sleErpDomainEntry 14 }

		
		-- 1.3.6.1.4.1.6296.101.3.18.1.1.15
		sleErpDomainMultipleRM OBJECT-TYPE
			SYNTAX INTEGER
				{
				clear(0),
				raised(1)
				}
			MAX-ACCESS read-only
			STATUS current
			DESCRIPTION
				"Multiple Redundancy Manager alarm status. Only meaningful
				in RM node."
			::= { sleErpDomainEntry 15 }

		
		-- 1.3.6.1.4.1.6296.101.3.18.1.1.16
		sleErpDomainRMNodeReacheablility OBJECT-TYPE
			SYNTAX INTEGER
				{
				clear(0),
				raised(1)
				}
			MAX-ACCESS read-only
			STATUS current
			DESCRIPTION
				"RM Node reacheability alarm status. Only meaningful in
				normal node."
			::= { sleErpDomainEntry 16 }

		
		-- 1.3.6.1.4.1.6296.101.3.18.1.1.17
		sleErpDomainHoldOffTime OBJECT-TYPE
			SYNTAX INTEGER (0 | 1..20000)
			MAX-ACCESS read-only
			STATUS current
			DESCRIPTION
				"Description."
			::= { sleErpDomainEntry 17 }

		
		-- 1.3.6.1.4.1.6296.101.3.18.1.1.18
		sleErpDomainRingPriority OBJECT-TYPE
			SYNTAX INTEGER (0 | 1..255)
			MAX-ACCESS read-only
			STATUS current
			DESCRIPTION
				"Description."
			::= { sleErpDomainEntry 18 }

		
		-- 1.3.6.1.4.1.6296.101.3.18.2
		sleErpDomainControl OBJECT IDENTIFIER ::= { sleErpDomain 2 }

		
		-- 1.3.6.1.4.1.6296.101.3.18.2.1
		sleErpDomainControlRequest OBJECT-TYPE
			SYNTAX INTEGER
				{
				createErpDomain(1),
				destroyErpDomain(2),
				setErpDomainProfile(3),
				setErpProtectionActivation(4),
				setErpHoldOffTime(5),
				setErpRingPriority(6),
				setErpTrap(7)
				}
			MAX-ACCESS read-write
			STATUS current
			DESCRIPTION
				"
				createErpDomain:
				sleErpDomainControlIndex
				sleErpDomainControlName
				sleErpDomainControlPrimaryPort
				sleErpDomainControlSecondaryPort
				sleErpDomainControlBridgeRole
				sleErpDomainControlProtectionActivation
				sleErpDomainControlOperatorRequest
				sleErpDomainControlWaitToRestoreTime
				sleErpDomainControlTestPacketInterval
				sleErpDomainControlLearningDisabledTime
				
				destroyErpDomain:
				sleErpDomainControlIndex
				 
				setErpDomainProfile:
				sleErpDomainControlIndex 
				sleErpDomainControlName
				sleErpDomainControlPrimaryPort
				sleErpDomainControlSecondaryPort
				sleErpDomainControlBridgeRole
				sleErpDomainControlOperatorRequest
				sleErpDomainControlWaitToRestoreTime
				sleErpDomainControlTestPacketInterval
				sleErpDomainControlLearningDisabledTime
				
				setErpProtectionActivation:
				sleErpDomainControlIndex 
				sleErpDomainControlProtectionActivation
				"
			::= { sleErpDomainControl 1 }

		
		-- 1.3.6.1.4.1.6296.101.3.18.2.2
		sleErpDomainControlStatus OBJECT-TYPE
			SYNTAX SleControlStatusType
			MAX-ACCESS read-only
			STATUS current
			DESCRIPTION
				"The status of a user command. 
				"
			::= { sleErpDomainControl 2 }

		
		-- 1.3.6.1.4.1.6296.101.3.18.2.3
		sleErpDomainControlTimer OBJECT-TYPE
			SYNTAX Gauge32
			MAX-ACCESS read-write
			STATUS current
			DESCRIPTION
				"The maximum wait time for the manager for a long running user command. 
				"
			::= { sleErpDomainControl 3 }

		
		-- 1.3.6.1.4.1.6296.101.3.18.2.4
		sleErpDomainControlTImeStamp OBJECT-TYPE
			SYNTAX TimeTicks
			MAX-ACCESS read-only
			STATUS current
			DESCRIPTION
				"The time stamp of the last command (end of command)."
			::= { sleErpDomainControl 4 }

		
		-- 1.3.6.1.4.1.6296.101.3.18.2.5
		sleErpDomainControlReqResult OBJECT-TYPE
			SYNTAX SleControlRequestResultType
			MAX-ACCESS read-only
			STATUS current
			DESCRIPTION
				"The result of the last user command."
			::= { sleErpDomainControl 5 }

		
		-- 1.3.6.1.4.1.6296.101.3.18.2.6
		sleErpDomainControlIndex OBJECT-TYPE
			SYNTAX Integer32
			MAX-ACCESS read-write
			STATUS current
			DESCRIPTION
				" "
			::= { sleErpDomainControl 6 }

		
		-- 1.3.6.1.4.1.6296.101.3.18.2.7
		sleErpDomainControlName OBJECT-TYPE
			SYNTAX OCTET STRING
			MAX-ACCESS read-write
			STATUS current
			DESCRIPTION
				" "
			::= { sleErpDomainControl 7 }

		
		-- 1.3.6.1.4.1.6296.101.3.18.2.8
		sleErpDomainControlPrimaryPort OBJECT-TYPE
			SYNTAX InterfaceIndex
			MAX-ACCESS read-write
			STATUS current
			DESCRIPTION
				" "
			::= { sleErpDomainControl 8 }

		
		-- 1.3.6.1.4.1.6296.101.3.18.2.9
		sleErpDomainControlSecondaryPort OBJECT-TYPE
			SYNTAX InterfaceIndex
			MAX-ACCESS read-write
			STATUS current
			DESCRIPTION
				" "
			::= { sleErpDomainControl 9 }

		
		-- 1.3.6.1.4.1.6296.101.3.18.2.10
		sleErpDomainControlBridgeRole OBJECT-TYPE
			SYNTAX INTEGER
				{
				normalNode(0),
				rmNode(1)
				}
			MAX-ACCESS read-write
			STATUS current
			DESCRIPTION
				" "
			::= { sleErpDomainControl 10 }

		
		-- 1.3.6.1.4.1.6296.101.3.18.2.11
		sleErpDomainControlProtectionActivation OBJECT-TYPE
			SYNTAX INTEGER
				{
				deactivated(0),
				activated(1)
				}
			MAX-ACCESS read-write
			STATUS current
			DESCRIPTION
				" "
			::= { sleErpDomainControl 11 }

		
		-- 1.3.6.1.4.1.6296.101.3.18.2.12
		sleErpDomainControlOperatorRequest OBJECT-TYPE
			SYNTAX INTEGER
				{
				clear(0),
				manualToSecondary(1)
				}
			MAX-ACCESS read-write
			STATUS current
			DESCRIPTION
				" "
			::= { sleErpDomainControl 12 }

		
		-- 1.3.6.1.4.1.6296.101.3.18.2.13
		sleErpDomainControlWaitToRestoreTime OBJECT-TYPE
			SYNTAX INTEGER (1..720)
			MAX-ACCESS read-write
			STATUS current
			DESCRIPTION
				" "
			::= { sleErpDomainControl 13 }

		
		-- 1.3.6.1.4.1.6296.101.3.18.2.14
		sleErpDomainControlTestPacketInterval OBJECT-TYPE
			SYNTAX INTEGER (10..500)
			MAX-ACCESS read-write
			STATUS current
			DESCRIPTION
				" "
			::= { sleErpDomainControl 14 }

		
		-- 1.3.6.1.4.1.6296.101.3.18.2.15
		sleErpDomainControlLearningDisabledTime OBJECT-TYPE
			SYNTAX INTEGER (0..500)
			MAX-ACCESS read-write
			STATUS current
			DESCRIPTION
				" "
			::= { sleErpDomainControl 15 }

		
		-- 1.3.6.1.4.1.6296.101.3.18.2.16
		sleErpDomainControlHoldOffTime OBJECT-TYPE
			SYNTAX INTEGER (0 | 1..20000)
			MAX-ACCESS read-write
			STATUS current
			DESCRIPTION
				"Description."
			::= { sleErpDomainControl 16 }

		
		-- 1.3.6.1.4.1.6296.101.3.18.2.17
		sleErpDomainControlRingPriority OBJECT-TYPE
			SYNTAX INTEGER (0 | 1..255)
			MAX-ACCESS read-write
			STATUS current
			DESCRIPTION
				"Description."
			::= { sleErpDomainControl 17 }

		
		-- 1.3.6.1.4.1.6296.101.3.18.2.18
		sleErpDomainControlLotp OBJECT-TYPE
			SYNTAX INTEGER
				{
				clear(0),
				raised(1)
				}
			MAX-ACCESS read-write
			STATUS current
			DESCRIPTION
				"Description."
			::= { sleErpDomainControl 18 }

		
		-- 1.3.6.1.4.1.6296.101.3.18.2.19
		sleErpDomainControlULotp OBJECT-TYPE
			SYNTAX INTEGER
				{
				clear(0),
				raised(1)
				}
			MAX-ACCESS read-write
			STATUS current
			DESCRIPTION
				"Description."
			::= { sleErpDomainControl 19 }

		
		-- 1.3.6.1.4.1.6296.101.3.18.2.20
		sleErpDomainControlMultipleRM OBJECT-TYPE
			SYNTAX INTEGER
				{
				clear(0),
				raised(1)
				}
			MAX-ACCESS read-write
			STATUS current
			DESCRIPTION
				"Description."
			::= { sleErpDomainControl 20 }

		
		-- 1.3.6.1.4.1.6296.101.3.18.2.21
		sleErpDomainControlRMNodeReacheablility OBJECT-TYPE
			SYNTAX INTEGER
				{
				clear(0),
				raised(1)
				}
			MAX-ACCESS read-write
			STATUS current
			DESCRIPTION
				"Description."
			::= { sleErpDomainControl 21 }

		
		-- 1.3.6.1.4.1.6296.101.3.18.3
		sleErpDomainNotification OBJECT IDENTIFIER ::= { sleErpDomain 3 }

		
		-- 1.3.6.1.4.1.6296.101.3.18.3.1
		sleErpDomainCreated NOTIFICATION-TYPE
			OBJECTS { sleErpDomainControlRequest, sleErpDomainControlReqResult, sleErpDomainControlTImeStamp, sleErpDomainName, sleErpDomainPrimaryPort, 
				sleErpDomainSecondaryPort, sleErpDomainBridgeRole, sleErpDomainProtectionActivation, sleErpDomainOperatorRequest, sleErpDomainWaitToRestoreTime, 
				sleErpDomainTestPacketInterval, sleErpDomainLearningDisabledTime }
			STATUS current
			DESCRIPTION 
				" "
			::= { sleErpDomainNotification 1 }

		
		-- 1.3.6.1.4.1.6296.101.3.18.3.2
		sleErpDomainDestroyed NOTIFICATION-TYPE
			OBJECTS { sleErpDomainControlRequest, sleErpDomainControlReqResult, sleErpDomainControlTImeStamp, sleErpDomainIndex }
			STATUS current
			DESCRIPTION 
				" "
			::= { sleErpDomainNotification 2 }

		
		-- 1.3.6.1.4.1.6296.101.3.18.3.3
		sleErpDomainProfileChanged NOTIFICATION-TYPE
			OBJECTS { sleErpDomainControlRequest, sleErpDomainControlReqResult, sleErpDomainControlTImeStamp, sleErpDomainName, sleErpDomainPrimaryPort, 
				sleErpDomainSecondaryPort, sleErpDomainBridgeRole, sleErpDomainOperatorRequest, sleErpDomainWaitToRestoreTime, sleErpDomainTestPacketInterval, 
				sleErpDomainLearningDisabledTime }
			STATUS current
			DESCRIPTION 
				" "
			::= { sleErpDomainNotification 3 }

		
		-- 1.3.6.1.4.1.6296.101.3.18.3.4
		sleErpProtectionActivationChanged NOTIFICATION-TYPE
			OBJECTS { sleErpDomainControlRequest, sleErpDomainControlReqResult, sleErpDomainControlTImeStamp, sleErpDomainProtectionActivation }
			STATUS current
			DESCRIPTION 
				" "
			::= { sleErpDomainNotification 4 }

		
		-- 1.3.6.1.4.1.6296.101.3.18.3.5
		sleErpHoldOffTimeChanged NOTIFICATION-TYPE
			OBJECTS { sleErpDomainControlRequest, sleErpDomainControlTImeStamp, sleErpDomainControlReqResult, sleErpDomainHoldOffTime }
			STATUS current
			DESCRIPTION 
				"Description."
			::= { sleErpDomainNotification 5 }

		
		-- 1.3.6.1.4.1.6296.101.3.18.3.6
		sleErpRingPriorityChanged NOTIFICATION-TYPE
			OBJECTS { sleErpDomainControlRequest, sleErpDomainControlTImeStamp, sleErpDomainControlReqResult, sleErpDomainRingPriority }
			STATUS current
			DESCRIPTION 
				"Description."
			::= { sleErpDomainNotification 6 }

		
		-- 1.3.6.1.4.1.6296.101.3.18.3.7
		sleErpTrapChanged NOTIFICATION-TYPE
			OBJECTS { sleErpDomainControlRequest, sleErpDomainControlTImeStamp, sleErpDomainControlReqResult, sleErpDomainLotp, sleErpDomainULotp, 
				sleErpDomainMultipleRM, sleErpDomainRMNodeReacheablility }
			STATUS current
			DESCRIPTION 
				"Description."
			::= { sleErpDomainNotification 7 }

		
--  1.3.6.1.4.1.6296.9.8.19
		-- 1.3.6.1.4.1.6296.101.3.19
		sleLldpPort OBJECT IDENTIFIER ::= { sleBridge 19 }

		
--  1.3.6.1.4.1.6296.9.8.19.1
		-- 1.3.6.1.4.1.6296.101.3.19.1
		sleLldpPortTable OBJECT-TYPE
			SYNTAX SEQUENCE OF SleLldpPortEntry
			MAX-ACCESS not-accessible
			STATUS current
			DESCRIPTION
				" "
			::= { sleLldpPort 1 }

		
--  1.3.6.1.4.1.6296.9.8.19.1.1
		-- 1.3.6.1.4.1.6296.101.3.19.1.1
		sleLldpPortEntry OBJECT-TYPE
			SYNTAX SleLldpPortEntry
			MAX-ACCESS not-accessible
			STATUS current
			DESCRIPTION
				" "
			INDEX { sleLldpPortIndex }
			::= { sleLldpPortTable 1 }

		
		SleLldpPortEntry ::=
			SEQUENCE { 
				sleLldpPortIndex
					INTEGER,
				sleLldpPortActivity
					Boolean,
				sleLldpPortAdminStatus
					INTEGER,
				sleLldpPortNotificationEnable
					Boolean,
				sleLldpPortTLVsTxEnable
					BITS,
				sleLldpPortMgmtTxEnable
					Boolean,
				sleLldpPortMgmtAddress
					IpAddress
			 }

--  1.3.6.1.4.1.6296.9.8.19.1.1.1
		-- 1.3.6.1.4.1.6296.101.3.19.1.1.1
		sleLldpPortIndex OBJECT-TYPE
			SYNTAX INTEGER (1..255)
			MAX-ACCESS read-only
			STATUS current
			DESCRIPTION
				" "
			::= { sleLldpPortEntry 1 }

		
		-- 1.3.6.1.4.1.6296.101.3.19.1.1.2
		sleLldpPortActivity OBJECT-TYPE
			SYNTAX Boolean
			MAX-ACCESS read-only
			STATUS current
			DESCRIPTION
				"Description."
			::= { sleLldpPortEntry 2 }

		
--  1.3.6.1.4.1.6296.9.8.19.1.1.2
		-- 1.3.6.1.4.1.6296.101.3.19.1.1.3
		sleLldpPortAdminStatus OBJECT-TYPE
			SYNTAX INTEGER
				{
				txOnly(1),
				rxOnly(2),
				txAndRx(3),
				disabled(4)
				}
			MAX-ACCESS read-write
			STATUS current
			DESCRIPTION
				"The administratively desired status of the local LLDP agent."
			::= { sleLldpPortEntry 3 }

		
--  It controls, on a per port basis,  whether or not notifications from the agent are enabled.
-- 1.3.6.1.4.1.6296.9.8.19.1.1.3
		-- 1.3.6.1.4.1.6296.101.3.19.1.1.4
		sleLldpPortNotificationEnable OBJECT-TYPE
			SYNTAX Boolean
			MAX-ACCESS read-write
			STATUS current
			DESCRIPTION
				"It controls, on a per port basis,  whether or not notifications from the agent are enabled. "
			::= { sleLldpPortEntry 4 }

		
--  1.3.6.1.4.1.6296.9.8.19.1.1.4
		-- 1.3.6.1.4.1.6296.101.3.19.1.1.5
		sleLldpPortTLVsTxEnable OBJECT-TYPE
			SYNTAX BITS
				{
				portDesc(0),
				sysName(1),
				sysDesc(2),
				sysCap(3)
				}
			MAX-ACCESS read-write
			STATUS current
			DESCRIPTION
				"Bitmap that includes the basic set of LLDP TLVs whose transmission is allowed on the local LLDP agent by the network management."
			::= { sleLldpPortEntry 5 }

		
		-- 1.3.6.1.4.1.6296.101.3.19.1.1.6
		sleLldpPortMgmtTxEnable OBJECT-TYPE
			SYNTAX Boolean
			MAX-ACCESS read-only
			STATUS current
			DESCRIPTION
				"It indicates that the port is either enable or not to transfer management address."
			::= { sleLldpPortEntry 6 }

		
		-- 1.3.6.1.4.1.6296.101.3.19.1.1.7
		sleLldpPortMgmtAddress OBJECT-TYPE
			SYNTAX IpAddress
			MAX-ACCESS read-only
			STATUS current
			DESCRIPTION
				"Management address to transfer on the port."
			::= { sleLldpPortEntry 7 }

		
--  1.3.6.1.4.1.6296.9.8.19.2
		-- 1.3.6.1.4.1.6296.101.3.19.2
		sleLldpPortControl OBJECT IDENTIFIER ::= { sleLldpPort 2 }

		
--  1.3.6.1.4.1.6296.9.8.19.2.1
		-- 1.3.6.1.4.1.6296.101.3.19.2.1
		sleLldpPortControlRequest OBJECT-TYPE
			SYNTAX INTEGER { setLldpPortProfile(1) }
			MAX-ACCESS read-write
			STATUS current
			DESCRIPTION
				" "
			::= { sleLldpPortControl 1 }

		
--  1.3.6.1.4.1.6296.9.8.19.2.2
		-- 1.3.6.1.4.1.6296.101.3.19.2.2
		sleLldpPortControlStatus OBJECT-TYPE
			SYNTAX SleControlStatusType
			MAX-ACCESS read-only
			STATUS current
			DESCRIPTION
				" "
			::= { sleLldpPortControl 2 }

		
--  1.3.6.1.4.1.6296.9.8.19.2.3
		-- 1.3.6.1.4.1.6296.101.3.19.2.3
		sleLldpPortControlTimer OBJECT-TYPE
			SYNTAX Gauge32
			MAX-ACCESS read-write
			STATUS current
			DESCRIPTION
				" "
			::= { sleLldpPortControl 3 }

		
--  1.3.6.1.4.1.6296.9.8.19.2.4
		-- 1.3.6.1.4.1.6296.101.3.19.2.4
		sleLldpPortControlTimeStamp OBJECT-TYPE
			SYNTAX TimeTicks
			MAX-ACCESS read-only
			STATUS current
			DESCRIPTION
				" "
			::= { sleLldpPortControl 4 }

		
--  1.3.6.1.4.1.6296.9.8.19.2.5
		-- 1.3.6.1.4.1.6296.101.3.19.2.5
		sleLldpPortControlReqResult OBJECT-TYPE
			SYNTAX SleControlRequestResultType
			MAX-ACCESS read-only
			STATUS current
			DESCRIPTION
				" "
			::= { sleLldpPortControl 5 }

		
		-- 1.3.6.1.4.1.6296.101.3.19.2.6
		sleLldpPortControlIndex OBJECT-TYPE
			SYNTAX INTEGER (1..255)
			MAX-ACCESS read-write
			STATUS current
			DESCRIPTION
				"sleLldpPortIndex"
			::= { sleLldpPortControl 6 }

		
		-- 1.3.6.1.4.1.6296.101.3.19.2.7
		sleLldpPortControlActivity OBJECT-TYPE
			SYNTAX Boolean
			MAX-ACCESS read-write
			STATUS current
			DESCRIPTION
				"Description."
			::= { sleLldpPortControl 7 }

		
--  1.3.6.1.4.1.6296.9.8.19.2.6
		-- 1.3.6.1.4.1.6296.101.3.19.2.8
		sleLldpPortControlAdminstatus OBJECT-TYPE
			SYNTAX INTEGER
				{
				txOnly(1),
				rxOnly(2),
				txAndRx(3),
				disabled(4)
				}
			MAX-ACCESS read-write
			STATUS current
			DESCRIPTION
				" "
			::= { sleLldpPortControl 8 }

		
--  1.3.6.1.4.1.6296.9.8.19.2.7
		-- 1.3.6.1.4.1.6296.101.3.19.2.9
		sleLldpPortControlNotificationEnable OBJECT-TYPE
			SYNTAX Boolean
			MAX-ACCESS read-write
			STATUS current
			DESCRIPTION
				" "
			::= { sleLldpPortControl 9 }

		
--  1.3.6.1.4.1.6296.9.8.19.2.8
		-- 1.3.6.1.4.1.6296.101.3.19.2.10
		sleLldpPortControlTLVsTxEnable OBJECT-TYPE
			SYNTAX BITS
				{
				portDesc(0),
				sysName(1),
				sysDesc(2),
				sysCap(3)
				}
			MAX-ACCESS read-write
			STATUS current
			DESCRIPTION
				" "
			::= { sleLldpPortControl 10 }

		
		-- 1.3.6.1.4.1.6296.101.3.19.2.11
		sleLldpPortControlMgmtTxEnable OBJECT-TYPE
			SYNTAX Boolean
			MAX-ACCESS read-write
			STATUS current
			DESCRIPTION
				"It indicates that the port is either enable or not to transfer management address."
			::= { sleLldpPortControl 11 }

		
		-- 1.3.6.1.4.1.6296.101.3.19.2.12
		sleLldpPortControlMgmtAddress OBJECT-TYPE
			SYNTAX IpAddress
			MAX-ACCESS read-write
			STATUS current
			DESCRIPTION
				"Management address to transfer on the port."
			::= { sleLldpPortControl 12 }

		
--  1.3.6.1.4.1.6296.9.8.19.3
		-- 1.3.6.1.4.1.6296.101.3.19.3
		sleLldpPortNotification OBJECT IDENTIFIER ::= { sleLldpPort 3 }

		
--  1.3.6.1.4.1.6296.9.8.19.3.1
		-- 1.3.6.1.4.1.6296.101.3.19.3.1
		sleLldpPortProfileChanged NOTIFICATION-TYPE
			OBJECTS { sleLldpPortActivity, sleLldpPortAdminStatus, sleLldpPortNotificationEnable, sleLldpPortTLVsTxEnable, sleLldpPortMgmtTxEnable, 
				sleLldpPortMgmtAddress, sleLldpPortControlRequest, sleLldpPortControlTimeStamp, sleLldpPortControlReqResult }
			STATUS current
			DESCRIPTION 
				" "
			::= { sleLldpPortNotification 1 }

		
--  1.3.6.1.4.1.6296.9.8.20
		-- 1.3.6.1.4.1.6296.101.3.20
		sleLldpRemote OBJECT IDENTIFIER ::= { sleBridge 20 }

		
--  1.3.6.1.4.1.6296.9.8.20.1
		-- 1.3.6.1.4.1.6296.101.3.20.1
		sleLldpRemoteTable OBJECT-TYPE
			SYNTAX SEQUENCE OF SleLldpRemoteEntry
			MAX-ACCESS not-accessible
			STATUS current
			DESCRIPTION
				" "
			::= { sleLldpRemote 1 }

		
--  1.3.6.1.4.1.6296.9.8.20.1.1
		-- 1.3.6.1.4.1.6296.101.3.20.1.1
		sleLldpRemoteEntry OBJECT-TYPE
			SYNTAX SleLldpRemoteEntry
			MAX-ACCESS not-accessible
			STATUS current
			DESCRIPTION
				" "
			INDEX { sleLldpPortIndex, sleLldpRemIndex }
			::= { sleLldpRemoteTable 1 }

		
		SleLldpRemoteEntry ::=
			SEQUENCE { 
				sleLldpRemIndex
					Integer32,
				sleLldpRemTimeMark
					TimeTicks,
				sleLldpRemChassisIdSubtype
					INTEGER,
				sleLldpRemChassisId
					OCTET STRING,
				sleLldpRemPortIdSubtype
					INTEGER,
				sleLldpRemPortId
					OCTET STRING,
				sleLldpRemPortDesc
					OCTET STRING,
				sleLldpRemSysName
					OCTET STRING,
				sleLldpRemSysDesc
					OCTET STRING,
				sleLldpRemSysCapSupported
					BITS,
				sleLldpRemSysCapEnabled
					BITS
			 }

--  1.3.6.1.4.1.6296.9.8.20.1.1.3
		-- 1.3.6.1.4.1.6296.101.3.20.1.1.1
		sleLldpRemIndex OBJECT-TYPE
			SYNTAX Integer32 (1..2147483647)
			MAX-ACCESS read-write
			STATUS current
			DESCRIPTION
				"This object represents an arbitrary local integer value used by this agent to identify a particular connection instance, unique only for the indicated remote system."
			::= { sleLldpRemoteEntry 1 }

		
--  1.3.6.1.4.1.6296.9.8.20.1.1.1
		-- 1.3.6.1.4.1.6296.101.3.20.1.1.2
		sleLldpRemTimeMark OBJECT-TYPE
			SYNTAX TimeTicks
			MAX-ACCESS read-only
			STATUS current
			DESCRIPTION
				"The sysUptime that this entry has been created or modified."
			::= { sleLldpRemoteEntry 2 }

		
--  1.3.6.1.4.1.6296.9.8.20.1.1.4
		-- 1.3.6.1.4.1.6296.101.3.20.1.1.3
		sleLldpRemChassisIdSubtype OBJECT-TYPE
			SYNTAX INTEGER
				{
				chassisComponent(1),
				interfaceAlias(2),
				portComponent(3),
				macAddress(4),
				networkAddress(5),
				interfaceName(6),
				local(7)
				}
			MAX-ACCESS read-only
			STATUS current
			DESCRIPTION
				"The type of encoding used to identify the chassis associatedwith the remote system."
			::= { sleLldpRemoteEntry 3 }

		
--  1.3.6.1.4.1.6296.9.8.20.1.1.5
		-- 1.3.6.1.4.1.6296.101.3.20.1.1.4
		sleLldpRemChassisId OBJECT-TYPE
			SYNTAX OCTET STRING (SIZE (1..255))
			MAX-ACCESS read-write
			STATUS current
			DESCRIPTION
				"The type of encoding used to identify the chassis associatedwith the remote system."
			::= { sleLldpRemoteEntry 4 }

		
--  1.3.6.1.4.1.6296.9.8.20.1.1.6
		-- 1.3.6.1.4.1.6296.101.3.20.1.1.5
		sleLldpRemPortIdSubtype OBJECT-TYPE
			SYNTAX INTEGER
				{
				interfaceAlias(1),
				portComponent(2),
				macAddress(3),
				networkAddress(4),
				interfaceName(5),
				agentCircuitId(6),
				local(7)
				}
			MAX-ACCESS read-write
			STATUS current
			DESCRIPTION
				"The type of port identifier encoding used in the associated'lldpRemPortId' object."
			::= { sleLldpRemoteEntry 5 }

		
--  1.3.6.1.4.1.6296.9.8.20.1.1.7
		-- 1.3.6.1.4.1.6296.101.3.20.1.1.6
		sleLldpRemPortId OBJECT-TYPE
			SYNTAX OCTET STRING (SIZE (1..255))
			MAX-ACCESS read-only
			STATUS current
			DESCRIPTION
				"The string value used to identify the port component associated with the remote system."
			::= { sleLldpRemoteEntry 6 }

		
--  1.3.6.1.4.1.6296.9.8.20.1.1.8
		-- 1.3.6.1.4.1.6296.101.3.20.1.1.7
		sleLldpRemPortDesc OBJECT-TYPE
			SYNTAX OCTET STRING (SIZE (0..255))
			MAX-ACCESS read-only
			STATUS current
			DESCRIPTION
				"The string value used to identify the description of the given port associated with the remote system."
			::= { sleLldpRemoteEntry 7 }

		
--  1.3.6.1.4.1.6296.9.8.20.1.1.9
		-- 1.3.6.1.4.1.6296.101.3.20.1.1.8
		sleLldpRemSysName OBJECT-TYPE
			SYNTAX OCTET STRING (SIZE (0..255))
			MAX-ACCESS read-only
			STATUS current
			DESCRIPTION
				"The string value used to identify the system name of the remote system."
			::= { sleLldpRemoteEntry 8 }

		
--  1.3.6.1.4.1.6296.9.8.20.1.1.10
		-- 1.3.6.1.4.1.6296.101.3.20.1.1.9
		sleLldpRemSysDesc OBJECT-TYPE
			SYNTAX OCTET STRING (SIZE (0..255))
			MAX-ACCESS read-only
			STATUS current
			DESCRIPTION
				"The string value used to identify the system description of the remote system."
			::= { sleLldpRemoteEntry 9 }

		
--  1.3.6.1.4.1.6296.9.8.20.1.1.11
		-- 1.3.6.1.4.1.6296.101.3.20.1.1.10
		sleLldpRemSysCapSupported OBJECT-TYPE
			SYNTAX BITS
				{
				other(0),
				repeater(1),
				bridge(2),
				wlanAccessPoint(3),
				router(4),
				telephone(5),
				docsisCableDevice(6),
				stationOnly(7)
				}
			MAX-ACCESS read-only
			STATUS current
			DESCRIPTION
				"The bitmap value used to identify which system capabilities are supported on the remote system."
			::= { sleLldpRemoteEntry 10 }

		
--  1.3.6.1.4.1.6296.9.8.20.1.1.12
		-- 1.3.6.1.4.1.6296.101.3.20.1.1.11
		sleLldpRemSysCapEnabled OBJECT-TYPE
			SYNTAX BITS
				{
				other(0),
				repeater(1),
				bridge(2),
				wlanAccessPoint(3),
				router(4),
				telephone(5),
				docsisCableDevice(6),
				stationOnly(7)
				}
			MAX-ACCESS read-only
			STATUS current
			DESCRIPTION
				"The bitmap value used to identify which system capabilities are enabled on the remote system."
			::= { sleLldpRemoteEntry 11 }

		
		-- 1.3.6.1.4.1.6296.101.3.21
		sleLldpStatistics OBJECT IDENTIFIER ::= { sleBridge 21 }

		
		-- 1.3.6.1.4.1.6296.101.3.21.1
		sleLldpStatisticsTable OBJECT-TYPE
			SYNTAX SEQUENCE OF SleLldpStatisticsEntry
			MAX-ACCESS not-accessible
			STATUS current
			DESCRIPTION
				"Description."
			::= { sleLldpStatistics 1 }

		
		-- 1.3.6.1.4.1.6296.101.3.21.1.1
		sleLldpStatisticsEntry OBJECT-TYPE
			SYNTAX SleLldpStatisticsEntry
			MAX-ACCESS not-accessible
			STATUS current
			DESCRIPTION
				"Description."
			INDEX { sleLldpPortIndex }
			::= { sleLldpStatisticsTable 1 }

		
		SleLldpStatisticsEntry ::=
			SEQUENCE { 
				sleLldpStatsTxPortFramesTotal
					Integer32,
				sleLldpStatsRxPortFramesDiscardedTotal
					Counter32,
				sleLldpStatsRxPortFramesErrors
					Integer32,
				sleLldpStatsRxPortFramesTotal
					Counter32,
				sleLldpStatsRxPortTLVsDiscardedTotal
					Integer32,
				sleLldpStatsRxPortTLVsUnrecognizedTotal
					Integer32,
				sleLldpStatsRxPortAgeoutsTotal
					Counter32
			 }

		-- 1.3.6.1.4.1.6296.101.3.21.1.1.1
		sleLldpStatsTxPortFramesTotal OBJECT-TYPE
			SYNTAX Integer32
			MAX-ACCESS read-only
			STATUS current
			DESCRIPTION
				"The number of LLDP frames transmitted by this LLDP agent on the indicated port."
			::= { sleLldpStatisticsEntry 1 }

		
		-- 1.3.6.1.4.1.6296.101.3.21.1.1.2
		sleLldpStatsRxPortFramesDiscardedTotal OBJECT-TYPE
			SYNTAX Counter32
			MAX-ACCESS read-only
			STATUS current
			DESCRIPTION
				"The number of LLDP frames received by this LLDP agent on  the indicated port, and then discarded for any reason."
			::= { sleLldpStatisticsEntry 2 }

		
		-- 1.3.6.1.4.1.6296.101.3.21.1.1.3
		sleLldpStatsRxPortFramesErrors OBJECT-TYPE
			SYNTAX Integer32
			MAX-ACCESS read-only
			STATUS current
			DESCRIPTION
				"The number of invalid LLDP frames received by this LLDPagent on the indicated port, while this LLDP agent is enabled."
			::= { sleLldpStatisticsEntry 3 }

		
		-- 1.3.6.1.4.1.6296.101.3.21.1.1.4
		sleLldpStatsRxPortFramesTotal OBJECT-TYPE
			SYNTAX Counter32
			MAX-ACCESS read-only
			STATUS current
			DESCRIPTION
				"The number of valid LLDP frames received by this LLDP agent on the indicated port, while this LLDP agent is enabled."
			::= { sleLldpStatisticsEntry 4 }

		
		-- 1.3.6.1.4.1.6296.101.3.21.1.1.5
		sleLldpStatsRxPortTLVsDiscardedTotal OBJECT-TYPE
			SYNTAX Integer32
			MAX-ACCESS read-only
			STATUS current
			DESCRIPTION
				"The number of LLDP TLVs discarded for any reason by this LLDP agent on the indicated port."
			::= { sleLldpStatisticsEntry 5 }

		
		-- 1.3.6.1.4.1.6296.101.3.21.1.1.6
		sleLldpStatsRxPortTLVsUnrecognizedTotal OBJECT-TYPE
			SYNTAX Integer32
			MAX-ACCESS read-only
			STATUS current
			DESCRIPTION
				"The number of LLDP TLVs received on the given port that are not recognized by this LLDP agent on the indicated port."
			::= { sleLldpStatisticsEntry 6 }

		
		-- 1.3.6.1.4.1.6296.101.3.21.1.1.7
		sleLldpStatsRxPortAgeoutsTotal OBJECT-TYPE
			SYNTAX Counter32
			MAX-ACCESS read-only
			STATUS current
			DESCRIPTION
				"The counter that represents the number of age-outs that occurred on a given port."
			::= { sleLldpStatisticsEntry 7 }

		
		-- 1.3.6.1.4.1.6296.101.3.21.2
		sleLldpStatisticsControl OBJECT IDENTIFIER ::= { sleLldpStatistics 2 }

		
		-- 1.3.6.1.4.1.6296.101.3.21.2.1
		sleLldpStatsControlRequest OBJECT-TYPE
			SYNTAX INTEGER { clearLldpStatistics(1) }
			MAX-ACCESS read-write
			STATUS current
			DESCRIPTION
				"Description."
			::= { sleLldpStatisticsControl 1 }

		
		-- 1.3.6.1.4.1.6296.101.3.21.2.2
		sleLldpStatsControlStatus OBJECT-TYPE
			SYNTAX SleControlStatusType
			MAX-ACCESS read-only
			STATUS current
			DESCRIPTION
				"Description."
			::= { sleLldpStatisticsControl 2 }

		
		-- 1.3.6.1.4.1.6296.101.3.21.2.3
		sleLldpStatsControlTimer OBJECT-TYPE
			SYNTAX Gauge32
			MAX-ACCESS read-write
			STATUS current
			DESCRIPTION
				"Description."
			::= { sleLldpStatisticsControl 3 }

		
		-- 1.3.6.1.4.1.6296.101.3.21.2.4
		sleLldpStatsControlTimeStamp OBJECT-TYPE
			SYNTAX TimeTicks
			MAX-ACCESS read-only
			STATUS current
			DESCRIPTION
				"Description."
			::= { sleLldpStatisticsControl 4 }

		
		-- 1.3.6.1.4.1.6296.101.3.21.2.5
		sleLldpStatsControlReqResult OBJECT-TYPE
			SYNTAX SleControlRequestResultType
			MAX-ACCESS read-only
			STATUS current
			DESCRIPTION
				"Description."
			::= { sleLldpStatisticsControl 5 }

		
		-- 1.3.6.1.4.1.6296.101.3.21.2.6
		sleLldpStatsControlPortIndex OBJECT-TYPE
			SYNTAX Unsigned32 (1..255)
			MAX-ACCESS read-write
			STATUS current
			DESCRIPTION
				"Description."
			::= { sleLldpStatisticsControl 6 }

		
		-- 1.3.6.1.4.1.6296.101.3.21.3
		sleLldpStatisticsNotification OBJECT IDENTIFIER ::= { sleLldpStatistics 3 }

		
		-- 1.3.6.1.4.1.6296.101.3.21.3.1
		sleLldpStatisticsCleared NOTIFICATION-TYPE
			OBJECTS { sleLldpStatsControlRequest, sleLldpStatsControlTimeStamp, sleLldpStatsControlReqResult, sleLldpPortIndex }
			STATUS current
			DESCRIPTION 
				"Description."
			::= { sleLldpStatisticsNotification 1 }

		
		-- 1.3.6.1.4.1.6296.101.3.22
		sleBridgePortSecurity OBJECT IDENTIFIER ::= { sleBridge 22 }

		
		-- 1.3.6.1.4.1.6296.101.3.22.1
		sleBridgePSTable OBJECT-TYPE
			SYNTAX SEQUENCE OF SleBridgePSEntry
			MAX-ACCESS not-accessible
			STATUS current
			DESCRIPTION
				"Description."
			::= { sleBridgePortSecurity 1 }

		
		-- 1.3.6.1.4.1.6296.101.3.22.1.1
		sleBridgePSEntry OBJECT-TYPE
			SYNTAX SleBridgePSEntry
			MAX-ACCESS not-accessible
			STATUS current
			DESCRIPTION
				"Description."
			INDEX { sleBridgePSIndex }
			::= { sleBridgePSTable 1 }

		
		SleBridgePSEntry ::=
			SEQUENCE { 
				sleBridgePSIndex
					InterfaceIndex,
				sleBridgePSStatus
					INTEGER,
				sleBridgePSMaxCount
					INTEGER,
				sleBridgePSCurrCount
					Unsigned32,
				sleBridgePSAgingType
					INTEGER,
				sleBridgePSAgingTimer
					INTEGER,
				sleBridgePSAgingStatic
					INTEGER,
				sleBridgePSViolation
					INTEGER
			 }

		-- 1.3.6.1.4.1.6296.101.3.22.1.1.1
		sleBridgePSIndex OBJECT-TYPE
			SYNTAX InterfaceIndex
			MAX-ACCESS read-only
			STATUS current
			DESCRIPTION
				"Description."
			::= { sleBridgePSEntry 1 }

		
		-- 1.3.6.1.4.1.6296.101.3.22.1.1.2
		sleBridgePSStatus OBJECT-TYPE
			SYNTAX INTEGER
				{
				enable(1),
				disable(2)
				}
			MAX-ACCESS read-only
			STATUS current
			DESCRIPTION
				"Description."
			::= { sleBridgePSEntry 2 }

		
		-- 1.3.6.1.4.1.6296.101.3.22.1.1.3
		sleBridgePSMaxCount OBJECT-TYPE
			SYNTAX INTEGER (-1 | 1..16384)
			MAX-ACCESS read-only
			STATUS current
			DESCRIPTION
				"Description."
			::= { sleBridgePSEntry 3 }

		
		-- 1.3.6.1.4.1.6296.101.3.22.1.1.4
		sleBridgePSCurrCount OBJECT-TYPE
			SYNTAX Unsigned32
			MAX-ACCESS read-only
			STATUS current
			DESCRIPTION
				"Description."
			::= { sleBridgePSEntry 4 }

		
		-- 1.3.6.1.4.1.6296.101.3.22.1.1.5
		sleBridgePSAgingType OBJECT-TYPE
			SYNTAX INTEGER
				{
				absolute(1),
				inactivity(2)
				}
			MAX-ACCESS read-only
			STATUS current
			DESCRIPTION
				"Description."
			::= { sleBridgePSEntry 5 }

		
		-- 1.3.6.1.4.1.6296.101.3.22.1.1.6
		sleBridgePSAgingTimer OBJECT-TYPE
			SYNTAX INTEGER (-1 | 0 | 1..2147483647)
			UNITS "second"
			MAX-ACCESS read-only
			STATUS current
			DESCRIPTION
				"Description."
			::= { sleBridgePSEntry 6 }

		
		-- 1.3.6.1.4.1.6296.101.3.22.1.1.7
		sleBridgePSAgingStatic OBJECT-TYPE
			SYNTAX INTEGER
				{
				enable(1),
				disable(2)
				}
			MAX-ACCESS read-only
			STATUS current
			DESCRIPTION
				"Description."
			::= { sleBridgePSEntry 7 }

		
		-- 1.3.6.1.4.1.6296.101.3.22.1.1.8
		sleBridgePSViolation OBJECT-TYPE
			SYNTAX INTEGER
				{
				shutdown(1),
				protect(2),
				restrict(3)
				}
			MAX-ACCESS read-only
			STATUS current
			DESCRIPTION
				"Description."
			::= { sleBridgePSEntry 8 }

		
		-- 1.3.6.1.4.1.6296.101.3.22.2
		sleBridgePSControl OBJECT IDENTIFIER ::= { sleBridgePortSecurity 2 }

		
		-- 1.3.6.1.4.1.6296.101.3.22.2.1
		sleBridgePSControlRequest OBJECT-TYPE
			SYNTAX INTEGER
				{
				setPSStatus(1),
				setPSMaxCount(2),
				setPSProfile(3)
				}
			MAX-ACCESS read-write
			STATUS current
			DESCRIPTION
				"Description."
			::= { sleBridgePSControl 1 }

		
		-- 1.3.6.1.4.1.6296.101.3.22.2.2
		sleBridgePSControlStatus OBJECT-TYPE
			SYNTAX SleControlStatusType
			MAX-ACCESS read-only
			STATUS current
			DESCRIPTION
				"Description."
			::= { sleBridgePSControl 2 }

		
		-- 1.3.6.1.4.1.6296.101.3.22.2.3
		sleBridgePSControlTimer OBJECT-TYPE
			SYNTAX Gauge32
			MAX-ACCESS read-write
			STATUS current
			DESCRIPTION
				"Description."
			::= { sleBridgePSControl 3 }

		
		-- 1.3.6.1.4.1.6296.101.3.22.2.4
		sleBridgePSControlTimeStamp OBJECT-TYPE
			SYNTAX TimeTicks
			MAX-ACCESS read-only
			STATUS current
			DESCRIPTION
				"Description."
			::= { sleBridgePSControl 4 }

		
		-- 1.3.6.1.4.1.6296.101.3.22.2.5
		sleBridgePSControlReqResult OBJECT-TYPE
			SYNTAX SleControlRequestResultType
			MAX-ACCESS read-only
			STATUS current
			DESCRIPTION
				"Description."
			::= { sleBridgePSControl 5 }

		
		-- 1.3.6.1.4.1.6296.101.3.22.2.6
		sleBridgePSControlIndex OBJECT-TYPE
			SYNTAX InterfaceIndex
			MAX-ACCESS read-write
			STATUS current
			DESCRIPTION
				"Description."
			::= { sleBridgePSControl 6 }

		
		-- 1.3.6.1.4.1.6296.101.3.22.2.7
		sleBridgePSControlPSStatus OBJECT-TYPE
			SYNTAX INTEGER
				{
				enable(1),
				disable(2)
				}
			MAX-ACCESS read-write
			STATUS current
			DESCRIPTION
				"Description."
			::= { sleBridgePSControl 7 }

		
		-- 1.3.6.1.4.1.6296.101.3.22.2.8
		sleBridgePSControlMaxCount OBJECT-TYPE
			SYNTAX INTEGER (-1 | 1..16384)
			MAX-ACCESS read-write
			STATUS current
			DESCRIPTION
				"Description."
			::= { sleBridgePSControl 8 }

		
		-- 1.3.6.1.4.1.6296.101.3.22.2.9
		sleBridgePSControlAgingType OBJECT-TYPE
			SYNTAX INTEGER
				{
				absolute(1),
				inactivity(2)
				}
			MAX-ACCESS read-write
			STATUS current
			DESCRIPTION
				"Description."
			::= { sleBridgePSControl 9 }

		
		-- 1.3.6.1.4.1.6296.101.3.22.2.10
		sleBridgePSControlAgingTimer OBJECT-TYPE
			SYNTAX INTEGER (-1 | 0 | 1..2147483647)
			UNITS "second"
			MAX-ACCESS read-write
			STATUS current
			DESCRIPTION
				"Description."
			::= { sleBridgePSControl 10 }

		
		-- 1.3.6.1.4.1.6296.101.3.22.2.11
		sleBridgePSControlAgingStatic OBJECT-TYPE
			SYNTAX INTEGER
				{
				enable(1),
				disable(2)
				}
			MAX-ACCESS read-write
			STATUS current
			DESCRIPTION
				"Description."
			::= { sleBridgePSControl 11 }

		
		-- 1.3.6.1.4.1.6296.101.3.22.2.12
		sleBridgePScontrolViolation OBJECT-TYPE
			SYNTAX INTEGER
				{
				shutdown(1),
				protect(2),
				restrict(3)
				}
			MAX-ACCESS read-write
			STATUS current
			DESCRIPTION
				"Description."
			::= { sleBridgePSControl 12 }

		
		-- 1.3.6.1.4.1.6296.101.3.22.3
		sleBridgePSNotification OBJECT IDENTIFIER ::= { sleBridgePortSecurity 3 }

		
		-- 1.3.6.1.4.1.6296.101.3.22.3.1
		sleBridgePSStatusChanged NOTIFICATION-TYPE
			OBJECTS { sleBridgePSControlRequest, sleBridgePSControlTimeStamp, sleBridgePSControlReqResult, sleBridgePSControlIndex, sleBridgePSControlPSStatus
				 }
			STATUS current
			DESCRIPTION 
				"Description."
			::= { sleBridgePSNotification 1 }

		
		-- 1.3.6.1.4.1.6296.101.3.22.3.2
		sleBridgePSMaxCountChanged NOTIFICATION-TYPE
			OBJECTS { sleBridgePSControlRequest, sleBridgePSControlTimeStamp, sleBridgePSControlReqResult, sleBridgePSControlIndex, sleBridgePSControlMaxCount
				 }
			STATUS current
			DESCRIPTION 
				"Description."
			::= { sleBridgePSNotification 2 }

		
		-- 1.3.6.1.4.1.6296.101.3.22.3.3
		sleBridgePSProfileChanged NOTIFICATION-TYPE
			OBJECTS { sleBridgePSControlRequest, sleBridgePSControlTimeStamp, sleBridgePSControlReqResult, sleBridgePSControlIndex, sleBridgePSControlAgingType, 
				sleBridgePSControlAgingTimer, sleBridgePSControlAgingStatic, sleBridgePScontrolViolation }
			STATUS current
			DESCRIPTION 
				"Description."
			::= { sleBridgePSNotification 3 }

		
		-- 1.3.6.1.4.1.6296.101.3.23
		sleBridgePortSecurityFdb OBJECT IDENTIFIER ::= { sleBridge 23 }

		
		-- 1.3.6.1.4.1.6296.101.3.23.1
		sleBridgePSFdbTable OBJECT-TYPE
			SYNTAX SEQUENCE OF SleBridgePSFdbEntry
			MAX-ACCESS not-accessible
			STATUS current
			DESCRIPTION
				"Description."
			::= { sleBridgePortSecurityFdb 1 }

		
		-- 1.3.6.1.4.1.6296.101.3.23.1.1
		sleBridgePSFdbEntry OBJECT-TYPE
			SYNTAX SleBridgePSFdbEntry
			MAX-ACCESS not-accessible
			STATUS current
			DESCRIPTION
				"Description."
			INDEX { sleBridgePSFdbPort, sleBridgePSFdbVid, sleBridgePSFdbMacAddress }
			::= { sleBridgePSFdbTable 1 }

		
		SleBridgePSFdbEntry ::=
			SEQUENCE { 
				sleBridgePSFdbPort
					INTEGER,
				sleBridgePSFdbVid
					INTEGER,
				sleBridgePSFdbMacAddress
					OCTET STRING,
				sleBridgePSFdbMode
					INTEGER,
				sleBridgePSFdbElapsedTime
					Unsigned32
			 }

		-- 1.3.6.1.4.1.6296.101.3.23.1.1.1
		sleBridgePSFdbPort OBJECT-TYPE
			SYNTAX INTEGER (1..512)
			MAX-ACCESS read-only
			STATUS current
			DESCRIPTION
				"Description."
			::= { sleBridgePSFdbEntry 1 }

		
		-- 1.3.6.1.4.1.6296.101.3.23.1.1.2
		sleBridgePSFdbVid OBJECT-TYPE
			SYNTAX INTEGER (1..4094)
			MAX-ACCESS read-only
			STATUS current
			DESCRIPTION
				"Description."
			::= { sleBridgePSFdbEntry 2 }

		
		-- 1.3.6.1.4.1.6296.101.3.23.1.1.3
		sleBridgePSFdbMacAddress OBJECT-TYPE
			SYNTAX OCTET STRING (SIZE (0..6))
			MAX-ACCESS read-only
			STATUS current
			DESCRIPTION
				"Description."
			::= { sleBridgePSFdbEntry 3 }

		
		-- 1.3.6.1.4.1.6296.101.3.23.1.1.4
		sleBridgePSFdbMode OBJECT-TYPE
			SYNTAX INTEGER
				{
				dynamic(1),
				static(2)
				}
			MAX-ACCESS read-only
			STATUS current
			DESCRIPTION
				"Description."
			::= { sleBridgePSFdbEntry 4 }

		
		-- 1.3.6.1.4.1.6296.101.3.23.1.1.5
		sleBridgePSFdbElapsedTime OBJECT-TYPE
			SYNTAX Unsigned32
			MAX-ACCESS read-only
			STATUS current
			DESCRIPTION
				"Description."
			::= { sleBridgePSFdbEntry 5 }

		
		-- 1.3.6.1.4.1.6296.101.3.23.2
		sleBridgePSFdbControl OBJECT IDENTIFIER ::= { sleBridgePortSecurityFdb 2 }

		
		-- 1.3.6.1.4.1.6296.101.3.23.2.1
		sleBridgePSFdbControlRequest OBJECT-TYPE
			SYNTAX INTEGER
				{
				createPSFedEntry(1),
				destroyPSFdbEntry(2),
				clearPSFdbEntry(3)
				}
			MAX-ACCESS read-write
			STATUS current
			DESCRIPTION
				"Description."
			::= { sleBridgePSFdbControl 1 }

		
		-- 1.3.6.1.4.1.6296.101.3.23.2.2
		sleBridgePSFdbControlStatus OBJECT-TYPE
			SYNTAX SleControlStatusType
			MAX-ACCESS read-only
			STATUS current
			DESCRIPTION
				"Description."
			::= { sleBridgePSFdbControl 2 }

		
		-- 1.3.6.1.4.1.6296.101.3.23.2.3
		sleBridgePSFdbControlTimer OBJECT-TYPE
			SYNTAX Gauge32
			MAX-ACCESS read-write
			STATUS current
			DESCRIPTION
				"Description."
			::= { sleBridgePSFdbControl 3 }

		
		-- 1.3.6.1.4.1.6296.101.3.23.2.4
		sleBridgePSFdbControlTimeStamp OBJECT-TYPE
			SYNTAX TimeTicks
			MAX-ACCESS read-only
			STATUS current
			DESCRIPTION
				"Description."
			::= { sleBridgePSFdbControl 4 }

		
		-- 1.3.6.1.4.1.6296.101.3.23.2.5
		sleBridgePSFdbControlReqResult OBJECT-TYPE
			SYNTAX SleControlRequestResultType
			MAX-ACCESS read-only
			STATUS current
			DESCRIPTION
				"Description."
			::= { sleBridgePSFdbControl 5 }

		
		-- 1.3.6.1.4.1.6296.101.3.23.2.6
		sleBridgePSFdbControlPort OBJECT-TYPE
			SYNTAX INTEGER (1..512)
			MAX-ACCESS read-write
			STATUS current
			DESCRIPTION
				"Description."
			::= { sleBridgePSFdbControl 6 }

		
		-- 1.3.6.1.4.1.6296.101.3.23.2.7
		sleBridgePSFdbControlVid OBJECT-TYPE
			SYNTAX INTEGER (1..4094)
			MAX-ACCESS read-write
			STATUS current
			DESCRIPTION
				"Description."
			::= { sleBridgePSFdbControl 7 }

		
		-- 1.3.6.1.4.1.6296.101.3.23.2.8
		sleBridgePSFdbControlMacAddress OBJECT-TYPE
			SYNTAX OCTET STRING (SIZE (0..6))
			MAX-ACCESS read-write
			STATUS current
			DESCRIPTION
				"Description."
			::= { sleBridgePSFdbControl 8 }

		
		-- 1.3.6.1.4.1.6296.101.3.23.3
		sleBridgePSFdbNotification OBJECT IDENTIFIER ::= { sleBridgePortSecurityFdb 3 }

		
		-- 1.3.6.1.4.1.6296.101.3.23.3.1
		sleBridgePSFdbEntryCreated NOTIFICATION-TYPE
			OBJECTS { sleBridgePSFdbControlRequest, sleBridgePSFdbControlTimeStamp, sleBridgePSFdbControlReqResult, sleBridgePSFdbControlPort, sleBridgePSFdbControlVid, 
				sleBridgePSFdbControlMacAddress }
			STATUS current
			DESCRIPTION 
				"Description."
			::= { sleBridgePSFdbNotification 1 }

		
		-- 1.3.6.1.4.1.6296.101.3.23.3.2
		sleBridgePSFdbEntryDestroyed NOTIFICATION-TYPE
			OBJECTS { sleBridgePSFdbControlRequest, sleBridgePSFdbControlTimeStamp, sleBridgePSFdbControlReqResult, sleBridgePSFdbControlPort, sleBridgePSFdbControlVid, 
				sleBridgePSFdbControlMacAddress }
			STATUS current
			DESCRIPTION 
				"Description."
			::= { sleBridgePSFdbNotification 2 }

		
		-- 1.3.6.1.4.1.6296.101.3.23.3.3
		sleBridgePSFdbEntryCleared NOTIFICATION-TYPE
			OBJECTS { sleBridgePSFdbControlRequest, sleBridgePSFdbControlTimeStamp, sleBridgePSFdbControlReqResult, sleBridgePSFdbControlPort }
			STATUS current
			DESCRIPTION 
				"Description."
			::= { sleBridgePSFdbNotification 3 }

		
		-- 1.3.6.1.4.1.6296.101.3.24
		sleBridgeFloodGuard OBJECT IDENTIFIER ::= { sleBridge 24 }

		
		-- 1.3.6.1.4.1.6296.101.3.24.1
		sleBridgeFGBase OBJECT IDENTIFIER ::= { sleBridgeFloodGuard 1 }

		
		-- 1.3.6.1.4.1.6296.101.3.24.1.1
		sleBridgeFGBaseInfo OBJECT IDENTIFIER ::= { sleBridgeFGBase 1 }

		
		-- 1.3.6.1.4.1.6296.101.3.24.1.1.1
		sleBridgeFGBaseCfgdEnabled OBJECT-TYPE
			SYNTAX INTEGER
				{
				enable(1),
				disable(2)
				}
			MAX-ACCESS read-only
			STATUS current
			DESCRIPTION
				"Description."
			::= { sleBridgeFGBaseInfo 1 }

		
		-- 1.3.6.1.4.1.6296.101.3.24.1.1.2
		sleBridgeFGBaseMfgdEnabled OBJECT-TYPE
			SYNTAX INTEGER
				{
				enable(1),
				disable(2)
				}
			MAX-ACCESS read-only
			STATUS current
			DESCRIPTION
				"Description."
			::= { sleBridgeFGBaseInfo 2 }

		
		-- 1.3.6.1.4.1.6296.101.3.24.1.1.3
		sleBridgeFGBaseSfgdEnabled OBJECT-TYPE
			SYNTAX INTEGER
				{
				enable(1),
				disable(2)
				}
			MAX-ACCESS read-only
			STATUS current
			DESCRIPTION
				"Description."
			::= { sleBridgeFGBaseInfo 3 }

		
		-- 1.3.6.1.4.1.6296.101.3.24.1.2
		sleBridgeFGBaseControl OBJECT IDENTIFIER ::= { sleBridgeFGBase 2 }

		
		-- 1.3.6.1.4.1.6296.101.3.24.1.2.1
		sleBridgeFGBaseControlRequest OBJECT-TYPE
			SYNTAX INTEGER
				{
				setCfgdEnable(1),
				setSfgdEnable(2)
				}
			MAX-ACCESS read-write
			STATUS current
			DESCRIPTION
				"Description."
			::= { sleBridgeFGBaseControl 1 }

		
		-- 1.3.6.1.4.1.6296.101.3.24.1.2.2
		sleBridgeFGBaseControlStatus OBJECT-TYPE
			SYNTAX SleControlStatusType
			MAX-ACCESS read-only
			STATUS current
			DESCRIPTION
				"Description."
			::= { sleBridgeFGBaseControl 2 }

		
		-- 1.3.6.1.4.1.6296.101.3.24.1.2.3
		sleBridgeFGBaseControlTimer OBJECT-TYPE
			SYNTAX Gauge32
			MAX-ACCESS read-write
			STATUS current
			DESCRIPTION
				"Description."
			::= { sleBridgeFGBaseControl 3 }

		
		-- 1.3.6.1.4.1.6296.101.3.24.1.2.4
		sleBridgeFGBaseControlTimeStamp OBJECT-TYPE
			SYNTAX TimeTicks
			MAX-ACCESS read-only
			STATUS current
			DESCRIPTION
				"Description."
			::= { sleBridgeFGBaseControl 4 }

		
		-- 1.3.6.1.4.1.6296.101.3.24.1.2.5
		sleBridgeFGBaseControlReqResult OBJECT-TYPE
			SYNTAX SleControlRequestResultType
			MAX-ACCESS read-only
			STATUS current
			DESCRIPTION
				"Description."
			::= { sleBridgeFGBaseControl 5 }

		
		-- 1.3.6.1.4.1.6296.101.3.24.1.2.6
		sleBridgeFGBaseControlCfgdEnable OBJECT-TYPE
			SYNTAX INTEGER
				{
				enable(1),
				disable(2)
				}
			MAX-ACCESS read-write
			STATUS current
			DESCRIPTION
				"Description."
			::= { sleBridgeFGBaseControl 6 }

		
		-- 1.3.6.1.4.1.6296.101.3.24.1.2.7
		sleBridgeFGBaseControlSfgdEnable OBJECT-TYPE
			SYNTAX INTEGER
				{
				enable(1),
				disable(2)
				}
			MAX-ACCESS read-write
			STATUS current
			DESCRIPTION
				"Description."
			::= { sleBridgeFGBaseControl 7 }

		
		-- 1.3.6.1.4.1.6296.101.3.24.1.3
		sleBridgeFGBaseNotification OBJECT IDENTIFIER ::= { sleBridgeFGBase 3 }

		
		-- 1.3.6.1.4.1.6296.101.3.24.1.3.1
		sleBridgeFGBaseCfgdStatusChanged NOTIFICATION-TYPE
			OBJECTS { sleBridgeFGBaseControlRequest, sleBridgeFGBaseControlTimeStamp, sleBridgeFGBaseControlReqResult, sleBridgeFGBaseControlCfgdEnable }
			STATUS current
			DESCRIPTION 
				"Description."
			::= { sleBridgeFGBaseNotification 1 }

		
		-- 1.3.6.1.4.1.6296.101.3.24.1.3.2
		sleBridgeFGBaseSfgdStatusChanged NOTIFICATION-TYPE
			OBJECTS { sleBridgeFGBaseControlRequest, sleBridgeFGBaseControlTimeStamp, sleBridgeFGBaseControlReqResult, sleBridgeFGBaseControlSfgdEnable }
			STATUS current
			DESCRIPTION 
				"Description."
			::= { sleBridgeFGBaseNotification 2 }

		
		-- 1.3.6.1.4.1.6296.101.3.24.2
		sleBridgeFGPort OBJECT IDENTIFIER ::= { sleBridgeFloodGuard 2 }

		
		-- 1.3.6.1.4.1.6296.101.3.24.2.1
		sleBridgeFGPortTable OBJECT-TYPE
			SYNTAX SEQUENCE OF SleBridgeFGPortEntry
			MAX-ACCESS not-accessible
			STATUS current
			DESCRIPTION
				"Description."
			::= { sleBridgeFGPort 1 }

		
		-- 1.3.6.1.4.1.6296.101.3.24.2.1.1
		sleBridgeFGPortEntry OBJECT-TYPE
			SYNTAX SleBridgeFGPortEntry
			MAX-ACCESS not-accessible
			STATUS current
			DESCRIPTION
				"Description."
			INDEX { sleBridgePortIndex, sleBridgeFGPortType }
			::= { sleBridgeFGPortTable 1 }

		
		SleBridgeFGPortEntry ::=
			SEQUENCE { 
				sleBridgeFGPortType
					INTEGER,
				sleBridgeFGPortFrameType
					INTEGER,
				sleBridgeFGPortFrame
					INTEGER,
				sleBridgeFGPortBlocked
					INTEGER,
				sleBridgeFGPortTimer
					INTEGER
			 }

		-- 1.3.6.1.4.1.6296.101.3.24.2.1.1.1
		sleBridgeFGPortType OBJECT-TYPE
			SYNTAX INTEGER
				{
				systemFloodGuard(1),
				cpuFloodGuard(2),
				macFloodGuard(3)
				}
			MAX-ACCESS read-only
			STATUS current
			DESCRIPTION
				"Description."
			::= { sleBridgeFGPortEntry 1 }

		
		-- 1.3.6.1.4.1.6296.101.3.24.2.1.1.2
		sleBridgeFGPortFrameType OBJECT-TYPE
			SYNTAX INTEGER
				{
				none(0),
				multicast(1),
				broadcast(2),
				both(3)
				}
			MAX-ACCESS read-only
			STATUS current
			DESCRIPTION
				"Description."
			::= { sleBridgeFGPortEntry 2 }

		
		-- 1.3.6.1.4.1.6296.101.3.24.2.1.1.3
		sleBridgeFGPortFrame OBJECT-TYPE
			SYNTAX INTEGER (-1 | 1..2147483647)
			MAX-ACCESS read-only
			STATUS current
			DESCRIPTION
				"Description."
			::= { sleBridgeFGPortEntry 3 }

		
		-- 1.3.6.1.4.1.6296.101.3.24.2.1.1.4
		sleBridgeFGPortBlocked OBJECT-TYPE
			SYNTAX INTEGER
				{
				block(1),
				unblock(2)
				}
			MAX-ACCESS read-only
			STATUS current
			DESCRIPTION
				"Description."
			::= { sleBridgeFGPortEntry 4 }

		
		-- 1.3.6.1.4.1.6296.101.3.24.2.1.1.5
		sleBridgeFGPortTimer OBJECT-TYPE
			SYNTAX INTEGER (-1 | 10..3600)
			MAX-ACCESS read-only
			STATUS current
			DESCRIPTION
				"Description."
			::= { sleBridgeFGPortEntry 5 }

		
		-- 1.3.6.1.4.1.6296.101.3.24.2.2
		sleBridgeFGPortControl OBJECT IDENTIFIER ::= { sleBridgeFGPort 2 }

		
		-- 1.3.6.1.4.1.6296.101.3.24.2.2.1
		sleBridgeFGPortControlRequest OBJECT-TYPE
			SYNTAX INTEGER
				{
				setFgPortProfile(1),
				setFgPortUnblock(2)
				}
			MAX-ACCESS read-write
			STATUS current
			DESCRIPTION
				"Description."
			::= { sleBridgeFGPortControl 1 }

		
		-- 1.3.6.1.4.1.6296.101.3.24.2.2.2
		sleBridgeFGPortControlStatus OBJECT-TYPE
			SYNTAX SleControlStatusType
			MAX-ACCESS read-only
			STATUS current
			DESCRIPTION
				"Description."
			::= { sleBridgeFGPortControl 2 }

		
		-- 1.3.6.1.4.1.6296.101.3.24.2.2.3
		sleBridgeFGPortControlTimer OBJECT-TYPE
			SYNTAX Gauge32
			MAX-ACCESS read-only
			STATUS current
			DESCRIPTION
				"Description."
			::= { sleBridgeFGPortControl 3 }

		
		-- 1.3.6.1.4.1.6296.101.3.24.2.2.4
		sleBridgeFGPortControlTimeStamp OBJECT-TYPE
			SYNTAX TimeTicks
			MAX-ACCESS read-only
			STATUS current
			DESCRIPTION
				"Description."
			::= { sleBridgeFGPortControl 4 }

		
		-- 1.3.6.1.4.1.6296.101.3.24.2.2.5
		sleBridgeFGPortControlReqResult OBJECT-TYPE
			SYNTAX SleControlRequestResultType
			MAX-ACCESS read-only
			STATUS current
			DESCRIPTION
				"Description."
			::= { sleBridgeFGPortControl 5 }

		
		-- 1.3.6.1.4.1.6296.101.3.24.2.2.6
		sleBridgeFGPortControlIndex OBJECT-TYPE
			SYNTAX Integer32
			MAX-ACCESS read-write
			STATUS current
			DESCRIPTION
				"Description."
			::= { sleBridgeFGPortControl 6 }

		
		-- 1.3.6.1.4.1.6296.101.3.24.2.2.7
		sleBridgeFGPortControlType OBJECT-TYPE
			SYNTAX INTEGER
				{
				systemfloodguard(1),
				cpufloodguard(2),
				macfloodguard(3)
				}
			MAX-ACCESS read-write
			STATUS current
			DESCRIPTION
				"Description."
			::= { sleBridgeFGPortControl 7 }

		
		-- 1.3.6.1.4.1.6296.101.3.24.2.2.8
		sleBridgeFGPortControlFrameType OBJECT-TYPE
			SYNTAX INTEGER
				{
				none(0),
				multicast(1),
				broadcast(2),
				both(3)
				}
			MAX-ACCESS read-write
			STATUS current
			DESCRIPTION
				"Description."
			::= { sleBridgeFGPortControl 8 }

		
		-- 1.3.6.1.4.1.6296.101.3.24.2.2.9
		sleBridgeFGPortControlFrame OBJECT-TYPE
			SYNTAX INTEGER (-1 | 1..2147483647)
			MAX-ACCESS read-write
			STATUS current
			DESCRIPTION
				"Description."
			::= { sleBridgeFGPortControl 9 }

		
		-- 1.3.6.1.4.1.6296.101.3.24.2.2.10
		sleBridgeFGPortControlSetTimer OBJECT-TYPE
			SYNTAX INTEGER (-1 | 10..3600)
			MAX-ACCESS read-write
			STATUS current
			DESCRIPTION
				"Description."
			::= { sleBridgeFGPortControl 10 }

		
		-- 1.3.6.1.4.1.6296.101.3.24.2.2.11
		sleBridgeFGPortControlBlock OBJECT-TYPE
			SYNTAX INTEGER
				{
				block(1),
				unblock(2)
				}
			MAX-ACCESS read-write
			STATUS current
			DESCRIPTION
				"Description."
			::= { sleBridgeFGPortControl 11 }

		
		-- 1.3.6.1.4.1.6296.101.3.24.2.3
		sleBridgeFGPortNotification OBJECT IDENTIFIER ::= { sleBridgeFGPort 3 }

		
		-- 1.3.6.1.4.1.6296.101.3.24.2.3.1
		sleBridgeFGPortProfileChanged NOTIFICATION-TYPE
			OBJECTS { sleBridgeFGPortControlReqResult, sleBridgeFGPortControlTimeStamp, sleBridgeFGPortControlRequest, sleBridgeFGPortControlIndex, sleBridgeFGPortControlType, 
				sleBridgeFGPortControlFrameType, sleBridgeFGPortControlFrame, sleBridgeFGPortControlSetTimer, sleBridgeFGPortControlBlock }
			STATUS current
			DESCRIPTION 
				"Description."
			::= { sleBridgeFGPortNotification 1 }

		
		-- 1.3.6.1.4.1.6296.101.3.24.2.3.2
		sleBridgeFGPortUnblockChanged NOTIFICATION-TYPE
			OBJECTS { sleBridgeFGPortControlRequest, sleBridgeFGPortControlTimeStamp, sleBridgeFGPortControlReqResult, sleBridgeFGPortControlIndex, sleBridgeFGPortControlType
				 }
			STATUS current
			DESCRIPTION 
				"Description."
			::= { sleBridgeFGPortNotification 2 }

		
		-- 1.3.6.1.4.1.6296.101.3.25
		sleBridgeVlanTranslation OBJECT IDENTIFIER ::= { sleBridge 25 }

		
		-- 1.3.6.1.4.1.6296.101.3.25.1
		sleBridgeVTTable OBJECT-TYPE
			SYNTAX SEQUENCE OF SleBridgeVTEntry
			MAX-ACCESS not-accessible
			STATUS current
			DESCRIPTION
				"Description."
			::= { sleBridgeVlanTranslation 1 }

		
		-- 1.3.6.1.4.1.6296.101.3.25.1.1
		sleBridgeVTEntry OBJECT-TYPE
			SYNTAX SleBridgeVTEntry
			MAX-ACCESS not-accessible
			STATUS current
			DESCRIPTION
				"Description."
			INDEX { sleBridgeVTServiceId, sleBridgeVTSubscriberId }
			::= { sleBridgeVTTable 1 }

		
		SleBridgeVTEntry ::=
			SEQUENCE { 
				sleBridgeVTServiceId
					INTEGER,
				sleBridgeVTSubscriberId
					INTEGER
			 }

		-- 1.3.6.1.4.1.6296.101.3.25.1.1.1
		sleBridgeVTServiceId OBJECT-TYPE
			SYNTAX INTEGER (1..4094)
			MAX-ACCESS read-only
			STATUS current
			DESCRIPTION
				"Description."
			::= { sleBridgeVTEntry 1 }

		
		-- 1.3.6.1.4.1.6296.101.3.25.1.1.2
		sleBridgeVTSubscriberId OBJECT-TYPE
			SYNTAX INTEGER (1..4094)
			MAX-ACCESS read-only
			STATUS current
			DESCRIPTION
				"Description."
			::= { sleBridgeVTEntry 2 }

		
		-- 1.3.6.1.4.1.6296.101.3.25.2
		sleBridgeVTRuleTable OBJECT-TYPE
			SYNTAX SEQUENCE OF SleBridgeVTRuleEntry
			MAX-ACCESS not-accessible
			STATUS current
			DESCRIPTION
				"Description."
			::= { sleBridgeVlanTranslation 2 }

		
		-- 1.3.6.1.4.1.6296.101.3.25.2.1
		sleBridgeVTRuleEntry OBJECT-TYPE
			SYNTAX SleBridgeVTRuleEntry
			MAX-ACCESS not-accessible
			STATUS current
			DESCRIPTION
				"Description."
			INDEX { sleBridgeVTRuleMac, sleBridgeVTRuleVid }
			::= { sleBridgeVTRuleTable 1 }

		
		SleBridgeVTRuleEntry ::=
			SEQUENCE { 
				sleBridgeVTRuleMac
					MacAddress,
				sleBridgeVTRuleVid
					INTEGER,
				sleBridgeVTRuleRDirVid
					INTEGER,
				sleBridgeVTRuleRDirPort
					Integer32,
				sleBridgeVTRuleStatus
					INTEGER
			 }

		-- 1.3.6.1.4.1.6296.101.3.25.2.1.1
		sleBridgeVTRuleMac OBJECT-TYPE
			SYNTAX MacAddress
			MAX-ACCESS read-only
			STATUS current
			DESCRIPTION
				"Description."
			::= { sleBridgeVTRuleEntry 1 }

		
		-- 1.3.6.1.4.1.6296.101.3.25.2.1.2
		sleBridgeVTRuleVid OBJECT-TYPE
			SYNTAX INTEGER (1..4094)
			MAX-ACCESS read-only
			STATUS current
			DESCRIPTION
				"Description."
			::= { sleBridgeVTRuleEntry 2 }

		
		-- 1.3.6.1.4.1.6296.101.3.25.2.1.3
		sleBridgeVTRuleRDirVid OBJECT-TYPE
			SYNTAX INTEGER (1..4094)
			MAX-ACCESS read-only
			STATUS current
			DESCRIPTION
				"Description."
			::= { sleBridgeVTRuleEntry 3 }

		
		-- 1.3.6.1.4.1.6296.101.3.25.2.1.4
		sleBridgeVTRuleRDirPort OBJECT-TYPE
			SYNTAX Integer32
			MAX-ACCESS read-only
			STATUS current
			DESCRIPTION
				"Description."
			::= { sleBridgeVTRuleEntry 4 }

		
		-- 1.3.6.1.4.1.6296.101.3.25.2.1.5
		sleBridgeVTRuleStatus OBJECT-TYPE
			SYNTAX INTEGER
				{
				static(1),
				dynamic(2)
				}
			MAX-ACCESS read-only
			STATUS current
			DESCRIPTION
				"Description."
			::= { sleBridgeVTRuleEntry 5 }

		
		-- 1.3.6.1.4.1.6296.101.3.25.3
		sleBridgeVTControl OBJECT IDENTIFIER ::= { sleBridgeVlanTranslation 3 }

		
		-- 1.3.6.1.4.1.6296.101.3.25.3.1
		sleBridgeVTControlRequest OBJECT-TYPE
			SYNTAX INTEGER
				{
				setVT(1),
				clearVT(2)
				}
			MAX-ACCESS read-write
			STATUS current
			DESCRIPTION
				"The request of a user command."
			::= { sleBridgeVTControl 1 }

		
		-- 1.3.6.1.4.1.6296.101.3.25.3.2
		sleBridgeVTControlStatus OBJECT-TYPE
			SYNTAX SleControlStatusType
			MAX-ACCESS read-only
			STATUS current
			DESCRIPTION
				"The status of a user command."
			::= { sleBridgeVTControl 2 }

		
		-- 1.3.6.1.4.1.6296.101.3.25.3.3
		sleBridgeVTControlTimer OBJECT-TYPE
			SYNTAX Gauge32
			MAX-ACCESS read-write
			STATUS current
			DESCRIPTION
				"The maximum wait time for the manager for a long running user command."
			::= { sleBridgeVTControl 3 }

		
		-- 1.3.6.1.4.1.6296.101.3.25.3.4
		sleBridgeVTControlTimeStamp OBJECT-TYPE
			SYNTAX TimeTicks
			MAX-ACCESS read-only
			STATUS current
			DESCRIPTION
				"The time stamp of the last command (end of command)."
			::= { sleBridgeVTControl 4 }

		
		-- 1.3.6.1.4.1.6296.101.3.25.3.5
		sleBridgeVTControllReqResult OBJECT-TYPE
			SYNTAX SleControlRequestResultType
			MAX-ACCESS read-only
			STATUS current
			DESCRIPTION
				"The result of the last user command."
			::= { sleBridgeVTControl 5 }

		
		-- 1.3.6.1.4.1.6296.101.3.25.3.6
		sleBridgeVTControlServerId OBJECT-TYPE
			SYNTAX INTEGER (1..4094)
			MAX-ACCESS read-write
			STATUS current
			DESCRIPTION
				"Network Interface Index."
			::= { sleBridgeVTControl 6 }

		
		-- 1.3.6.1.4.1.6296.101.3.25.3.7
		sleBridgeVTControlClientId OBJECT-TYPE
			SYNTAX INTEGER (1..4094)
			MAX-ACCESS read-write
			STATUS current
			DESCRIPTION
				"Network Interface Index."
			::= { sleBridgeVTControl 7 }

		
		-- 1.3.6.1.4.1.6296.101.3.25.4
		sleBridgeVTNotification OBJECT IDENTIFIER ::= { sleBridgeVlanTranslation 4 }

		
		-- 1.3.6.1.4.1.6296.101.3.25.4.1
		sleBridgeVTSet NOTIFICATION-TYPE
			OBJECTS { sleBridgeVTControlRequest, sleBridgeVTControlTimeStamp, sleBridgeVTControllReqResult, sleBridgeVTControlServerId, sleBridgeVTControlClientId
				 }
			STATUS current
			DESCRIPTION 
				"Description."
			::= { sleBridgeVTNotification 1 }

		
		-- 1.3.6.1.4.1.6296.101.3.25.4.2
		sleBridgeVTClear NOTIFICATION-TYPE
			OBJECTS { sleBridgeVTControlRequest, sleBridgeVTControlTimeStamp, sleBridgeVTControllReqResult, sleBridgeVTControlServerId, sleBridgeVTControlClientId
				 }
			STATUS current
			DESCRIPTION 
				"Description."
			::= { sleBridgeVTNotification 2 }

		
		-- 1.3.6.1.4.1.6296.101.3.26
		sleBridgeGarp OBJECT IDENTIFIER ::= { sleBridge 26 }

		
		-- 1.3.6.1.4.1.6296.101.3.26.1
		sleBridgeGarpBase OBJECT IDENTIFIER ::= { sleBridgeGarp 1 }

		
		-- 1.3.6.1.4.1.6296.101.3.26.1.1
		sleBridgeGarpBaseInfo OBJECT IDENTIFIER ::= { sleBridgeGarpBase 1 }

		
		-- 1.3.6.1.4.1.6296.101.3.26.1.1.1
		sleBridgeGvrpStatus OBJECT-TYPE
			SYNTAX INTEGER
				{
				enable(1),
				disable(2)
				}
			MAX-ACCESS read-only
			STATUS current
			DESCRIPTION
				"Global GVRP status"
			::= { sleBridgeGarpBaseInfo 1 }

		
		-- 1.3.6.1.4.1.6296.101.3.26.1.1.2
		sleBridgeGmrpStatus OBJECT-TYPE
			SYNTAX INTEGER
				{
				enable(1),
				disable(2)
				}
			MAX-ACCESS read-only
			STATUS current
			DESCRIPTION
				"Global GMRP status"
			::= { sleBridgeGarpBaseInfo 2 }

		
		-- 1.3.6.1.4.1.6296.101.3.26.1.1.3
		sleBridgeGarpTimerJoin OBJECT-TYPE
			SYNTAX Integer32
			MAX-ACCESS read-only
			STATUS current
			DESCRIPTION
				"Global Join Timer"
			::= { sleBridgeGarpBaseInfo 3 }

		
		-- 1.3.6.1.4.1.6296.101.3.26.1.1.4
		sleBridgeGarpTimerLeave OBJECT-TYPE
			SYNTAX Integer32
			MAX-ACCESS read-only
			STATUS current
			DESCRIPTION
				"Global Leave Timer"
			::= { sleBridgeGarpBaseInfo 4 }

		
		-- 1.3.6.1.4.1.6296.101.3.26.1.1.5
		sleBridgeGarpTimerLeaveAll OBJECT-TYPE
			SYNTAX Integer32
			MAX-ACCESS read-only
			STATUS current
			DESCRIPTION
				"Global LeaveAll Timer"
			::= { sleBridgeGarpBaseInfo 5 }

		
		-- 1.3.6.1.4.1.6296.101.3.26.1.2
		sleBridgeGarpBaseControl OBJECT IDENTIFIER ::= { sleBridgeGarpBase 2 }

		
		-- 1.3.6.1.4.1.6296.101.3.26.1.2.1
		sleBridgeGarpBaseControlRequest OBJECT-TYPE
			SYNTAX INTEGER
				{
				setGarpStatus(1),
				setGarpTimer(2)
				}
			MAX-ACCESS read-write
			STATUS current
			DESCRIPTION
				"Description."
			::= { sleBridgeGarpBaseControl 1 }

		
		-- 1.3.6.1.4.1.6296.101.3.26.1.2.2
		sleBridgeGarpBaseControlStatus OBJECT-TYPE
			SYNTAX SleControlStatusType
			MAX-ACCESS read-only
			STATUS current
			DESCRIPTION
				"Description."
			::= { sleBridgeGarpBaseControl 2 }

		
		-- 1.3.6.1.4.1.6296.101.3.26.1.2.3
		sleBridgeGarpBaseControlTimer OBJECT-TYPE
			SYNTAX Gauge32
			MAX-ACCESS read-write
			STATUS current
			DESCRIPTION
				"Description."
			::= { sleBridgeGarpBaseControl 3 }

		
		-- 1.3.6.1.4.1.6296.101.3.26.1.2.4
		sleBridgeGarpBaseControlTimeStamp OBJECT-TYPE
			SYNTAX TimeTicks
			MAX-ACCESS read-only
			STATUS current
			DESCRIPTION
				"Description."
			::= { sleBridgeGarpBaseControl 4 }

		
		-- 1.3.6.1.4.1.6296.101.3.26.1.2.5
		sleBridgeGarpBaseControlReqResult OBJECT-TYPE
			SYNTAX SleControlRequestResultType
			MAX-ACCESS read-only
			STATUS current
			DESCRIPTION
				"Description."
			::= { sleBridgeGarpBaseControl 5 }

		
		-- 1.3.6.1.4.1.6296.101.3.26.1.2.6
		sleBridgeGarpBaseControlGvrpStatus OBJECT-TYPE
			SYNTAX INTEGER
				{
				enable(1),
				disable(2)
				}
			MAX-ACCESS read-write
			STATUS current
			DESCRIPTION
				"Description."
			::= { sleBridgeGarpBaseControl 6 }

		
		-- 1.3.6.1.4.1.6296.101.3.26.1.2.7
		sleBridgeGarpBaseControlGmrpStatus OBJECT-TYPE
			SYNTAX INTEGER
				{
				enable(1),
				disable(2)
				}
			MAX-ACCESS read-write
			STATUS current
			DESCRIPTION
				"Description."
			::= { sleBridgeGarpBaseControl 7 }

		
		-- 1.3.6.1.4.1.6296.101.3.26.1.2.8
		sleBridgeGarpBaseControlTimerJoin OBJECT-TYPE
			SYNTAX Integer32
			MAX-ACCESS read-write
			STATUS current
			DESCRIPTION
				"Description."
			::= { sleBridgeGarpBaseControl 8 }

		
		-- 1.3.6.1.4.1.6296.101.3.26.1.2.9
		sleBridgeGarpBaseControlTimerLeave OBJECT-TYPE
			SYNTAX Integer32
			MAX-ACCESS read-write
			STATUS current
			DESCRIPTION
				"Description."
			::= { sleBridgeGarpBaseControl 9 }

		
		-- 1.3.6.1.4.1.6296.101.3.26.1.2.10
		sleBridgeGarpBaseControlTimerLeaveAll OBJECT-TYPE
			SYNTAX Integer32
			MAX-ACCESS read-write
			STATUS current
			DESCRIPTION
				"Description."
			::= { sleBridgeGarpBaseControl 10 }

		
		-- 1.3.6.1.4.1.6296.101.3.26.1.3
		sleBridgeGarpBaseNotification OBJECT IDENTIFIER ::= { sleBridgeGarpBase 3 }

		
		-- 1.3.6.1.4.1.6296.101.3.26.1.3.1
		sleBridgeGarpStatusChanged NOTIFICATION-TYPE
			OBJECTS { sleBridgeGarpBaseControlRequest, sleBridgeGarpBaseControlTimeStamp, sleBridgeGarpBaseControlReqResult, sleBridgeGarpBaseControlGvrpStatus, sleBridgeGarpBaseControlGmrpStatus
				 }
			STATUS current
			DESCRIPTION 
				"Description."
			::= { sleBridgeGarpBaseNotification 1 }

		
		-- 1.3.6.1.4.1.6296.101.3.26.1.3.2
		sleBridgeGarpTimerChanged NOTIFICATION-TYPE
			OBJECTS { sleBridgeGarpBaseControlRequest, sleBridgeGarpBaseControlTimeStamp, sleBridgeGarpBaseControlReqResult, sleBridgeGarpBaseControlTimerJoin, sleBridgeGarpBaseControlTimerLeave, 
				sleBridgeGarpBaseControlTimerLeaveAll }
			STATUS current
			DESCRIPTION 
				"Description."
			::= { sleBridgeGarpBaseNotification 2 }

		
		-- 1.3.6.1.4.1.6296.101.3.26.2
		sleBridgeGarpApplication OBJECT IDENTIFIER ::= { sleBridgeGarp 2 }

		
		-- 1.3.6.1.4.1.6296.101.3.26.2.1
		sleBridgeGarpAppPortTable OBJECT-TYPE
			SYNTAX SEQUENCE OF SleBridgeGarpAppPortEntry
			MAX-ACCESS not-accessible
			STATUS current
			DESCRIPTION
				"Description."
			::= { sleBridgeGarpApplication 1 }

		
		-- 1.3.6.1.4.1.6296.101.3.26.2.1.1
		sleBridgeGarpAppPortEntry OBJECT-TYPE
			SYNTAX SleBridgeGarpAppPortEntry
			MAX-ACCESS not-accessible
			STATUS current
			DESCRIPTION
				"Description."
			INDEX { sleBridgeGarpAppPortIndex, sleBridgeGarpAppPortType }
			::= { sleBridgeGarpAppPortTable 1 }

		
		SleBridgeGarpAppPortEntry ::=
			SEQUENCE { 
				sleBridgeGarpAppPortIndex
					INTEGER,
				sleBridgeGarpAppPortType
					INTEGER,
				sleBridgeGarpAppPortStatus
					INTEGER,
				sleBridgeGarpAppPortFailedRegistrations
					Integer32,
				sleBridgeGarpAppPortLastPduOrigin
					OCTET STRING,
				sleBridgeGarpAppPortRegistration
					INTEGER,
				sleBridgeGarpAppPortApplicant
					INTEGER,
				sleBridgeGarpAppPortFwdAll
					INTEGER,
				sleBridgeGarpAppPortTimerJoin
					Integer32,
				sleBridgeGarpAppPortTimerLeave
					Integer32,
				sleBridgeGarpAppPortTimerLeaveAll
					Integer32
			 }

		-- 1.3.6.1.4.1.6296.101.3.26.2.1.1.1
		sleBridgeGarpAppPortIndex OBJECT-TYPE
			SYNTAX INTEGER (1..65535)
			MAX-ACCESS read-only
			STATUS current
			DESCRIPTION
				"Port index.  Same as ifindex."
			::= { sleBridgeGarpAppPortEntry 1 }

		
		-- 1.3.6.1.4.1.6296.101.3.26.2.1.1.2
		sleBridgeGarpAppPortType OBJECT-TYPE
			SYNTAX INTEGER
				{
				gvrp(1),
				gmrp(2)
				}
			MAX-ACCESS read-only
			STATUS current
			DESCRIPTION
				"GARP Application Type.
				Supports GVRP, GMRP 
				"
			::= { sleBridgeGarpAppPortEntry 2 }

		
		-- 1.3.6.1.4.1.6296.101.3.26.2.1.1.3
		sleBridgeGarpAppPortStatus OBJECT-TYPE
			SYNTAX INTEGER
				{
				enable(1),
				disable(2)
				}
			MAX-ACCESS read-only
			STATUS current
			DESCRIPTION
				"Description."
			::= { sleBridgeGarpAppPortEntry 3 }

		
		-- 1.3.6.1.4.1.6296.101.3.26.2.1.1.4
		sleBridgeGarpAppPortFailedRegistrations OBJECT-TYPE
			SYNTAX Integer32
			MAX-ACCESS read-only
			STATUS current
			DESCRIPTION
				"The current value of the Failed Registrations counter maintained for a GARP Attribute type."
			::= { sleBridgeGarpAppPortEntry 4 }

		
		-- 1.3.6.1.4.1.6296.101.3.26.2.1.1.5
		sleBridgeGarpAppPortLastPduOrigin OBJECT-TYPE
			SYNTAX OCTET STRING (SIZE (1..6))
			MAX-ACCESS read-only
			STATUS current
			DESCRIPTION
				"MAC Address of the last pdu that caused a state change for a given GARP Attribute."
			::= { sleBridgeGarpAppPortEntry 5 }

		
		-- 1.3.6.1.4.1.6296.101.3.26.2.1.1.6
		sleBridgeGarpAppPortRegistration OBJECT-TYPE
			SYNTAX INTEGER
				{
				nomal(1),
				fixed(2),
				forbidden(3)
				}
			MAX-ACCESS read-only
			STATUS current
			DESCRIPTION
				"GARP registration mode."
			::= { sleBridgeGarpAppPortEntry 6 }

		
		-- 1.3.6.1.4.1.6296.101.3.26.2.1.1.7
		sleBridgeGarpAppPortApplicant OBJECT-TYPE
			SYNTAX INTEGER
				{
				participant(1),
				nonParticipant(2)
				}
			MAX-ACCESS read-only
			STATUS current
			DESCRIPTION
				"Applicant type
				1: Transmissible PDU
				2: Untransmissible PDU
				"
			::= { sleBridgeGarpAppPortEntry 7 }

		
		-- 1.3.6.1.4.1.6296.101.3.26.2.1.1.8
		sleBridgeGarpAppPortFwdAll OBJECT-TYPE
			SYNTAX INTEGER
				{
				enable(1),
				disable(2)
				}
			MAX-ACCESS read-only
			STATUS current
			DESCRIPTION
				"GMRP forward all registered-groups."
			::= { sleBridgeGarpAppPortEntry 8 }

		
		-- 1.3.6.1.4.1.6296.101.3.26.2.1.1.9
		sleBridgeGarpAppPortTimerJoin OBJECT-TYPE
			SYNTAX Integer32
			MAX-ACCESS read-only
			STATUS current
			DESCRIPTION
				"Description."
			::= { sleBridgeGarpAppPortEntry 9 }

		
		-- 1.3.6.1.4.1.6296.101.3.26.2.1.1.10
		sleBridgeGarpAppPortTimerLeave OBJECT-TYPE
			SYNTAX Integer32
			MAX-ACCESS read-only
			STATUS current
			DESCRIPTION
				"Description."
			::= { sleBridgeGarpAppPortEntry 10 }

		
		-- 1.3.6.1.4.1.6296.101.3.26.2.1.1.11
		sleBridgeGarpAppPortTimerLeaveAll OBJECT-TYPE
			SYNTAX Integer32
			MAX-ACCESS read-only
			STATUS current
			DESCRIPTION
				"Description."
			::= { sleBridgeGarpAppPortEntry 11 }

		
		-- 1.3.6.1.4.1.6296.101.3.26.2.2
		sleBridgeGarpAppPortControl OBJECT IDENTIFIER ::= { sleBridgeGarpApplication 2 }

		
		-- 1.3.6.1.4.1.6296.101.3.26.2.2.1
		sleBridgeGarpAppPortControlRequest OBJECT-TYPE
			SYNTAX INTEGER
				{
				setGarpAppStatus(1),
				setGarpAppProfile(2)
				}
			MAX-ACCESS read-write
			STATUS current
			DESCRIPTION
				"Description."
			::= { sleBridgeGarpAppPortControl 1 }

		
		-- 1.3.6.1.4.1.6296.101.3.26.2.2.2
		sleBridgeGarpAppPortControlStatus OBJECT-TYPE
			SYNTAX SleControlStatusType
			MAX-ACCESS read-only
			STATUS current
			DESCRIPTION
				"Description."
			::= { sleBridgeGarpAppPortControl 2 }

		
		-- 1.3.6.1.4.1.6296.101.3.26.2.2.3
		sleBridgeGarpAppPortControlTimer OBJECT-TYPE
			SYNTAX Gauge32
			MAX-ACCESS read-write
			STATUS current
			DESCRIPTION
				"Description."
			::= { sleBridgeGarpAppPortControl 3 }

		
		-- 1.3.6.1.4.1.6296.101.3.26.2.2.4
		sleBridgeGarpAppPortControlTimeStamp OBJECT-TYPE
			SYNTAX TimeTicks
			MAX-ACCESS read-only
			STATUS current
			DESCRIPTION
				"Description."
			::= { sleBridgeGarpAppPortControl 4 }

		
		-- 1.3.6.1.4.1.6296.101.3.26.2.2.5
		sleBridgeGarpAppPortControlReqResult OBJECT-TYPE
			SYNTAX SleControlRequestResultType
			MAX-ACCESS read-only
			STATUS current
			DESCRIPTION
				"Description."
			::= { sleBridgeGarpAppPortControl 5 }

		
		-- 1.3.6.1.4.1.6296.101.3.26.2.2.6
		sleBridgeGarpAppPortControlIndex OBJECT-TYPE
			SYNTAX INTEGER (1..65535)
			MAX-ACCESS read-write
			STATUS current
			DESCRIPTION
				"Description."
			::= { sleBridgeGarpAppPortControl 6 }

		
		-- 1.3.6.1.4.1.6296.101.3.26.2.2.7
		sleBridgeGarpAppPortControlType OBJECT-TYPE
			SYNTAX INTEGER
				{
				gvrp(1),
				gmrp(2)
				}
			MAX-ACCESS read-write
			STATUS current
			DESCRIPTION
				"Description."
			::= { sleBridgeGarpAppPortControl 7 }

		
		-- 1.3.6.1.4.1.6296.101.3.26.2.2.8
		sleBridgeGarpAppPortControlPortStatus OBJECT-TYPE
			SYNTAX INTEGER
				{
				enable(1),
				disable(2)
				}
			MAX-ACCESS read-write
			STATUS current
			DESCRIPTION
				"Description."
			::= { sleBridgeGarpAppPortControl 8 }

		
		-- 1.3.6.1.4.1.6296.101.3.26.2.2.9
		sleBridgeGarpAppPortControlRegistration OBJECT-TYPE
			SYNTAX INTEGER
				{
				nomal(1),
				fixed(2),
				forbidden(3)
				}
			MAX-ACCESS read-write
			STATUS current
			DESCRIPTION
				"Description."
			::= { sleBridgeGarpAppPortControl 9 }

		
		-- 1.3.6.1.4.1.6296.101.3.26.2.2.10
		sleBridgeGarpAppPortControlApplicant OBJECT-TYPE
			SYNTAX INTEGER
				{
				participant(1),
				nonPorticipant(2)
				}
			MAX-ACCESS read-write
			STATUS current
			DESCRIPTION
				"Description."
			::= { sleBridgeGarpAppPortControl 10 }

		
		-- 1.3.6.1.4.1.6296.101.3.26.2.2.11
		sleBridgeGarpAppPortControlFwdAll OBJECT-TYPE
			SYNTAX INTEGER
				{
				enable(1),
				disable(2)
				}
			MAX-ACCESS read-write
			STATUS current
			DESCRIPTION
				"Description."
			::= { sleBridgeGarpAppPortControl 11 }

		
		-- 1.3.6.1.4.1.6296.101.3.26.2.2.12
		sleBridgeGarpAppPortControlTimerJoin OBJECT-TYPE
			SYNTAX Integer32
			MAX-ACCESS read-write
			STATUS current
			DESCRIPTION
				"Description."
			::= { sleBridgeGarpAppPortControl 12 }

		
		-- 1.3.6.1.4.1.6296.101.3.26.2.2.13
		sleBridgeGarpAppPortControlTimerLeave OBJECT-TYPE
			SYNTAX Integer32
			MAX-ACCESS read-write
			STATUS current
			DESCRIPTION
				"Description."
			::= { sleBridgeGarpAppPortControl 13 }

		
		-- 1.3.6.1.4.1.6296.101.3.26.2.2.14
		sleBridgeGarpAppPortControlTimerLeaveAll OBJECT-TYPE
			SYNTAX Integer32
			MAX-ACCESS read-write
			STATUS current
			DESCRIPTION
				"Description."
			::= { sleBridgeGarpAppPortControl 14 }

		
		-- 1.3.6.1.4.1.6296.101.3.26.2.3
		sleBridgeGarpAppPortNotification OBJECT IDENTIFIER ::= { sleBridgeGarpApplication 3 }

		
		-- 1.3.6.1.4.1.6296.101.3.26.2.3.1
		sleBridgeGarpAppPortStatusChanged NOTIFICATION-TYPE
			OBJECTS { sleBridgeGarpAppPortControlRequest, sleBridgeGarpAppPortControlTimeStamp, sleBridgeGarpAppPortControlReqResult, sleBridgeGarpAppPortControlIndex, sleBridgeGarpAppPortControlType, 
				sleBridgeGarpAppPortControlPortStatus }
			STATUS current
			DESCRIPTION 
				"Description."
			::= { sleBridgeGarpAppPortNotification 1 }

		
		-- 1.3.6.1.4.1.6296.101.3.26.2.3.2
		sleBridgeGarpAppPortProfileChanged NOTIFICATION-TYPE
			OBJECTS { sleBridgeGarpAppPortControlRequest, sleBridgeGarpAppPortControlTimeStamp, sleBridgeGarpAppPortControlReqResult, sleBridgeGarpAppPortControlIndex, sleBridgeGarpAppPortControlType, 
				sleBridgeGarpAppPortControlRegistration, sleBridgeGarpAppPortControlApplicant, sleBridgeGarpAppPortControlFwdAll, sleBridgeGarpAppPortControlTimerJoin, sleBridgeGarpAppPortControlTimerLeave, 
				sleBridgeGarpAppPortControlTimerLeaveAll }
			STATUS current
			DESCRIPTION 
				"Description."
			::= { sleBridgeGarpAppPortNotification 2 }

		
		-- 1.3.6.1.4.1.6296.101.3.26.3
		sleBridgeGarpStats OBJECT IDENTIFIER ::= { sleBridgeGarp 3 }

		
		-- 1.3.6.1.4.1.6296.101.3.26.3.1
		sleBridgeGarpStatsTable OBJECT-TYPE
			SYNTAX SEQUENCE OF SleBridgeGarpStatsEntry
			MAX-ACCESS not-accessible
			STATUS current
			DESCRIPTION
				"Description."
			::= { sleBridgeGarpStats 1 }

		
		-- 1.3.6.1.4.1.6296.101.3.26.3.1.1
		sleBridgeGarpStatsEntry OBJECT-TYPE
			SYNTAX SleBridgeGarpStatsEntry
			MAX-ACCESS not-accessible
			STATUS current
			DESCRIPTION
				"Description."
			INDEX { sleBridgeGarpAppPortIndex, sleBridgeGarpAppPortType }
			::= { sleBridgeGarpStatsTable 1 }

		
		SleBridgeGarpStatsEntry ::=
			SEQUENCE { 
				sleBridgeGarpStatsJoinEmptyReceived
					Integer32,
				sleBridgeGarpStatsJoinInReceived
					Integer32,
				sleBridgeGarpStatsEmptyReceived
					Integer32,
				sleBridgeGarpStatsLeaveInReceived
					Integer32,
				sleBridgeGarpStatsLeaveEmptyReceived
					Integer32,
				sleBridgeGarpStatsLeaveAllReceived
					Integer32,
				sleBridgeGarpStatsJoinEmptyTransmitted
					Integer32,
				sleBridgeGarpStatsJoinInTransmitted
					Integer32,
				sleBridgeGarpStatsEmptyTransmitted
					Integer32,
				sleBridgeGarpStatsLeaveInTransmitted
					Integer32,
				sleBridgeGarpStatsLeaveEmptyTransmitted
					Integer32,
				sleBridgeGarpStatsLeaveAllTransmitted
					Integer32
			 }

		-- 1.3.6.1.4.1.6296.101.3.26.3.1.1.1
		sleBridgeGarpStatsJoinEmptyReceived OBJECT-TYPE
			SYNTAX Integer32
			MAX-ACCESS read-only
			STATUS current
			DESCRIPTION
				"Description."
			::= { sleBridgeGarpStatsEntry 1 }

		
		-- 1.3.6.1.4.1.6296.101.3.26.3.1.1.2
		sleBridgeGarpStatsJoinInReceived OBJECT-TYPE
			SYNTAX Integer32
			MAX-ACCESS read-only
			STATUS current
			DESCRIPTION
				"Description."
			::= { sleBridgeGarpStatsEntry 2 }

		
		-- 1.3.6.1.4.1.6296.101.3.26.3.1.1.3
		sleBridgeGarpStatsEmptyReceived OBJECT-TYPE
			SYNTAX Integer32
			MAX-ACCESS read-only
			STATUS current
			DESCRIPTION
				"Description."
			::= { sleBridgeGarpStatsEntry 3 }

		
		-- 1.3.6.1.4.1.6296.101.3.26.3.1.1.4
		sleBridgeGarpStatsLeaveInReceived OBJECT-TYPE
			SYNTAX Integer32
			MAX-ACCESS read-only
			STATUS current
			DESCRIPTION
				"Description."
			::= { sleBridgeGarpStatsEntry 4 }

		
		-- 1.3.6.1.4.1.6296.101.3.26.3.1.1.5
		sleBridgeGarpStatsLeaveEmptyReceived OBJECT-TYPE
			SYNTAX Integer32
			MAX-ACCESS read-only
			STATUS current
			DESCRIPTION
				"Description."
			::= { sleBridgeGarpStatsEntry 5 }

		
		-- 1.3.6.1.4.1.6296.101.3.26.3.1.1.6
		sleBridgeGarpStatsLeaveAllReceived OBJECT-TYPE
			SYNTAX Integer32
			MAX-ACCESS read-only
			STATUS current
			DESCRIPTION
				"Description."
			::= { sleBridgeGarpStatsEntry 6 }

		
		-- 1.3.6.1.4.1.6296.101.3.26.3.1.1.7
		sleBridgeGarpStatsJoinEmptyTransmitted OBJECT-TYPE
			SYNTAX Integer32
			MAX-ACCESS read-only
			STATUS current
			DESCRIPTION
				"Description."
			::= { sleBridgeGarpStatsEntry 7 }

		
		-- 1.3.6.1.4.1.6296.101.3.26.3.1.1.8
		sleBridgeGarpStatsJoinInTransmitted OBJECT-TYPE
			SYNTAX Integer32
			MAX-ACCESS read-only
			STATUS current
			DESCRIPTION
				"Description."
			::= { sleBridgeGarpStatsEntry 8 }

		
		-- 1.3.6.1.4.1.6296.101.3.26.3.1.1.9
		sleBridgeGarpStatsEmptyTransmitted OBJECT-TYPE
			SYNTAX Integer32
			MAX-ACCESS read-only
			STATUS current
			DESCRIPTION
				"Description."
			::= { sleBridgeGarpStatsEntry 9 }

		
		-- 1.3.6.1.4.1.6296.101.3.26.3.1.1.10
		sleBridgeGarpStatsLeaveInTransmitted OBJECT-TYPE
			SYNTAX Integer32
			MAX-ACCESS read-only
			STATUS current
			DESCRIPTION
				"Description."
			::= { sleBridgeGarpStatsEntry 10 }

		
		-- 1.3.6.1.4.1.6296.101.3.26.3.1.1.11
		sleBridgeGarpStatsLeaveEmptyTransmitted OBJECT-TYPE
			SYNTAX Integer32
			MAX-ACCESS read-only
			STATUS current
			DESCRIPTION
				"Description."
			::= { sleBridgeGarpStatsEntry 11 }

		
		-- 1.3.6.1.4.1.6296.101.3.26.3.1.1.12
		sleBridgeGarpStatsLeaveAllTransmitted OBJECT-TYPE
			SYNTAX Integer32
			MAX-ACCESS read-only
			STATUS current
			DESCRIPTION
				"Description."
			::= { sleBridgeGarpStatsEntry 12 }

		
		-- 1.3.6.1.4.1.6296.101.3.26.3.2
		sleBridgeGarpStatsControl OBJECT IDENTIFIER ::= { sleBridgeGarpStats 2 }

		
		-- 1.3.6.1.4.1.6296.101.3.26.3.2.1
		sleBridgeGarpStatsControlRequest OBJECT-TYPE
			SYNTAX INTEGER { clearGarpPktStatistics(1) }
			MAX-ACCESS read-write
			STATUS current
			DESCRIPTION
				"Description."
			::= { sleBridgeGarpStatsControl 1 }

		
		-- 1.3.6.1.4.1.6296.101.3.26.3.2.2
		sleBridgeGarpStatstControlStatus OBJECT-TYPE
			SYNTAX SleControlStatusType
			MAX-ACCESS read-only
			STATUS current
			DESCRIPTION
				"Description."
			::= { sleBridgeGarpStatsControl 2 }

		
		-- 1.3.6.1.4.1.6296.101.3.26.3.2.3
		sleBridgeGarpStatsControlTimer OBJECT-TYPE
			SYNTAX Gauge32
			MAX-ACCESS read-write
			STATUS current
			DESCRIPTION
				"Description."
			::= { sleBridgeGarpStatsControl 3 }

		
		-- 1.3.6.1.4.1.6296.101.3.26.3.2.4
		sleBridgeGarpStatsControlTimeStamp OBJECT-TYPE
			SYNTAX TimeTicks
			MAX-ACCESS read-only
			STATUS current
			DESCRIPTION
				"Description."
			::= { sleBridgeGarpStatsControl 4 }

		
		-- 1.3.6.1.4.1.6296.101.3.26.3.2.5
		sleBridgeGarpStatsControlReqResult OBJECT-TYPE
			SYNTAX SleControlRequestResultType
			MAX-ACCESS read-only
			STATUS current
			DESCRIPTION
				"Description."
			::= { sleBridgeGarpStatsControl 5 }

		
		-- 1.3.6.1.4.1.6296.101.3.26.3.2.6
		sleBridgeGarpStatsControlIndex OBJECT-TYPE
			SYNTAX INTEGER (1..65535)
			MAX-ACCESS read-write
			STATUS current
			DESCRIPTION
				"Description."
			::= { sleBridgeGarpStatsControl 6 }

		
		-- 1.3.6.1.4.1.6296.101.3.26.3.2.7
		sleBridgeGarpStatsControlType OBJECT-TYPE
			SYNTAX INTEGER
				{
				gvrp(1),
				gmrp(2)
				}
			MAX-ACCESS read-write
			STATUS current
			DESCRIPTION
				"Description."
			::= { sleBridgeGarpStatsControl 7 }

		
		-- 1.3.6.1.4.1.6296.101.3.26.3.3
		sleBridgeGarpStatsNotification OBJECT IDENTIFIER ::= { sleBridgeGarpStats 3 }

		
		-- 1.3.6.1.4.1.6296.101.3.26.3.3.1
		sleBridgeGarpStatisticsCleared NOTIFICATION-TYPE
			OBJECTS { sleBridgeGarpStatsControlRequest, sleBridgeGarpStatsControlTimeStamp, sleBridgeGarpStatsControlReqResult, sleBridgeGarpStatsControlIndex, sleBridgeGarpStatsControlType
				 }
			STATUS current
			DESCRIPTION 
				"Description."
			::= { sleBridgeGarpStatsNotification 1 }

		
		-- 1.3.6.1.4.1.6296.101.3.26.4
		sleBridgeGmrpStatic OBJECT IDENTIFIER ::= { sleBridgeGarp 4 }

		
		-- 1.3.6.1.4.1.6296.101.3.26.4.1
		sleBridgeGmrpStaticTable OBJECT-TYPE
			SYNTAX SEQUENCE OF SleBridgeGmrpStaticEntry
			MAX-ACCESS not-accessible
			STATUS current
			DESCRIPTION
				"Description."
			::= { sleBridgeGmrpStatic 1 }

		
		-- 1.3.6.1.4.1.6296.101.3.26.4.1.1
		sleBridgeGmrpStaticEntry OBJECT-TYPE
			SYNTAX SleBridgeGmrpStaticEntry
			MAX-ACCESS not-accessible
			STATUS current
			DESCRIPTION
				"Description."
			INDEX { sleBridgeGmrpStaticVid, sleBridgeGmrpStaticPort, sleBridgeGmrpStaticGmac }
			::= { sleBridgeGmrpStaticTable 1 }

		
		SleBridgeGmrpStaticEntry ::=
			SEQUENCE { 
				sleBridgeGmrpStaticVid
					INTEGER,
				sleBridgeGmrpStaticPort
					INTEGER,
				sleBridgeGmrpStaticGmac
					OCTET STRING
			 }

		-- 1.3.6.1.4.1.6296.101.3.26.4.1.1.1
		sleBridgeGmrpStaticVid OBJECT-TYPE
			SYNTAX INTEGER (1..65535)
			MAX-ACCESS read-only
			STATUS current
			DESCRIPTION
				"VLAN Id"
			::= { sleBridgeGmrpStaticEntry 1 }

		
		-- 1.3.6.1.4.1.6296.101.3.26.4.1.1.2
		sleBridgeGmrpStaticPort OBJECT-TYPE
			SYNTAX INTEGER (1..65535)
			MAX-ACCESS read-only
			STATUS current
			DESCRIPTION
				"Port index"
			::= { sleBridgeGmrpStaticEntry 2 }

		
		-- 1.3.6.1.4.1.6296.101.3.26.4.1.1.3
		sleBridgeGmrpStaticGmac OBJECT-TYPE
			SYNTAX OCTET STRING (SIZE (0..6))
			MAX-ACCESS read-only
			STATUS current
			DESCRIPTION
				"Group Mac Address"
			::= { sleBridgeGmrpStaticEntry 3 }

		
		-- 1.3.6.1.4.1.6296.101.3.26.4.2
		sleBridgeGmrpStaticControl OBJECT IDENTIFIER ::= { sleBridgeGmrpStatic 2 }

		
		-- 1.3.6.1.4.1.6296.101.3.26.4.2.1
		sleBridgeGmrpStaticControlRequest OBJECT-TYPE
			SYNTAX INTEGER
				{
				addGmrpStatic(1),
				delGmrpStatic(2)
				}
			MAX-ACCESS read-write
			STATUS current
			DESCRIPTION
				"Description."
			::= { sleBridgeGmrpStaticControl 1 }

		
		-- 1.3.6.1.4.1.6296.101.3.26.4.2.2
		sleBridgeGmrpStaticControlStatus OBJECT-TYPE
			SYNTAX SleControlStatusType
			MAX-ACCESS read-only
			STATUS current
			DESCRIPTION
				"Description."
			::= { sleBridgeGmrpStaticControl 2 }

		
		-- 1.3.6.1.4.1.6296.101.3.26.4.2.3
		sleBridgeGmrpStaticControlTimer OBJECT-TYPE
			SYNTAX Gauge32
			MAX-ACCESS read-write
			STATUS current
			DESCRIPTION
				"Description."
			::= { sleBridgeGmrpStaticControl 3 }

		
		-- 1.3.6.1.4.1.6296.101.3.26.4.2.4
		sleBridgeGmrpStaticControlTimeStamp OBJECT-TYPE
			SYNTAX TimeTicks
			MAX-ACCESS read-only
			STATUS current
			DESCRIPTION
				"Description."
			::= { sleBridgeGmrpStaticControl 4 }

		
		-- 1.3.6.1.4.1.6296.101.3.26.4.2.5
		sleBridgeGmrpStaticControlReqResult OBJECT-TYPE
			SYNTAX SleControlRequestResultType
			MAX-ACCESS read-only
			STATUS current
			DESCRIPTION
				"Description."
			::= { sleBridgeGmrpStaticControl 5 }

		
		-- 1.3.6.1.4.1.6296.101.3.26.4.2.6
		sleBridgeGmrpStaticControlVid OBJECT-TYPE
			SYNTAX INTEGER (1..65535)
			MAX-ACCESS read-write
			STATUS current
			DESCRIPTION
				"Description."
			::= { sleBridgeGmrpStaticControl 6 }

		
		-- 1.3.6.1.4.1.6296.101.3.26.4.2.7
		sleBridgeGmrpStaticControlPort OBJECT-TYPE
			SYNTAX INTEGER (1..65535)
			MAX-ACCESS read-write
			STATUS current
			DESCRIPTION
				"Description."
			::= { sleBridgeGmrpStaticControl 7 }

		
		-- 1.3.6.1.4.1.6296.101.3.26.4.2.8
		sleBridgeGmrpStaticControlGmac OBJECT-TYPE
			SYNTAX OCTET STRING (SIZE (0..6))
			MAX-ACCESS read-write
			STATUS current
			DESCRIPTION
				"Description."
			::= { sleBridgeGmrpStaticControl 8 }

		
		-- 1.3.6.1.4.1.6296.101.3.26.4.3
		sleBridgeGmrpStaticNotification OBJECT IDENTIFIER ::= { sleBridgeGmrpStatic 3 }

		
		-- 1.3.6.1.4.1.6296.101.3.26.4.3.1
		sleBridgeGmrpStaticAdded NOTIFICATION-TYPE
			OBJECTS { sleBridgeGmrpStaticControlRequest, sleBridgeGmrpStaticControlTimeStamp, sleBridgeGmrpStaticControlReqResult, sleBridgeGmrpStaticControlVid, sleBridgeGmrpStaticControlPort, 
				sleBridgeGmrpStaticControlGmac }
			STATUS current
			DESCRIPTION 
				"Description."
			::= { sleBridgeGmrpStaticNotification 1 }

		
		-- 1.3.6.1.4.1.6296.101.3.26.4.3.2
		sleBridgeGmrpStaticDeleted NOTIFICATION-TYPE
			OBJECTS { sleBridgeGmrpStaticControlRequest, sleBridgeGmrpStaticControlTimeStamp, sleBridgeGmrpStaticControlReqResult, sleBridgeGmrpStaticControlVid, sleBridgeGmrpStaticControlPort, 
				sleBridgeGmrpStaticControlGmac }
			STATUS current
			DESCRIPTION 
				"Description."
			::= { sleBridgeGmrpStaticNotification 2 }

		
		-- 1.3.6.1.4.1.6296.101.3.27
		sleVlanTag OBJECT IDENTIFIER ::= { sleBridge 27 }

		
		-- 1.3.6.1.4.1.6296.101.3.27.1
		sleVlanInboundTag OBJECT IDENTIFIER ::= { sleVlanTag 1 }

		
		-- 1.3.6.1.4.1.6296.101.3.27.1.1
		sleVlanInboundTagTable OBJECT-TYPE
			SYNTAX SEQUENCE OF SleVlanInboundTagEntry
			MAX-ACCESS not-accessible
			STATUS current
			DESCRIPTION
				"Description."
			::= { sleVlanInboundTag 1 }

		
		-- 1.3.6.1.4.1.6296.101.3.27.1.1.1
		sleVlanInboundTagEntry OBJECT-TYPE
			SYNTAX SleVlanInboundTagEntry
			MAX-ACCESS not-accessible
			STATUS current
			DESCRIPTION
				"Description."
			INDEX { sleVlanInboundTagPortIndex, sleVlanInboundTagVlanIndex }
			::= { sleVlanInboundTagTable 1 }

		
		SleVlanInboundTagEntry ::=
			SEQUENCE { 
				sleVlanInboundTagPortIndex
					INTEGER,
				sleVlanInboundTagVlanIndex
					INTEGER,
				sleVlanInboundTagOuterVid
					INTEGER
			 }

		-- 1.3.6.1.4.1.6296.101.3.27.1.1.1.1
		sleVlanInboundTagPortIndex OBJECT-TYPE
			SYNTAX INTEGER (1..65535)
			MAX-ACCESS read-only
			STATUS current
			DESCRIPTION
				"Bridge Port Index"
			::= { sleVlanInboundTagEntry 1 }

		
		-- 1.3.6.1.4.1.6296.101.3.27.1.1.1.2
		sleVlanInboundTagVlanIndex OBJECT-TYPE
			SYNTAX INTEGER (1..4094)
			MAX-ACCESS read-only
			STATUS current
			DESCRIPTION
				"Vlan Index of inner-tag"
			::= { sleVlanInboundTagEntry 2 }

		
		-- 1.3.6.1.4.1.6296.101.3.27.1.1.1.3
		sleVlanInboundTagOuterVid OBJECT-TYPE
			SYNTAX INTEGER (1..4094)
			MAX-ACCESS read-write
			STATUS current
			DESCRIPTION
				"The Outer Vlan-ID to tag for incoming packet with vlan index"
			::= { sleVlanInboundTagEntry 3 }

		
		-- 1.3.6.1.4.1.6296.101.3.27.1.2
		sleVlanInboundTagControl OBJECT IDENTIFIER ::= { sleVlanInboundTag 2 }

		
		-- 1.3.6.1.4.1.6296.101.3.27.1.2.1
		sleVlanInboundTagControlRequest OBJECT-TYPE
			SYNTAX INTEGER { setInboundVid(1) }
			MAX-ACCESS read-write
			STATUS current
			DESCRIPTION
				"Description."
			::= { sleVlanInboundTagControl 1 }

		
		-- 1.3.6.1.4.1.6296.101.3.27.1.2.2
		sleVlanInboundTagControlStatus OBJECT-TYPE
			SYNTAX SleControlStatusType
			MAX-ACCESS read-only
			STATUS current
			DESCRIPTION
				"Description."
			::= { sleVlanInboundTagControl 2 }

		
		-- 1.3.6.1.4.1.6296.101.3.27.1.2.3
		sleVlanInboundTagControlTimer OBJECT-TYPE
			SYNTAX Gauge32
			MAX-ACCESS read-write
			STATUS current
			DESCRIPTION
				"Description."
			::= { sleVlanInboundTagControl 3 }

		
		-- 1.3.6.1.4.1.6296.101.3.27.1.2.4
		sleVlanInboundTagControlTimeStamp OBJECT-TYPE
			SYNTAX TimeTicks
			MAX-ACCESS read-only
			STATUS current
			DESCRIPTION
				"Description."
			::= { sleVlanInboundTagControl 4 }

		
		-- 1.3.6.1.4.1.6296.101.3.27.1.2.5
		sleVlanInboundTagControlReqResult OBJECT-TYPE
			SYNTAX SleControlRequestResultType
			MAX-ACCESS read-only
			STATUS current
			DESCRIPTION
				"Description."
			::= { sleVlanInboundTagControl 5 }

		
		-- 1.3.6.1.4.1.6296.101.3.27.1.2.6
		sleVlanInboundTagControlPortIndex OBJECT-TYPE
			SYNTAX INTEGER (1..65535)
			MAX-ACCESS read-write
			STATUS current
			DESCRIPTION
				"sleVlanInboundTagPortIndex"
			::= { sleVlanInboundTagControl 6 }

		
		-- 1.3.6.1.4.1.6296.101.3.27.1.2.7
		sleVlanInboundTagControlVlanIndex OBJECT-TYPE
			SYNTAX INTEGER (1..4094)
			MAX-ACCESS read-write
			STATUS current
			DESCRIPTION
				"sleVlanInboundTagVlanIndex"
			::= { sleVlanInboundTagControl 7 }

		
		-- 1.3.6.1.4.1.6296.101.3.27.1.2.8
		sleVlanInboundTagControlOuterVid OBJECT-TYPE
			SYNTAX INTEGER (0..4094)
			MAX-ACCESS read-write
			STATUS current
			DESCRIPTION
				"The Vlan-ID for outer-tag
				0 : clear
				"
			::= { sleVlanInboundTagControl 8 }

		
		-- 1.3.6.1.4.1.6296.101.3.27.1.3
		sleVlanInboundTagNotification OBJECT IDENTIFIER ::= { sleVlanInboundTag 3 }

		
		-- 1.3.6.1.4.1.6296.101.3.27.1.3.1
		sleVlanInboundTagChanged NOTIFICATION-TYPE
			OBJECTS { sleVlanInboundTagControlRequest, sleVlanInboundTagControlReqResult, sleVlanInboundTagControlTimeStamp, sleVlanInboundTagControlPortIndex, sleVlanInboundTagControlVlanIndex, 
				sleVlanInboundTagControlOuterVid }
			STATUS current
			DESCRIPTION 
				"setInboundVid"
			::= { sleVlanInboundTagNotification 1 }

		
		-- 1.3.6.1.4.1.6296.101.3.27.2
		sleVlanOutboundTag OBJECT IDENTIFIER ::= { sleVlanTag 2 }

		
		-- 1.3.6.1.4.1.6296.101.3.27.2.1
		sleVlanOutboundTagTable OBJECT-TYPE
			SYNTAX SEQUENCE OF SleVlanOutboundTagEntry
			MAX-ACCESS not-accessible
			STATUS current
			DESCRIPTION
				"Description."
			::= { sleVlanOutboundTag 1 }

		
		-- 1.3.6.1.4.1.6296.101.3.27.2.1.1
		sleVlanOutboundTagEntry OBJECT-TYPE
			SYNTAX SleVlanOutboundTagEntry
			MAX-ACCESS not-accessible
			STATUS current
			DESCRIPTION
				"Description."
			INDEX { sleVlanOutboundTagPortIndex, sleVlanOutboundTagVlanIndex }
			::= { sleVlanOutboundTagTable 1 }

		
		SleVlanOutboundTagEntry ::=
			SEQUENCE { 
				sleVlanOutboundTagPortIndex
					INTEGER,
				sleVlanOutboundTagVlanIndex
					INTEGER
			 }

		-- 1.3.6.1.4.1.6296.101.3.27.2.1.1.1
		sleVlanOutboundTagPortIndex OBJECT-TYPE
			SYNTAX INTEGER (1..65535)
			MAX-ACCESS read-only
			STATUS current
			DESCRIPTION
				"Bridge Port Index for egress port"
			::= { sleVlanOutboundTagEntry 1 }

		
		-- 1.3.6.1.4.1.6296.101.3.27.2.1.1.2
		sleVlanOutboundTagVlanIndex OBJECT-TYPE
			SYNTAX INTEGER (1..4094)
			MAX-ACCESS read-only
			STATUS current
			DESCRIPTION
				"Vlan index of outer-tag"
			::= { sleVlanOutboundTagEntry 2 }

		
		-- 1.3.6.1.4.1.6296.101.3.27.2.2
		sleVlanOutboundTagControl OBJECT IDENTIFIER ::= { sleVlanOutboundTag 2 }

		
		-- 1.3.6.1.4.1.6296.101.3.27.2.2.1
		sleVlanOutboundTagControlRequest OBJECT-TYPE
			SYNTAX INTEGER
				{
				setOutboundtag(1),
				clearOutboundtag(2)
				}
			MAX-ACCESS read-write
			STATUS current
			DESCRIPTION
				"Description."
			::= { sleVlanOutboundTagControl 1 }

		
		-- 1.3.6.1.4.1.6296.101.3.27.2.2.2
		sleVlanOutboundTagControlStatus OBJECT-TYPE
			SYNTAX SleControlStatusType
			MAX-ACCESS read-only
			STATUS current
			DESCRIPTION
				"Description."
			::= { sleVlanOutboundTagControl 2 }

		
		-- 1.3.6.1.4.1.6296.101.3.27.2.2.3
		sleVlanOutboundTagControlTimer OBJECT-TYPE
			SYNTAX Gauge32
			MAX-ACCESS read-write
			STATUS current
			DESCRIPTION
				"Description."
			::= { sleVlanOutboundTagControl 3 }

		
		-- 1.3.6.1.4.1.6296.101.3.27.2.2.4
		sleVlanOutboundTagControlTimeStamp OBJECT-TYPE
			SYNTAX TimeTicks
			MAX-ACCESS read-only
			STATUS current
			DESCRIPTION
				"Description."
			::= { sleVlanOutboundTagControl 4 }

		
		-- 1.3.6.1.4.1.6296.101.3.27.2.2.5
		sleVlanOutboundTagControlReqResult OBJECT-TYPE
			SYNTAX SleControlRequestResultType
			MAX-ACCESS read-only
			STATUS current
			DESCRIPTION
				"Description."
			::= { sleVlanOutboundTagControl 5 }

		
		-- 1.3.6.1.4.1.6296.101.3.27.2.2.6
		sleVlanOutboundTagControlPortIndex OBJECT-TYPE
			SYNTAX INTEGER (1..65535)
			MAX-ACCESS read-write
			STATUS current
			DESCRIPTION
				"sleVlanOutboundTagPortIndex"
			::= { sleVlanOutboundTagControl 6 }

		
		-- 1.3.6.1.4.1.6296.101.3.27.2.2.7
		sleVlanOutboundTagControlOuterVid OBJECT-TYPE
			SYNTAX INTEGER (1..4094)
			MAX-ACCESS read-write
			STATUS current
			DESCRIPTION
				"The outer-tag vid of packet to go out on the egress port"
			::= { sleVlanOutboundTagControl 7 }

		
		-- 1.3.6.1.4.1.6296.101.3.27.2.3
		sleVlanOutboundTagNotification OBJECT IDENTIFIER ::= { sleVlanOutboundTag 3 }

		
		-- 1.3.6.1.4.1.6296.101.3.27.2.3.1
		sleVlanOutboundTagSet NOTIFICATION-TYPE
			OBJECTS { sleVlanOutboundTagControlRequest, sleVlanOutboundTagControlReqResult, sleVlanOutboundTagControlTimeStamp, sleVlanOutboundTagControlPortIndex, sleVlanOutboundTagControlOuterVid
				 }
			STATUS current
			DESCRIPTION 
				"setOutboundtag"
			::= { sleVlanOutboundTagNotification 1 }

		
		-- 1.3.6.1.4.1.6296.101.3.27.2.3.2
		sleVlanOutboundTagClear NOTIFICATION-TYPE
			OBJECTS { sleVlanOutboundTagControlRequest, sleVlanOutboundTagControlReqResult, sleVlanOutboundTagControlTimeStamp, sleVlanOutboundTagControlPortIndex, sleVlanOutboundTagControlOuterVid
				 }
			STATUS current
			DESCRIPTION 
				"clearOutboundtag"
			::= { sleVlanOutboundTagNotification 2 }

		
		-- 1.3.6.1.4.1.6296.101.3.28
		sleBridgeGroup OBJECT-GROUP
			OBJECTS { sleBridgeMacAddress, sleBridgePortNum, sleBridgeLagMaxId, sleBridgeLacpActivity, sleBridgeLacpPriority, 
				sleBridgeVlanSupportMode, sleBridgeVlanMaxNum, sleBridgeDoubleTagProtoId, sleBridgeMirrorMode, sleBridgeMirrorMonitorPortId, 
				sleBridgeMirroredIngressPorts, sleBridgeMirroredEgressPorts, sleBridgeMaxLearnPerUnit, sleBridgeFdbAgeingTime, sleBridgeFdbMaxEntries, 
				sleBridgeFdbCurrentEntries, sleBridgeStackMode, sleBridgeStackDeviceName, sleBridgeStackNodeId, sleBridgeLldpMessageTxInterval, 
				sleBridgeLldpTxHoldMultiplier, sleBridgeLldpReinitDelay, sleBridgeLldpTxDelay, sleBridgeLldpNotificationInterval, sleBridgeLldpStatsRemTablesLastChangeTime, 
				sleBridgeLldpStatsRemTablesInserts, sleBridgeLldpStatsRemTablesDeletes, sleBridgeLldpStatsRemTablesDrops, sleBridgeLldpStatsRemTablesAgeouts, sleBridgeLldpLocalChassisIdSubtype, 
				sleBridgeLldpLocalChassisId, sleBridgeLldpLocalSysName, sleBridgeLldpLocalSysDes, sleBridgeLldpLocalSysCapSupported, sleBridgeLldpLocalSysCapEnabled, 
				sleBridgeStpActivity, sleBridgeStpSelfLoop, sleBridgePvlanOnePromPortEnable, sleBridgeTcpSyncookie, sleBridgeTcpIgnoreRstUnknown, 
				sleBridgeControlRequest, sleBridgeControlStatus, sleBridgeControlTimer, sleBridgeControlTimeStamp, sleBridgeControlReqResult, 
				sleBridgeControlLacpActivity, sleBridgeControlLacpPriority, sleBridgeControlDoubleTagProtoId, sleBridgeControlMirrorMode, sleBridgeControlMirrorMonitorPortId, 
				sleBridgeControlMaxLearnPerUnit, sleBridgeControlFdbAgeingTime, sleBridgeControlStackMode, sleBridgeControlStackDeviceName, sleBridgeControlLldpMessageTxInterval, 
				sleBridgeControlLldpTxHoldMultiplier, sleBridgeControlLldpReinitDelay, sleBridgeControlLldpTxDelay, sleBridgeControlLldpNotificationInterval, sleBridgeControlStpActivity, 
				sleBridgeControlStpSelfLoop, sleBridgeControlTcpSyncookie, sleBridgeControlTcpIgnoreRstUnknown, sleBridgePortIndex, sleBridgePortIfIndex, 
				sleBridgePortPVid, sleBridgePortMaxHosts, sleBridgePortCurrentHosts, sleBridgePortMaxLearnPerUnit, sleBridgePortMACFilterPermission, 
				sleBridgePortIngMirrorStatus, sleBridgePortEgMirrorStatus, sleBridgePortBcastThreshold, sleBridgePortMcastThreshold, sleBridgePortDlfThreshold, 
				sleBridgePortQinQStatus, sleBridgePortAdminLinktype, sleBridgePortAdminEdgemode, sleBridgePortOperLinktype, sleBridgePortOperEdgemode, 
				sleBridgePortStpBpduFilter, sleBridgePortPvlanIsolatedStatus, sleBridgePortPvlanPromPorts, sleBridgePortControlRequest, sleBridgePortControlStatus, 
				sleBridgePortControlTimer, sleBridgePortControlTimeStamp, sleBridgePortControlReqResult, sleBridgePortControlIndex, sleBridgePortControlPVid, 
				sleBridgePortControlMaxHosts, sleBridgePortControlMaxLearnPerUnit, sleBridgePortControlMACFilterPermission, sleBridgePortControlIngMirrorStatus, sleBridgePortControlEgMirrorStatus, 
				sleBridgePortControlBcastThreshold, sleBridgePortControlMcastThreshold, sleBridgePortControlDlfThreshold, sleBridgePortControlQinQStatus, sleBridgePortControlAdminLinktype, 
				sleBridgePortControlAdminEdgemode, sleBridgePortControlStpBpduFilter, sleBridgePortControlPvlanIsolatedStatus, sleBridgePortControlPvlanPromPort, sleBridgePortControlStpBpduGuardErrRcv, 
				sleVlanIndex, sleVlanIfIndex, sleVlanName, sleVlanStatus, sleVlanEgressPorts, 
				sleVlanUnTaggedPorts, sleVlanCreationTime, sleVlanAgeingTime, sleVlanControlRequest, sleVlanControlStatus, 
				sleVlanControlTimer, sleVlanControlTimeStamp, sleVlanControlReqResult, sleVlanControlIndex, sleVlanControlName, 
				sleVlanControlEgressPorts, sleVlanControlUnTaggedPorts, sleVlanControlAgeingTime, sleVlanMapFid, sleVlanMapStpId, 
				sleVlanMapErpDomainId, sleVlanMapControlRequest, sleVlanMapControlStatus, sleVlanMapControlTimer, sleVlanMapControlTimeStamp, 
				sleVlanMapControlReqResult, sleVlanMapControlIndex, sleVlanMapControlFid, sleVlanMapControlStpId, sleVlanMapControlErpDomainId, 
				sleStpOperationMode, sleStpFormatSelector, sleStpConfigureName, sleStpRevisionLevel, sleStpFwdDelay, 
				sleStpHelloTime, sleStpMaxAge, sleStpMaxHops, sleStpExtRootBridgeId, sleStpExtPathcost, 
				sleStpBpduGuardMode, sleStpBpduGuardAutoRcvMode, sleStpBpduGuardAutoRcvTime, sleStpControlRequest, sleStpControlStatus, 
				sleStpControlTimer, sleStpControlTimeStamp, sleStpControlReqResult, sleStpControlOperationMode, sleStpControlConfigureName, 
				sleStpControlRevisionLevel, sleStpControlFwdDelay, sleStpControlHelloTime, sleStpControlMaxAge, sleStpControlMaxHops, 
				sleStpControlBpduGuardMode, sleStpControlBpduGuardAutoRcvMode, sleStpControlBpduGuardAutoRcvTime, sleStpInstanceIndex, sleStpInstanceEnable, 
				sleStpInstancePriority, sleStpInstanceRootBridgeId, sleStpInstanceRootPathcost, sleStpInstanceDesignatedBridgeId, sleStpInstanceDesignatedPortId, 
				sleStpInstanceRootPortId, sleStpInstanceFwdDelay, sleStpInstanceHelloTime, sleStpInstanceMaxAge, sleStpInstanceRemainHops, 
				sleStpInstanceBrFwdDelay, sleStpInstanceBrHelloTime, sleStpInstanceBrMaxAge, sleStpInstanceControlRequest, sleStpInstanceControlStatus, 
				sleStpInstanceControlTimer, sleStpInstanceControlTimeStamp, sleStpInstanceControlReqResult, sleStpInstanceControlIndex, sleStpInstanceControlEnable, 
				sleStpInstanceControlPriority, sleStpInstanceControlBrFwdDelay, sleStpInstanceControlBrHelloTime, sleStpInstanceControlBrMaxAge, sleStpInstancePortIndex, 
				sleStpInstancePortPathcost, sleStpInstancePortPriority, sleStpInstancePortRole, sleStpInstancePortState, sleStpInstancePortRootBridgeId, 
				sleStpInstancePortRootPathcost, sleStpInstancePortDesignateBridgeId, sleStpInstancePortDesignatePortId, sleStpInstancePortRootGuardMode, sleStpInstancePortControlRequest, 
				sleStpInstancePortControlStatus, sleStpInstancePortControlTimer, sleStpInstancePortControlTimeStamp, sleStpInstancePortControlReqResult, sleStpInstancePortControlIndex, 
				sleStpInstancePortControlInstanceId, sleStpInstancePortControlPathcost, sleStpInstancePortControlPriority, sleStpInstancePortControlRootGuardMode, sleSubnetVlanIp, 
				sleSubnetVlanMask, sleSubnetVlanVid, sleSubnetVlanControlRequest, sleSubnetVlanControlStatus, sleSubnetVlanControlTimer, 
				sleSubnetVlanControlTimeStamp, sleSubnetVlanControlReqResult, sleSubnetVlanControlIp, sleSubnetVlanControlMask, sleSubnetVlanControlVid, 
				sleProtocolVlanEtype, sleProtocolVlanVid, sleProtocolVlanControlRequest, sleProtocolVlanControlStatus, sleProtocolVlanControlTimer, 
				sleProtocolVlanControlTimeStamp, sleProtocolVlanControlReqResult, sleProtocolVlanControlPortIndex, sleProtocolVlanControlEtype, sleProtocolVlanControlVid, 
				sleLagIndex, sleLagPortId, sleLagDistMode, sleLagPortMap, sleLagMode, 
				sleLagControlRequest, sleLagControlStatus, sleLagControlTimer, sleLagControlTimeStamp, sleLagControlReqResult, 
				sleLagControlIndex, sleLagControlDistMode, sleLagControlPortMap, sleLagControlMode, sleLagLacpIndex, 
				sleLagLacpActorAggregatorKey, sleLagLacpActorSystemMAC, sleLagLacpPartnerSystemMAC, sleLagLacpPartnerSystemPriority, sleLagLacpPartnerAggregatorKey, 
				sleLagLacpPortIndex, sleLagLacpPortActivity, sleLagLacpPortActorPriority, sleLagLacpPortActorAggregatorId, sleLagLacpPortActorAdminKey, 
				sleLagLacpPortActorAdminState, sleLagLacpPortActorOperKey, sleLagLacpPortActorOperState, sleLagLacpPortPartnerAdminSystemMAC, sleLagLacpPortPartnerAdminSystemPriority, 
				sleLagLacpPortPartnerAdminKey, sleLagLacpPortPartnerAdminNum, sleLagLacpPortPartnerAdminPriority, sleLagLacpPortPartnerAdminState, sleLagLacpPortPartnerOperSystemMAC, 
				sleLagLacpPortPartnerOperSystemPriority, sleLagLacpPortPartnerOperKey, sleLagLacpPortPartnerOperNum, sleLagLacpPortPartnerOperPriority, sleLagLacpPortPartnerOperState, 
				sleLagLacpPortControlRequest, sleLagLacpPortControlStatus, sleLagLacpPortControlTimer, sleLagLacpPortControlTimeStamp, sleLagLacpPortControlReqResult, 
				sleLagLacpPortControlIndex, sleLagLacpPortControlActivity, sleLagLacpPortControlMode, sleLagLacpPortControlAdminKey, sleLagLacpPortControlAggregation, 
				sleLagLacpPortControlPriority, sleLagLacpPortControlTimeout, sleFdbEntryFid, sleFdbEntryPort, sleFdbEntryMacAddress, 
				sleFdbEntryVid, sleFdbEntryMode, sleFdbEntryPermission, sleFdbEntryElapsedTime, sleFdbEntryControlRequest, 
				sleFdbEntryControlStatus, sleFdbEntryControlTimer, sleFdbEntryControlTImeStamp, sleFdbEntryControlReqResult, sleFdbEntryControlFid, 
				sleFdbEntryControlPort, sleFdbEntryControlMacAddress, sleMfdbMacAddress, sleMfdbEntryPermission, sleMfdbVlanIndex, 
				sleMfdbPorts, sleMfdbControlRequest, sleMfdbControlStatus, sleMfdbControlTimer, sleMfdbControlTimeStamp, 
				sleMfdbControlReqResult, sleMfdbControlMacAddress, sleMfdbControlEntryPermission, sleMfdbControlVlanIndex, sleMfdbControlPorts, 
				sleIgmpConfVlanIndex, sleIgmpConfEnable, sleIgmpConfMulticastFilter, sleIgmpConfOutmostVlan, sleIgmpConfSnoopEnable, 
				sleIgmpConfSnoopJoinDelay, sleIgmpConfSnoopQueryDelay, sleIgmpConfSnoopMrouter, sleIgmpConfSnoopFastLeave, sleIgmpConfSnoopQuerier, 
				sleIgmpConfControlRequest, sleIgmpConfControlStatus, sleIgmpConfControlTimer, sleIgmpConfControlReqResult, sleIgmpConfControlTimeStamp, 
				sleIgmpConfControlVlanIndex, sleIgmpConfControlEnable, sleIgmpConfControlMulticastFilter, sleIgmpConfControlOutmostVlan, sleIgmpConfControlSnoopEnable, 
				sleIgmpConfControlSnoopJoinDelay, sleIgmpConfControlSnoopQueryDelay, sleIgmpConfControlSnoopMrouter, sleIgmpConfControlSnoopFastLeave, sleIgmpConfControlSnoopQuerier, 
				sleIgmpMcastVlanIndex, sleIgmpMcastIPAddress, sleIgmpMcastPortIndex, sleIgmpMcastType, sleIgmpMcastExpireTime, 
				sleIgmpMcastControlReqest, sleIgmpMcastControlStatus, sleIgmpMcastControlTimer, sleIgmpMcastControlTimeStamp, sleIgmpMcastControlReqResult, 
				sleIgmpMcastControlVlanIndex, sleIgmpMcastControlIPAddress, sleIgmpMcastControlPortIndex, sleStackDeviceMacAddress, sleStackDeviceNodeId, 
				sleStackDeviceDescriptor, sleStackDeviceMode, sleStackDeviceStatus, sleStackDeviceType, sleStackDeviceHostName, 
				sleStackDevicePortNum, sleStackDeviceControlRequest, sleStackDeviceControlStatus, sleStackDeviceControlTimer, sleStackDeviceControlTImeStamp, 
				sleStackDeviceControlReqResult, sleStackDeviceControlMacAddress, sleStackDeviceControlDescriptor, sleErpDomainIndex, sleErpDomainName, 
				sleErpDomainPrimaryPort, sleErpDomainSecondaryPort, sleErpDomainBridgeRole, sleErpDomainProtectionActivation, sleErpDomainOperatorRequest, 
				sleErpDomainWaitToRestoreTime, sleErpDomainTestPacketInterval, sleErpDomainLearningDisabledTime, sleErpDomainNodeStatus, sleErpDomainRingStatus, 
				sleErpDomainLotp, sleErpDomainULotp, sleErpDomainMultipleRM, sleErpDomainRMNodeReacheablility, sleErpDomainControlRequest, 
				sleErpDomainControlStatus, sleErpDomainControlTimer, sleErpDomainControlTImeStamp, sleErpDomainControlReqResult, sleErpDomainControlIndex, 
				sleErpDomainControlName, sleErpDomainControlPrimaryPort, sleErpDomainControlSecondaryPort, sleErpDomainControlBridgeRole, sleErpDomainControlProtectionActivation, 
				sleErpDomainControlOperatorRequest, sleErpDomainControlWaitToRestoreTime, sleErpDomainControlTestPacketInterval, sleErpDomainControlLearningDisabledTime, sleLldpPortIndex, 
				sleLldpPortActivity, sleLldpPortAdminStatus, sleLldpPortNotificationEnable, sleLldpPortTLVsTxEnable, sleLldpPortMgmtTxEnable, 
				sleLldpPortMgmtAddress, sleLldpPortControlRequest, sleLldpPortControlStatus, sleLldpPortControlTimer, sleLldpPortControlTimeStamp, 
				sleLldpPortControlReqResult, sleLldpPortControlIndex, sleLldpPortControlActivity, sleLldpPortControlAdminstatus, sleLldpPortControlNotificationEnable, 
				sleLldpPortControlTLVsTxEnable, sleLldpPortControlMgmtTxEnable, sleLldpPortControlMgmtAddress, sleLldpRemIndex, sleLldpRemTimeMark, 
				sleLldpRemChassisIdSubtype, sleLldpRemChassisId, sleLldpRemPortIdSubtype, sleLldpRemPortId, sleLldpRemPortDesc, 
				sleLldpRemSysName, sleLldpRemSysDesc, sleLldpRemSysCapSupported, sleLldpRemSysCapEnabled, sleLldpStatsTxPortFramesTotal, 
				sleLldpStatsRxPortFramesDiscardedTotal, sleLldpStatsRxPortFramesErrors, sleLldpStatsRxPortFramesTotal, sleLldpStatsRxPortTLVsDiscardedTotal, sleLldpStatsRxPortTLVsUnrecognizedTotal, 
				sleLldpStatsRxPortAgeoutsTotal, sleLldpStatsControlRequest, sleLldpStatsControlStatus, sleLldpStatsControlTimer, sleLldpStatsControlTimeStamp, 
				sleLldpStatsControlReqResult, sleLldpStatsControlPortIndex, sleBridgePSIndex, sleBridgePSStatus, sleBridgePSMaxCount, 
				sleBridgePSCurrCount, sleBridgePSAgingType, sleBridgePSAgingTimer, sleBridgePSAgingStatic, sleBridgePSViolation, 
				sleBridgePSControlRequest, sleBridgePSControlStatus, sleBridgePSControlTimer, sleBridgePSControlTimeStamp, sleBridgePSControlReqResult, 
				sleBridgePSControlIndex, sleBridgePSControlPSStatus, sleBridgePSControlMaxCount, sleBridgePSControlAgingType, sleBridgePSControlAgingTimer, 
				sleBridgePSControlAgingStatic, sleBridgePScontrolViolation, sleBridgePSFdbPort, sleBridgePSFdbVid, sleBridgePSFdbMacAddress, 
				sleBridgePSFdbMode, sleBridgePSFdbElapsedTime, sleBridgePSFdbControlRequest, sleBridgePSFdbControlStatus, sleBridgePSFdbControlTimer, 
				sleBridgePSFdbControlTimeStamp, sleBridgePSFdbControlReqResult, sleBridgePSFdbControlPort, sleBridgePSFdbControlVid, sleErpDomainControlRingPriority, 
				sleErpDomainHoldOffTime, sleErpDomainRingPriority, sleErpDomainControlHoldOffTime, sleErpDomainControlLotp, sleErpDomainControlULotp, 
				sleErpDomainControlMultipleRM, sleErpDomainControlRMNodeReacheablility, sleBridgeFGBaseControlRequest, sleBridgeFGBaseSfgdEnabled, sleBridgeFGBaseMfgdEnabled, 
				sleBridgeFGBaseCfgdEnabled, sleBridgePSFdbControlMacAddress, sleBridgePortDhcpFilterServer, sleBridgePortControlDhcpFilterServer, sleBridgeFGBaseControlStatus, 
				sleBridgeFGBaseControlTimer, sleBridgeFGBaseControlTimeStamp, sleBridgeFGBaseControlReqResult, sleBridgeFGBaseControlCfgdEnable, sleBridgeFGBaseControlSfgdEnable, 
				sleBridgeFGPortControlRequest, sleBridgeFGPortControlStatus, sleBridgeFGPortControlTimer, sleBridgeFGPortControlTimeStamp, sleBridgeFGPortControlReqResult, 
				sleBridgeFGPortControlIndex, sleBridgeFGPortType, sleBridgeFGPortFrame, sleBridgeFGPortBlocked, sleBridgeFGPortTimer, 
				sleBridgeFGPortControlFrame, sleBridgeFGPortFrameType, sleBridgeFGPortControlBlock, sleBridgeAutoInterfaceActivation, sleBridgeControlAutoInterfaceActivation, 
				sleBridgeLoopDetectStatus, sleBridgeLoopDetectPacketType, sleBridgeControlLoopDetectStatus, sleBridgeControlLoopDetectPacketType, sleBridgePortLoopDetectStatus, 
				sleBridgePortLoopDetectBlock, sleBridgePortLoopDetectPeriod, sleBridgePortLoopDetectTimer, sleBridgePortLoopDetectBlockStatus, sleBridgePortControlLoopDetectStatus, 
				sleBridgePortControlLoopDetectBlock, sleBridgePortControlLoopDetectPeriod, sleBridgePortControlLoopDetectTimer, sleBridgePvlanPromSelectMode, sleBridgePvlanPromiscuousPorts, 
				sleBridgeControlPvlanPromSelectMode, sleBridgeControlPvlanPromiscuousPorts, sleBridgeVTServiceId, sleBridgeVTSubscriberId, sleBridgeVTRuleMac, 
				sleBridgeVTRuleVid, sleBridgeVTRuleRDirVid, sleBridgeVTRuleRDirPort, sleBridgeVTRuleStatus, sleBridgeVTControlRequest, 
				sleBridgeVTControlStatus, sleBridgeVTControlTimer, sleBridgeVTControlTimeStamp, sleBridgeVTControllReqResult, sleBridgeVTControlServerId, 
				sleBridgeVTControlClientId, sleBridgeGvrpStatus, sleBridgeGmrpStatus, sleBridgeGarpTimerJoin, sleBridgeGarpTimerLeave, 
				sleBridgeGarpTimerLeaveAll, sleBridgeGarpBaseControlRequest, sleBridgeGarpBaseControlStatus, sleBridgeGarpBaseControlTimer, sleBridgeGarpBaseControlTimeStamp, 
				sleBridgeGarpBaseControlReqResult, sleBridgeGarpBaseControlGvrpStatus, sleBridgeGarpBaseControlGmrpStatus, sleBridgeGarpBaseControlTimerJoin, sleBridgeGarpBaseControlTimerLeave, 
				sleBridgeGarpBaseControlTimerLeaveAll, sleBridgeGarpAppPortIndex, sleBridgeGarpAppPortType, sleBridgeGarpAppPortStatus, sleBridgeGarpAppPortFailedRegistrations, 
				sleBridgeGarpAppPortLastPduOrigin, sleBridgeGarpAppPortRegistration, sleBridgeGarpAppPortApplicant, sleBridgeGarpAppPortFwdAll, sleBridgeGarpAppPortTimerJoin, 
				sleBridgeGarpAppPortTimerLeave, sleBridgeGarpAppPortTimerLeaveAll, sleBridgeGarpAppPortControlRequest, sleBridgeGarpAppPortControlStatus, sleBridgeGarpAppPortControlTimer, 
				sleBridgeGarpAppPortControlTimeStamp, sleBridgeGarpAppPortControlReqResult, sleBridgeGarpAppPortControlIndex, sleBridgeGarpAppPortControlType, sleBridgeGarpAppPortControlPortStatus, 
				sleBridgeGarpAppPortControlRegistration, sleBridgeGarpAppPortControlApplicant, sleBridgeGarpAppPortControlFwdAll, sleBridgeGarpAppPortControlTimerJoin, sleBridgeGarpAppPortControlTimerLeave, 
				sleBridgeGarpAppPortControlTimerLeaveAll, sleBridgeGarpStatsJoinEmptyReceived, sleBridgeGarpStatsJoinInReceived, sleBridgeGarpStatsLeaveInReceived, sleBridgeGarpStatsLeaveEmptyReceived, 
				sleBridgeGarpStatsLeaveAllReceived, sleBridgeGarpStatsJoinInTransmitted, sleBridgeGarpStatsEmptyTransmitted, sleBridgeGarpStatsLeaveInTransmitted, sleBridgeGarpStatsLeaveEmptyTransmitted, 
				sleBridgeGarpStatsControlRequest, sleBridgeGarpStatstControlStatus, sleBridgeGarpStatsControlTimer, sleBridgeGarpStatsControlTimeStamp, sleBridgeGarpStatsControlReqResult, 
				sleBridgeGarpStatsControlIndex, sleBridgeGarpStatsControlType, sleBridgeGmrpStaticVid, sleBridgeGmrpStaticPort, sleBridgeGmrpStaticGmac, 
				sleBridgeGmrpStaticControlRequest, sleBridgeGmrpStaticControlStatus, sleBridgeGmrpStaticControlTimer, sleBridgeGmrpStaticControlTimeStamp, sleBridgeGmrpStaticControlReqResult, 
				sleBridgeGmrpStaticControlVid, sleBridgeGmrpStaticControlPort, sleBridgeGmrpStaticControlGmac, sleBridgePortNetBIOSFilter, sleBridgePortControlNetBIOSFilter, 
				sleBridgePortPopInnertag, sleBridgePortInnertag, sleBridgePortPriority, sleBridgePortControlPushInnertag, sleBridgePortControlPopInnertag, 
				sleBridgePortControlInnertag, sleBridgePortControlPriority, sleBridgePortPushInnertag, sleVlanInboundTagPortIndex, sleVlanInboundTagVlanIndex, 
				sleVlanInboundTagOuterVid, sleVlanInboundTagControlRequest, sleVlanInboundTagControlStatus, sleVlanInboundTagControlTimer, sleVlanInboundTagControlTimeStamp, 
				sleVlanInboundTagControlReqResult, sleVlanInboundTagControlPortIndex, sleVlanInboundTagControlVlanIndex, sleVlanInboundTagControlOuterVid, sleVlanOutboundTagPortIndex, 
				sleVlanOutboundTagControlRequest, sleVlanOutboundTagControlStatus, sleVlanOutboundTagControlTimer, sleVlanOutboundTagControlTimeStamp, sleVlanOutboundTagControlReqResult, 
				sleVlanOutboundTagControlPortIndex, sleVlanOutboundTagControlOuterVid, sleVlanOutboundTagVlanIndex, sleBridgePortInner2outerVid, sleBridgePortInner2outerPri, 
				sleBridgeFGPortControlFrameType, sleBridgeFGPortControlType, sleBridgeFGPortControlSetTimer, sleBridgeGarpStatsEmptyReceived, sleBridgeGarpStatsJoinEmptyTransmitted, 
				sleBridgeGarpStatsLeaveAllTransmitted, sleBridgePortControlInner2outerPri, sleBridgePortControlInner2outerVid }
			STATUS current
			DESCRIPTION 
				"Description."
			::= { sleBridge 28 }

		
		-- 1.3.6.1.4.1.6296.101.3.29
		sleBridgeNotificationGroup NOTIFICATION-GROUP
			NOTIFICATIONS { sleBridgeLacpProfileChanged, sleBridgeDoubleTagProtoIdChanged, sleBridgeMirrorProfileChanged, sleBridgeMaxLearnPerUnitChanged, sleBridgeFdbAgeingTimeChanged, 
				sleBridgeStackProfileChanged, sleBridgeLldpProfileChanged, sleBridgeStpProfileChagned, sleBridgeTcpSyncookieChanged, sleBridgeTcpIgnoreRstUnknownChanged, 
				sleBridgePortPVidChanged, sleBridgePortMaxHostsChanged, sleBridgePortMaxLearnPerUnitChanged, sleBridgePortMACFilterPermissionChanged, sleBridgePortMirrorProfileChanged, 
				sleBridgePortBcscThresholdProfileChanged, sleBridgePortQinQStatusChanged, sleBridgePortLinktypeChanged, sleBridgePortEdgemodeChanged, sleBridgePortStpBpduFilterChanged, 
				sleBridgePortPvlanIsolatedStatusChanged, sleVlanCreated, sleVlanDestroyed, sleVlanPortProfileChanged, sleVlanAgeingTimeChanged, 
				sleVlanMapFidChanged, sleVlanMapStpIdChanged, sleVlanMapErpDomainIdChanged, sleStpOperationModeChanged, sleStpConfigureProfileChanged, 
				sleStpTimerProfileChanged, sleStpBpduGuardProfileChanged, sleStpInstanceEnableChanged, sleStpInstanceConfigProfileChanged, sleStpInstancePortProfileChanged, 
				sleSubnetVlanCreated, sleSubnetVlanDestroyed, sleProtocolVlanCreated, sleProtocolVlanDestroyed, sleLagProfileChanged, 
				sleLagLacpPortProfileChanged, sleLagLacpPortAggreChanged, sleFdbEntryCreated, sleFdbEntryDestoryed, sleFdbTableEntriesCleared, 
				sleMfdbEntryCreated, sleMfdbEntryDestoryed, sleMfdbEntryPermissionChanged, sleMfdbEntryTableCleared, sleIgmpConfProfileChanged, 
				sleIgmpStaticMcastCreated, sleIgmpStaticMcastDestroyed, sleStackDeviceCreated, sleStackDeviceDestoryed, sleErpDomainCreated, 
				sleErpDomainDestroyed, sleErpDomainProfileChanged, sleErpProtectionActivationChanged, sleLldpPortProfileChanged, sleLldpStatisticsCleared, 
				sleBridgePSStatusChanged, sleBridgePSMaxCountChanged, sleBridgePSProfileChanged, sleBridgePSFdbEntryCreated, sleBridgePSFdbEntryDestroyed, 
				sleBridgePortStpBpduGuardErrRcvChanged, sleErpHoldOffTimeChanged, sleErpRingPriorityChanged, sleErpTrapChanged, sleBridgeFGBaseCfgdStatusChanged, 
				sleBridgeAutoInterfaceActivationChanged, sleBridgeFGPortUnblockChanged, sleBridgeFGPortProfileChanged, sleBridgeLoopDetectProfileChanged, sleBridgePortLoopDetectProfileChanged, 
				sleBridgePortLoopDetectUnblock, sleBridgePvlanPormSelectModeChanged, sleBridgeVTSet, sleBridgeVTClear, sleBridgeGarpStatusChanged, 
				sleBridgeGarpTimerChanged, sleBridgeGarpAppPortStatusChanged, sleBridgeGarpAppPortProfileChanged, sleBridgeGarpStatisticsCleared, sleBridgeGmrpStaticAdded, 
				sleBridgeGmrpStaticDeleted, sleBridgePortNetBIOSFilterChanged, sleBridgePortPriorityChanged, sleBridgePortInnertagChanged, sleBridgePortPopInnertagChanged, 
				sleBridgePortPushInnertagChanged, sleVlanInboundTagChanged, sleVlanOutboundTagSet, sleVlanOutboundTagClear, sleBridgePortInner2outerVidChanged, 
				sleBridgePortInner2outerPriChanged, sleBridgePSFdbEntryCleared, sleBridgePortDhcpFilterServerChanged, sleBridgeFGBaseSfgdStatusChanged }
			STATUS current
			DESCRIPTION 
				"Description."
			::= { sleBridge 29 }

		
	
	END

--
-- SLE-BRIDGE-MIB.my
--
