CSI-BB2-BACNET-MIB 
-- ******************************************************
--Control Solutions, Inc., SNMP  MIB
--Prefix for private enterprises:  1.3.6.1.4.1	
--Control Solutions, Inc. private enterprize number:  3815
--
-- The following MIB is the definition of the SNMP based implementation
-- found in Control Solutions BACnet IP gateways.
--
--
-- ************************************************************

DEFINITIONS ::= BEGIN

IMPORTS  
	MODULE-IDENTITY, OBJECT-TYPE, Integer32, NOTIFICATION-TYPE 
		FROM SNMPv2-SMI
	MODULE-COMPLIANCE, OBJECT-GROUP, NOTIFICATION-GROUP
		FROM SNMPv2-CONF
 	bacnet, bb2-7010, bb2-7010-reg-v1 
		FROM Control-Solutions-MIB-Registrations;


bbipxModule MODULE-IDENTITY
	LAST-UPDATED "201510290000Z"
	ORGANIZATION "Control Solutions, Inc."
	CONTACT-INFO
		"Jim Hogenson
		Control Solutions, Inc.
		380 Oak Grove Pkwy, Suite 100
		PO Box 10789
		St. Paul, MN 55110
		jimhogenson@csimn.com
		Voice: 651-426-4410
		Fax: 651-426-4418"
	DESCRIPTION
		"The following MIB is the definition of SNMP access to
		Babel Buster models BB2-7010-02 and BB2-7030-02."
	REVISION "200812020000Z"
	DESCRIPTION
		"Initial draft."
	REVISION "201510290000Z"
	DESCRIPTION
		"Trap objects not previously declared correctly, 
		has been corrected. Also updated registration tree
		to reflect current product line."
	::= { bb2-7010-reg-v1 1 }


          -- textual conventions

          DisplayString ::=
              OCTET STRING
          -- This data type is used to model textual information taken
          -- from the NVT ASCII character set.  By convention, objects
          -- with this syntax are declared as having
          --
          --      SIZE (0..255)

-- Major object categories for Babel Buster BB2-7010

dataRegs	OBJECT IDENTIFIER ::= { bb2-7010 1 }  	-- 3815.1.3.1.1

-- ******************************************************
--
-- INTEGER DATA REGISTER TABLE (first int is 1.3.6.1.4.1.3815.1.3.1.1.1.2.1)
-- 
-- ******************************************************

dataRegTable OBJECT-TYPE
	SYNTAX	SEQUENCE OF DataRegEntry
	MAX-ACCESS	not-accessible
	STATUS	current
	DESCRIPTION
		"Integer data register table."
	::= { dataRegs 1 }

dataRegEntry OBJECT-TYPE
	SYNTAX	DataRegEntry
	MAX-ACCESS	not-accessible
	STATUS	current
	DESCRIPTION
		"Integer data register table entry."
	INDEX	{ dataRegIndex }
	::= { dataRegTable 1 }

DataRegEntry ::= SEQUENCE {
	dataRegIndex		INTEGER,
	dataRegRegister		Integer32,
	dataRegName			DisplayString
	}

dataRegIndex OBJECT-TYPE
	SYNTAX	INTEGER (1..65536) 
	MAX-ACCESS	not-accessible
	STATUS	current
	DESCRIPTION
		"Register number, index into integer data register table."
	::= { dataRegEntry 1 }

dataRegRegister OBJECT-TYPE
	SYNTAX	Integer32
	MAX-ACCESS	read-write
	STATUS	current
	DESCRIPTION
		"Register's data value."
	::= { dataRegEntry 2 }

dataRegName OBJECT-TYPE
	SYNTAX	DisplayString (SIZE(0..40))
	MAX-ACCESS	read-only
	STATUS	current
	DESCRIPTION
		"Register's name."
	::= { dataRegEntry 3 }

-- ******************************************************
--
-- SIMPLE I/O FOR SNMP NOTIFICATIONS
-- 
-- ******************************************************

bacnetTrapPrefix	OBJECT IDENTIFIER ::= { bb2-7010 2 }
bacnetTraps			OBJECT IDENTIFIER ::= { bacnetTrapPrefix 0 }

eventStateChange	NOTIFICATION-TYPE
	OBJECTS {
		dataRegRegister,
		dataRegName
	}
	STATUS	 	current
	DESCRIPTION
		"This trap is sent when a register changes value
		if notifications are enabled for the object that changed."
	::= { bacnetTraps 1 }

-- ******************************************************
--
-- SIMPLE I/O FOR SNMP COMPLIANCE
-- 
-- ******************************************************

bacnetConformance	OBJECT IDENTIFIER ::= { bb2-7010 3 }

bacnetGroups			OBJECT IDENTIFIER ::= { bacnetConformance 1 }
bacnetCompliances 	    OBJECT IDENTIFIER ::= { bacnetConformance 2 }

bbipxCompliance MODULE-COMPLIANCE
	STATUS 	current
	DESCRIPTION
		"The compliance statement for SNMPv2 entities which
		implement the agent supported by the Babel Buster X2 core."
	MODULE
	MANDATORY-GROUPS
		{ bacnetDataRegIntGroup }
	::= { bacnetCompliances 1 }

bacnetDataRegIntGroup	OBJECT-GROUP
	OBJECTS {
		dataRegRegister,
		dataRegName
	}
	STATUS 	current
	DESCRIPTION
		"Group of objects that define gateway data registers."
	::= { bacnetGroups 1 }

bacnetNotificationGroup	NOTIFICATION-GROUP
	NOTIFICATIONS { 
		eventStateChange 
	}
	STATUS current
	DESCRIPTION
		"Group of objects that define notifications."
	::= { bacnetGroups 2 }

END
