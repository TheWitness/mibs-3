--
-- she-system-mib.mib
-- MIB generated by MG-SOFT Visual MIB Builder Version 6.0  Build 88
-- Wednesday, May 28, 2008 at 15:39:41
--

-- Start of ClearCase branch-information of current release:
-- she-system-mib.mib   /main/she_main_grf/21
-- End of ClearCase branch-information.

	DS-SHE-SYSTEM-MIB DEFINITIONS ::= BEGIN
 
		IMPORTS
			she			
				FROM AN-MIB
			dsShe
				FROM DASAN-SMI							
			entPhysicalIndex, PhysicalIndex			
				FROM ENTITY-MIB			
			sheAlarmTimeAndDate, sheAlarmReportingSource, sheAlarmReportingSourceType, sheAlarmSeverity			
				FROM DS-SHE-ALARMING-MIB			
			SheControlStatusType, SheCardType, SheSystemFileIndexType			
				FROM DS-SHE-TC-MIB			
			OBJECT-GROUP, MODULE-COMPLIANCE, NOTIFICATION-GROUP			
				FROM SNMPv2-CONF    
			DateAndTime
				FROM SNMPv2-TC
			InetAddressType, InetAddress
				FROM INET-ADDRESS-MIB			
			TimeTicks, IpAddress, Integer32, Unsigned32, Gauge32, 
			OBJECT-TYPE, MODULE-IDENTITY, NOTIFICATION-TYPE			
				FROM SNMPv2-SMI			
			DisplayString, TruthValue, TEXTUAL-CONVENTION			
				FROM SNMPv2-TC;
	
	
--  1.3.6.1.4.1.231.7.1.2.2.1.2
		sheSystem MODULE-IDENTITY 
			LAST-UPDATED "200805281300Z"		-- May 28, 2008 at 13:00 GMT
			ORGANIZATION 
				"Nokia Siemens Networks"
			CONTACT-INFO 
				"Gerd Barchmann
				COO BBA DSLAM RD SDE
				
				gerd.barchmann@nsn.com
				+49 3834 555654"
			DESCRIPTION 
				" Definition of system global information and configuration,
				e.g. configuration of external time, snmp configuration
				file management for up and download of 
				- loads, 
				- configuration files
				- errorlog
				- remote inventory
				- performance data file
				- snmp configuration file
				"
			REVISION "200410071000Z"		-- October 07, 2004 at 10:00 GMT
			DESCRIPTION 
				"Add managed objects as to TimeZone"
			REVISION "200411241439Z"		-- November 24, 2004 at 14:39 GMT
			DESCRIPTION 
				"IUS Release 2. Correct access for
				sheSystemControlExternalTime."
			REVISION "200412081000Z"		-- December 08, 2004 at 10:00 GMT
			DESCRIPTION 
				"Change Description for sheSystemVersion."
			REVISION "200412201413Z"		-- December 20, 2004 at 14:13 GMT
			DESCRIPTION 
				"Change the description for the possible values of sheSystemVersion string."
			REVISION "200608221505Z"		-- August 22, 2006 at 15:05 GMT
			DESCRIPTION 
				"Take over by Gerd Barchmann for R2.5."
			REVISION "200609131512Z"		-- September 13, 2006 at 15:12 GMT
			DESCRIPTION 
				"Correct description for some sheSystemConfigLogFtp - parameters.
				Username and password could never be readout via snmp if.
				Correct spelling of variables in sheSystemSwmControl."
			REVISION "200611201222Z"		-- November 20, 2006 at 12:22 GMT
			DESCRIPTION 
				"Correct some names and definitions for backward compatibility.
				Add ControlReqResult and ControlReqStatus to sheSystemConfigLogControl. 
				Correct SheSystemDnsServerNameControlRequestType."
			REVISION "200612061203Z"		-- December 06, 2006 at 12:03 GMT
			DESCRIPTION 
				"Add group sheSystemAutoConfigBackup for backward compatibility. Will not be supported by R2.5."
			REVISION "200701120952Z"		-- January 12, 2007 at 09:52 GMT
			DESCRIPTION 
				"Add new system-version string."
			REVISION "200703301055Z"		-- March 30, 2007 at 10:55 GMT
			DESCRIPTION 
				"Add new system-version string for R2.5.2.
				Add new tables for configuration of IP host and static routes
				via snmp."
			REVISION "200704161524Z"		-- April 16, 2007 at 15:24 GMT
			DESCRIPTION 
				"Expand sheSystemFileControlTypeOfFile for alarmLog and uptimeLog."
			REVISION "200704251330Z"		-- April 25, 2007 at 13:30 GMT
			DESCRIPTION 
				"Modify SheSystemIpHostTable after late review comment."
			REVISION "200705111256Z"		-- May 11, 2007 at 12:56 GMT
			DESCRIPTION 
				"Modify sheSystemIpHostTable and change ..Usage attribute to ..Description."
			REVISION "200705241036Z"		-- May 24, 2007 at 10:36 GMT
			DESCRIPTION 
				"Remove index limits for IpHost- and IpRoute-table."
			REVISION "200706111601Z"		-- June 11, 2007 at 16:01 GMT
			DESCRIPTION 
				"Replace system-version string R2.5.2 with R2.6."
			REVISION "200708151046Z"		-- August 15, 2007 at 10:46 GMT
			DESCRIPTION 
				"Modify unit and range for sheSystemNtpClientXmitInterval and sheSystemNtpClientControlXmitInterval."
			REVISION "200710161349Z"		-- October 16, 2007 at 13:49 GMT
			DESCRIPTION 
				"Add new system version R2.7 and R2.8."
			REVISION "200711141534Z"		-- November 14, 2007 at 15:34 GMT
			DESCRIPTION 
				"Add new system version hiX5622/R1.0.
				Modify comment for sheSystemIpHostUseDhcp."
			REVISION "200711271040Z"		-- November 27, 2007 at 10:40 GMT
			DESCRIPTION 
				"Add systemversion string for R3.0."
			REVISION "200712051242Z"		-- December 05, 2007 at 12:42 GMT
			DESCRIPTION 
				"Add metric parameter to interface route table (CO hiX13598)."
			REVISION "200802221125Z"		-- February 22, 2008 at 11:25 GMT
			DESCRIPTION 
				"Correct missing Object list for swm externalFtpAccessAlarm."
			REVISION "200804091448Z"		-- April 09, 2008 at 14:48 GMT
			DESCRIPTION 
				"Expand valid range for TimeZone configuration."
			REVISION "200805141009Z"		-- May 14, 2008 at 10:09 GMT
			DESCRIPTION 
				"Add new system version string for R2.6S2, R2.7M and R2.8M."
			REVISION "200805281534Z"		-- May 28, 2008 at 15:34 GMT
			DESCRIPTION 
				"Modify valid values for Timezone configuration."
			::= { dsShe 2 }

		
	
--
-- Type definitions
--
	
--  --------------------------------------------------------------
-- Commands
-- --------------------------------------------------------------
-- This type specifies the user commands (control requests) for
-- system maintenance from the TMN-OS or LCT.
		SheSystemMaintenanceControlReq ::= INTEGER
			{
			noRequest(1),
			setSystemMaintenanceBase(50),
			setSwmAdminState(51),
			swmUpgrStartRequest(100),
			swmUpgrStartRequestNoReset(101),
			swmReadSAPSContentFile(102), 
			swmSetUpgrInterval(103),
			backupDb(200),
			refreshDbBackupFilesTable(201),
			dbReloadSpecificFile(202),
			setBackupPeriod(203),
			setLocalBackupAdminState(204),
			setRemoteBackupAdminState(205)
			}

--  --------------------------------------------------------------
-- Result
-- --------------------------------------------------------------
-- This type specifies the command results (controlReqResult) 
-- for the system maintenance to TMN-OS or LCT.
-- 
		SheSystemMaintenanceControlReqResult ::= INTEGER
			{
			noRequest(1),
			ftpIpAddrFailed(11),
			ftpAccountFailed(12),
			ftpPasswdFailed(13),
			ftpDescPathFailed(14),
			commExecStarted(30),
			paramFaulty(31),
			requestBusy(32),
			setDataFailed(34),
			aswTimeout(35),
			commandFailed(36),
			commandSucceeded(37),
			sucUpgrTaskCreationFault(51),
			sucUpgrDbAccessFault(52),
			sucUpgrMissParameter(54),
			sucAlreadyLoaded(55),
			sucOk(60),
			sucNotOk(61),
			sucDbAccessFailed(62),
			sucCardUnlocked(63),
			sucTransmissionError(64),
			sucWrongSwVersion(65),
			sucUnitTypeMismatch(66),
			sucFtpTransError(67),
			sucFtpCrcError(68),
			sucSwHwMismatch(69),
			sucUpgrWrongAvState(70),
			sucFepromCopyFault(71),
			sucUpdateDescFileFailed(72),
			sucFtpServerNoteAvailable(73),
			sucFtpSendError(74),
			sucDbBackupFault(75),
			sucUpgradeComplete(76),
			sucUpgradeNotComplete(77),
			sutInitialized(100),
			sutToDo(101),
			sutStarted(102),
			sutCrashed(103),
			sutFtpDone(104),
			sutDone(105),
			sutReadyForReset(106),
			sutObsolete(107),
			sutResetInProgress(108),
			localBackupOk(150),
			remoteBackupOk(151),
			localBackupFailed(152),
			remoteBackupFailed(153),
			flashAccessFailed(154),
			dbReadFailed(155),
			dbmLocalBackupOk(170),
			dbmRemoteBackupOk(171),
			dbmLocalBackupFailed(172),
			dbmRemoteBackupFailed(173),
			dbmFlashAccessFailed(174),
			dbmDbReadFailed(175),
			dbmLocalBackupFileFaulty(176),
			dbmRemoteBackupFileFaulty(177),
			dbmRestoreFailed(178),
			dbmRestoreOk(179),
			dbmRefreshFailed(180),
			dbmRefreshOk(181)
			}

--  The administrative state of an entity.
		SheSystemAdminState ::= INTEGER
			{
			unlocked(1),
			locked(2)
			}

		SheSystemIpControlReqType ::= INTEGER
			{
			createSystemIpHost(50),
			deleteSystemIpHost(51),
			modifySystemIpHost(52),
			createSystemIpRoute(55),
			deleteSystemIpRoute(56),
			modifySystemIpRoute(57),
			modifySystemIpTtl(58)
			}

	
--
-- Textual conventions
--
	
--  Textual conventions
-- 
-- type of startup                    
		SheSystemStartupType ::= TEXTUAL-CONVENTION
			STATUS current
			DESCRIPTION 
				"The startup type."
			SYNTAX INTEGER
				{
				resetSystem(1),
				resetSystemWithDefault(2)
				}

--   -----------------------------------------------------------------
-- Textual Conventions
-- -----------------------------------------------------------------
		SheSystemTmnConnectedType ::= TEXTUAL-CONVENTION
			STATUS current
			DESCRIPTION 
				" TMN Connected type."
			SYNTAX INTEGER
				{
				connected(1),
				disconnected(2)
				}

		SheSystemControlRequestType ::= TEXTUAL-CONVENTION
			STATUS current
			DESCRIPTION 
				"The type for system control commands."
			SYNTAX INTEGER
				{
				configureTime(1),
				tmnConnect(2),
				tmnDisconnect(3),
				lctConnect(4),
				lctDisconnect(5),
				writeDatatoFlash(6),
				configureTimeZone(7),
				setCPUThreshold(8),
				setMemoryThreshold(9),
				setTemperatureThreshold(10),
				setHostname(11),
				reloadSystem(12)
				}

--   GENERAL VALUES FOR USER COMMAND HANDLING
-- RETURN VALUES
		SheSystemControlRequestResultType ::= TEXTUAL-CONVENTION
			STATUS current
			DESCRIPTION 
				"The result type for system control commands."
			SYNTAX INTEGER
				{
				commExecStarted(30),
				paramFaulty(31),
				requestBusy(32),
				setDataFailed(34),
				aswTimeout(35),
				commandFailed(36),
				commandSucceeded(37),
				featureNotSupportedbyRelease(41)
				}

--   type of threshold interval
		SheSystemThresholdIntervalType ::= TEXTUAL-CONVENTION
			STATUS current
			DESCRIPTION 
				"The sampling interval for system threshold"
			SYNTAX INTEGER
				{
				sec5(1),
				sec60(2),
				sec600(3)
				}

--   return values to be defined
-- GENERAL VALUES FOR USER COMMAND HANDLING
-- RETURN VALUES
		SheSystemFileControlRequestType ::= TEXTUAL-CONVENTION
			STATUS current
			DESCRIPTION 
				"The type for file  control commands."
			SYNTAX INTEGER
				{
				upload(1),
				download(2),
				uploadCardsAllOfType(3),
				downloadCardsAllOfType(4),
				writeImage(5)
				}

-- GENERAL VALUES FOR USER COMMAND HANDLING RETURN VALUES
		SheSystemFileControlRequestResultType ::= TEXTUAL-CONVENTION
			STATUS current
			DESCRIPTION 
				"The result type for file  control commands."
			SYNTAX INTEGER
				{
				ftpError(10),
				ftpIpAddrFailed(11),
				ftpAccountFailed(12),
				ftpPasswdFailed(13),
				ftpDescPathFailed(14),
				swLoadPromotionFailed(20),
				commExecStarted(30),
				paramFaulty(31),
				requestBusy(32),
				setDataFailed(34),
				aswTimeout(35),
				commandFailed(36),
				commandSucceeded(37)
				}

-- Type definition for file management
		SheSystemTypeOfFile ::= TEXTUAL-CONVENTION
			STATUS current
			DESCRIPTION 
				"The type of files which can be managed."
			SYNTAX INTEGER
				{
				storedLoad(1),
				errorLog(2),
				restoreFile(3),
				remoteInventory(4),
				performanceData(5),
				alarmLog(6),
				uptimeLog(7)
				}

--   the load status type       
		SheSystemFileLoadStatusType ::= TEXTUAL-CONVENTION
			STATUS current
			DESCRIPTION 
				"The load status type."
			SYNTAX INTEGER
				{
				finished(1),
				running(2),
				broken(3)
				}

--  return values to be defined
-- GENERAL VALUES FOR USER COMMAND HANDLING
-- RETURN VALUES
		SheSystemNtpClientControlRequestType ::= TEXTUAL-CONVENTION
			STATUS current
			DESCRIPTION 
				"The type for NtpClient control commands."
			SYNTAX INTEGER
				{
				enableNtpClient(1),
				disableNtpClient(2),
				changeNtpClientXmitInterval(3),
				addNtpClientServerName(4),
				deleteNtpClientServerName(5)
				}

--   GENERAL VALUES FOR USER COMMAND HANDLING
-- RETURN VALUES
		SheSystemNtpClientControlRequestResultType ::= TEXTUAL-CONVENTION
			STATUS current
			DESCRIPTION 
				"The result type for file  control commands."
			SYNTAX INTEGER
				{
				noRequest(1),
				commExecStarted(30),
				paramFaulty(31),
				requestBusy(32),
				setDataFailed(34),
				aswTimeout(35),
				commandFailed(36),
				commandSucceeded(37),
				ntpClientEnableErr(50),
				ntpClientDisableErr(51),
				ntpClientChangeXmitIntervalErr(52),
				ntpClientServerNameAddErr(53),
				ntpClientServerNameDelErr(54)
				}

--  return values to be defined
-- GENERAL VALUES FOR USER COMMAND HANDLING
-- RETURN VALUES
		SheSystemDnsServerControlRequestType ::= TEXTUAL-CONVENTION
			STATUS current
			DESCRIPTION 
				"The type for DNS Server control commands."
			SYNTAX INTEGER
				{
				addedDnsServerName(1),
				deletedDnsServerName(2)
				}

--   GENERAL VALUES FOR USER COMMAND HANDLING
-- RETURN VALUES
		SheSystemDnsServerControlRequestResultType ::= TEXTUAL-CONVENTION
			STATUS current
			DESCRIPTION 
				"The result type for file  control commands."
			SYNTAX INTEGER
				{
				noRequest(1),
				commExecStarted(30),
				paramFaulty(31),
				requestBusy(32),
				setDataFailed(34),
				aswTimeout(35),
				commandFailed(36),
				commandSucceeded(37),
				dnsServerIpAddErr(60),
				dnsServerIpDelErr(61)
				}

--   type of Management Session                               
		SheSystemManagementSessionType ::= TEXTUAL-CONVENTION
			STATUS current
			DESCRIPTION 
				"Management Session Type."
			SYNTAX INTEGER
				{
				telnet(1),
				snmp(2),
				ssh(3),
				console(4)
				}

--   ManagementSessionControl Request
		SheSystemManagementSessionControlRequestType ::= TEXTUAL-CONVENTION
			STATUS current
			DESCRIPTION 
				"Management Session global user commands."
			SYNTAX INTEGER 
				{ 
				setSnmpSessionAgingTime(1),
				setSnmpSessionServiceLimit(2),
				setSnmpSessionServicePort(3)
				}

--   GENERAL VALUES FOR USER COMMAND HANDLING
-- ManagementSessionControl Return values
		SheSystemManagementSessionControlReqResultType ::= TEXTUAL-CONVENTION
			STATUS current
			DESCRIPTION 
				"The result type for Management Session control commands."
			SYNTAX INTEGER
				{
				noRequest(1),
				commExecStarted(30),
				paramFaulty(31),
				requestBusy(32),
				setDataFailed(34),
				aswTimeout(35),
				commandFailed(36),
				commandSucceeded(37),
				setAgingTimeFailed(60),
				setSessionServiceLimitFailed(61),
				setSessionServicePortFailed(62)
				}

--   ConfigLogControl Request
		SheSystemConfigLogControlRequestType ::= TEXTUAL-CONVENTION
			STATUS current
			DESCRIPTION 
				"Config Log control commands."
			SYNTAX INTEGER
				{
				setConfigLogEntryNumber(1),
				setFtpAccount(2),
				setFtpInterval(3)
				}

--   AutoConfigBackupControl Request
		SheSystemAutoConfigBackupControlRequest ::= TEXTUAL-CONVENTION
			STATUS current
			DESCRIPTION 
				"AutoConfig Backup control commands."
			SYNTAX INTEGER
				{
				setAutoConfigBackupEnabled(1),
				setFtpAccount(2),
				setBackupTimerval(3)
				}

--   type of active load                               
		SheSystemLoadType ::= TEXTUAL-CONVENTION
			STATUS current
			DESCRIPTION 
				"The load type."
			SYNTAX INTEGER
				{
				active(1),
				passive(2)
				}

		SheSystemStartupResultType ::= TEXTUAL-CONVENTION
			STATUS current
			DESCRIPTION 
				"Result of the last NE startup. "
			SYNTAX INTEGER
				{
				startupInProgress(1),
				startupFailed(2),
				startupFinished(3)
				}

		SheSystemIpHostUseDhcpType ::= TEXTUAL-CONVENTION
			STATUS current
			DESCRIPTION 
				"Either use DHCP or fixed IP address."
			SYNTAX INTEGER
				{
				noUseDhcp(0),
				useDhcp(1)
				}

	
--
-- Node definitions
--
	
--  Node definitions
-- 
-- MIB contains the following groups
-- 1.3.6.1.4.1.231.7.1.2.2.1.2.1
		sheSystemInfo OBJECT IDENTIFIER ::= { sheSystem 1 }

		
--   -----------------------------------------------------------------
-- System general information group
-- -----------------------------------------------------------------
-- 1.3.6.1.4.1.231.7.1.2.2.1.2.1.1
		sheSystemVersion OBJECT-TYPE
			SYNTAX DisplayString
			MAX-ACCESS read-only
			STATUS current
			DESCRIPTION
				"Contains the version of the net element.
				hiX5625/R2.5 
				hiX5630/R2.5 
				hiX5635/R2.5 
				hiX5625/R2.5.1 
				hiX5630/R2.5.1 
				hiX5635/R2.5.1 
				hiX5625/R2.6 
				hiX5630/R2.6 
				hiX5635/R2.6
				hiX5625/R2.7 
				hiX5630/R2.7 
				hiX5635/R2.7
				hiX5625/R2.8 
				hiX5630/R2.8 
				hiX5635/R2.8
				hiX5622/R1.0
				hiX5625/R3.0 
				hiX5630/R3.0 
				hiX5635/R3.0
				hiX5625/R2.6S2 
				hiX5630/R2.6S2 
				hiX5635/R2.6S2
				hiX5625/R2.7M 
				hiX5630/R2.7M 
				hiX5635/R2.7M
				hiX5625/R2.8M 
				hiX5630/R2.8M
				hiX5635/R2.8M
				The used shelftype could be retrieved from shePhysShelfTable."
			::= { sheSystemInfo 1 }

		
--   seabrigde has several flags in the system mib:
-- systemState : normal, upgrade
-- systemUpgradeState : upgrade-preparation, idle, ready-for-switchover
-- 1.3.6.1.4.1.231.7.1.2.2.1.2.1.2
		sheSystemExternalTime OBJECT-TYPE
			SYNTAX TimeTicks
			MAX-ACCESS read-only
			STATUS current
			DESCRIPTION
				"The external time of the net element (UTC).
				The TMN-OS should set this time after first time power up or system resets
				and should refresh it once a day. "
			::= { sheSystemInfo 2 }

		
--  1.3.6.1.4.1.231.7.1.2.2.1.2.1.3
		sheSystemStartupType OBJECT-TYPE
			SYNTAX SheSystemStartupType
			MAX-ACCESS read-only
			STATUS current
			DESCRIPTION
				" Startup type: 
				1..resetSystem
				2..resetSystemWithDefault
				"
			::= { sheSystemInfo 3 }

		
--  1.3.6.1.4.1.231.7.1.2.2.1.2.1.4
		sheSystemTmnConnected OBJECT-TYPE
			SYNTAX SheSystemTmnConnectedType
			MAX-ACCESS read-only
			STATUS current
			DESCRIPTION
				"  The value connected indicates that a manager has received 
				the trap sheSytemStartupEnd and has connected. "
			::= { sheSystemInfo 4 }

		
--  1.3.6.1.4.1.231.7.1.2.2.1.2.1.5
		sheSystemLctConnected OBJECT-TYPE
			SYNTAX SheSystemTmnConnectedType
			MAX-ACCESS read-only
			STATUS current
			DESCRIPTION
				"  The value connected indicates that a manager has connected as LCT. 
				SHE sends the trap sheSystemLctConnected to all known
				TMN systems to inform whether the LCT session has been setup or terminated. "
			::= { sheSystemInfo 5 }

		
--   -----------------------------------------------------------------
-- System feature capability table
-- -----------------------------------------------------------------
-- 1.3.6.1.4.1.231.7.1.2.2.1.2.1.6
		sheSystemFeatureCapabilityTable OBJECT-TYPE
			SYNTAX SEQUENCE OF SheSystemFeatureCapabilityEntry
			MAX-ACCESS not-accessible
			STATUS current
			DESCRIPTION
				" The alarm severity table.
				The alarm severity table associates
				profile index and AlarmID pairs with severities to be
				used for alarm traps.
				(Note that this table does not apply to cleared alarms). "
			::= { sheSystemInfo 6 }

		
--  1.3.6.1.4.1.231.7.1.2.2.1.2.1.6.1
		sheSystemFeatureCapabilityEntry OBJECT-TYPE
			SYNTAX SheSystemFeatureCapabilityEntry
			MAX-ACCESS not-accessible
			STATUS current
			DESCRIPTION
				" Entry of the sheSystemFeatureCapabilityTable. "
			INDEX { sheSystemFeatureIndex }
			::= { sheSystemFeatureCapabilityTable 1 }

		
		SheSystemFeatureCapabilityEntry ::=
			SEQUENCE { 
				sheSystemFeatureIndex
					Unsigned32,
				sheSystemFeatureName
					DisplayString
			 }

--  1.3.6.1.4.1.231.7.1.2.2.1.2.1.6.1.1
		sheSystemFeatureIndex OBJECT-TYPE
			SYNTAX Unsigned32 (1..65535)
			MAX-ACCESS read-only
			STATUS current
			DESCRIPTION
				" The system feature index. "
			::= { sheSystemFeatureCapabilityEntry 1 }

		
--  1.3.6.1.4.1.231.7.1.2.2.1.2.1.6.1.2
		sheSystemFeatureName OBJECT-TYPE
			SYNTAX DisplayString
			MAX-ACCESS read-only
			STATUS current
			DESCRIPTION
				" The system feature name. "
			::= { sheSystemFeatureCapabilityEntry 2 }

		
--   -----------------------------------------------------------------
-- System control group
-- -----------------------------------------------------------------
-- 1.3.6.1.4.1.231.7.1.2.2.1.2.1.7
		sheSystemControl OBJECT IDENTIFIER ::= { sheSystemInfo 7 }

		
--  1.3.6.1.4.1.231.7.1.2.2.1.2.1.7.1
		sheSystemControlRequest OBJECT-TYPE
			SYNTAX SheSystemControlRequestType
			MAX-ACCESS read-write
			STATUS current
			DESCRIPTION
				"  System commands :
				configureTime : 
				   The command to configure the external time.
				tmnConnect :
				    the command for a manager to connect in order to be allowed
				    to manage the SHE and to stop the NE sending the sheSystemStartupEnd trap.
				tmnDisconnect:
				    the command for a TMN to disconnect from the NE. 
				lctConnect :
				    the command for a manager to connect as a LCT.
				    The SHE then sends the sheSystemLctSession trap.
				lctDisconnect:
				    the command for a LCT to disconnect from the NE.
				    The SHE then sends the sheSystemLctSession trap. 
				    If a LCT does not disconnect a LCT session is automatically
				    disconnected by the SHE after a internal timer expired.
				writeDatatoFlash:
				    the command to start writing configuration data of all subsystems
				    to flash-memory (long running command).
				configureTimeZone:
				    the command to change the current timezone.
				setCPUThreshold:
					the command to configure the threshold that
					when CPU usage exceeds the certain limit, notification is sent.
				setMemoryThreshold:
					the command to configure the threshold that
					when Memory usage exceeds the certain limit, notification is sent. 
				setTemperatureThreshold:
					the command to configure the threshold that
					when temperature exceeds the certain limit, notification is sent 
				setHostname:
					the command to configure the hostname.  
				reloadOS
					the command to reload the system with the specific OS. 

					
				Notifications : 
				    sheSystemStartupEnd, sheSystemLctSession, sheSystemWriteDatatoFlashFinished,
				    sheSystemChangedCPULoadThreshold, sheSystemChangedMemoryThreshold,
				    sheSystemChangedTemperatureThreshold, sheSystemChangedHostname.
				"
			::= { sheSystemControl 1 }

		
--  1.3.6.1.4.1.231.7.1.2.2.1.2.1.7.2
		sheSystemControlStatus OBJECT-TYPE
			SYNTAX SheControlStatusType
			MAX-ACCESS read-only
			STATUS current
			DESCRIPTION
				" The status of a control request. "
			::= { sheSystemControl 2 }

		
--  1.3.6.1.4.1.231.7.1.2.2.1.2.1.7.3
		sheSystemControlTimer OBJECT-TYPE
			SYNTAX Unsigned32
			MAX-ACCESS read-only
			STATUS current
			DESCRIPTION
				" The maximum wait time for the manager for command ending.
				For long running commands.
				The manager reads this value from the SHE. "
			::= { sheSystemControl 3 }

		
--  1.3.6.1.4.1.231.7.1.2.2.1.2.1.7.4
		sheSystemControlReqResult OBJECT-TYPE
			SYNTAX SheSystemControlRequestResultType
			MAX-ACCESS read-only
			STATUS current
			DESCRIPTION
				" The result of the last user command. "
			::= { sheSystemControl 4 }

		
--  1.3.6.1.4.1.231.7.1.2.2.1.2.1.7.5
		sheSystemControlTimeStamp OBJECT-TYPE
			SYNTAX Unsigned32
			UNITS "sec"
			MAX-ACCESS read-only
			STATUS current
			DESCRIPTION
				" The time stamp of the last command (end of command). "
			::= { sheSystemControl 5 }

		
--  1.3.6.1.4.1.231.7.1.2.2.1.2.1.7.6
		sheSystemControlExternalTime OBJECT-TYPE
			SYNTAX TimeTicks
			MAX-ACCESS read-write
			STATUS current
			DESCRIPTION
				"The external time of the net element (UTC).
				The manager should set this time after first time power up or resetSystem
				and should refresh it once a day. "
			::= { sheSystemControl 6 }

		
--  1.3.6.1.4.1.231.7.1.2.2.1.2.1.7.7
		sheSystemControlTimeZone OBJECT-TYPE
			SYNTAX OCTET STRING (SIZE (0..16))
			MAX-ACCESS read-write
			STATUS current
			DESCRIPTION
				"The Time Zone of the net element.
				The TMN-OS should set this time zone in front of the NE's external time. 
				UTC,
				UTC+1,
				UTC+2,
				UTC+3,
				UTC+3.30,
				UTC+4,
				UTC+4.30,
				UTC+5,
				UTC+5.30,
				UTC+5.45,
				UTC+6,
				UTC+6.30,
				UTC+7,
				UTC+8,
				UTC+8.45,
				UTC+9,
				UTC+9.30,
				UTC+10,
				UTC+10.30,
				UTC+11,
				UTC+11.30,
				UTC+12,
				UTC+12.45,
				UTC+13,
				UTC+14,
				UTC-1,
				UTC-2,
				UTC-2.30,
				UTC-3,
				UTC-3.30,
				UTC-4,
				UTC-4.30,
				UTC-5,
				UTC-6,
				UTC-7,
				UTC-8,
				UTC-9,
				UTC-9.30,
				UTC-10,
				UTC-11,
				UTC-12,
				
				An automatic DST (dayligth saving time) switchover is not supported by the NE!!"
			::= { sheSystemControl 7 }

		
--  1.3.6.1.4.1.231.7.1.2.2.1.2.1.7.8
		sheSystemControlCPUThreshold OBJECT-TYPE
			SYNTAX Integer32 (20..100)
			UNITS "%"
			MAX-ACCESS read-write
			STATUS current
			DESCRIPTION
				" The CPU Load Threshold of System.
				The manager should set this threshold about CPU Load. "
			::= { sheSystemControl 8 }

		
--  1.3.6.1.4.1.231.7.1.2.2.1.2.1.7.9
		sheSystemControlCPUThresholdInterval OBJECT-TYPE
			SYNTAX SheSystemThresholdIntervalType
			MAX-ACCESS read-write
			STATUS current
			DESCRIPTION
				" The sampling interval for CPU threshold.
				Average CPU usage is checked on every interval configured. "
			::= { sheSystemControl 9 }

		
--  1.3.6.1.4.1.231.7.1.2.2.1.2.1.7.10
		sheSystemControlMemoryThreshold OBJECT-TYPE
			SYNTAX Integer32
			UNITS "kBytes"
			MAX-ACCESS read-write
			STATUS current
			DESCRIPTION
				" The Memory Usage Threshold of System.
				The manager should set this threshold about Memory usage. "
			::= { sheSystemControl 10 }

		
--  1.3.6.1.4.1.231.7.1.2.2.1.2.1.7.11
		sheSystemControlMemoryThresholdInterval OBJECT-TYPE
			SYNTAX SheSystemThresholdIntervalType
			MAX-ACCESS read-write
			STATUS current
			DESCRIPTION
				" The sampling interval for CPU threshold.
				Memory usage is checked on every interval configured. "
			::= { sheSystemControl 11 }


--  1.3.6.1.4.1.231.7.1.2.2.1.2.1.7.12
		sheSystemControlTemperatureThreshold OBJECT-TYPE
			SYNTAX Integer32
			UNITS "kBytes"
			MAX-ACCESS read-write
			STATUS current
			DESCRIPTION
				" The Temperature Threshold of System.
				The manager should set this threshold about temperature. "
			::= { sheSystemControl 12 }

		
--  1.3.6.1.4.1.231.7.1.2.2.1.2.1.7.13
		sheSystemControlTemperatureThresholdInterval OBJECT-TYPE
			SYNTAX SheSystemThresholdIntervalType
			MAX-ACCESS read-write
			STATUS current
			DESCRIPTION
				" The sampling interval for temperature threshold.
				Temperature is checked on every interval configured. "
			::= { sheSystemControl 13 }

--  1.3.6.1.4.1.231.7.1.2.2.1.2.1.7.14
		sheSystemControlHostname OBJECT-TYPE
			SYNTAX OCTET STRING
			MAX-ACCESS read-write
			STATUS current
			DESCRIPTION
				"The hostname of system. "
			::= { sheSystemControl 14 }

--  1.3.6.1.4.1.231.7.1.2.2.1.2.1.7.15
		sheSystemControlOSId OBJECT-TYPE
			SYNTAX INTEGER
				{
				os1(1),
				os2(2)
				}
			MAX-ACCESS read-write
			STATUS current
			DESCRIPTION
				"The hostname of system. "
			::= { sheSystemControl 15 }

		
--  1.3.6.1.4.1.231.7.1.2.2.1.2.1.8
		sheSystemTimeZone OBJECT-TYPE
			SYNTAX OCTET STRING (SIZE (0..16))
			MAX-ACCESS read-only
			STATUS current
			DESCRIPTION
				"The Time Zone of the net element.
				The TMN-OS should set this time zone in front of the NE's external time. 
				UTC,
				UTC+1,
				UTC+2,
				UTC+3,
				UTC+3.30,
				UTC+4,
				UTC+4.30,
				UTC+5,
				UTC+5.30,
				UTC+5.45,
				UTC+6,
				UTC+6.30,
				UTC+7,
				UTC+8,
				UTC+8.45,
				UTC+9,
				UTC+9.30,
				UTC+10,
				UTC+10.30,
				UTC+11,
				UTC+11.30,
				UTC+12,
				UTC+12.45,
				UTC+13,
				UTC+14,
				UTC-1,
				UTC-2,
				UTC-2.30,
				UTC-3,
				UTC-3.30,
				UTC-4,
				UTC-4.30,
				UTC-5,
				UTC-6,
				UTC-7,
				UTC-8,
				UTC-9,
				UTC-9.30,
				UTC-10,
				UTC-11,
				UTC-12,
				
				An automatic DST (dayligth saving time) switchover is not supported by the NE!!"
			::= { sheSystemInfo 8 }

		
--  1.3.6.1.4.1.231.7.1.2.2.1.2.1.9
		sheSystem5SecCPULoad OBJECT-TYPE
			SYNTAX Integer32
			UNITS "%"
			MAX-ACCESS read-only
			STATUS current
			DESCRIPTION
				"  The Avg. Value of CPU Load for 5 seconds. "
			::= { sheSystemInfo 9 }

		
--  1.3.6.1.4.1.231.7.1.2.2.1.2.1.10
		sheSystem1MinCPULoad OBJECT-TYPE
			SYNTAX Integer32
			UNITS "%"
			MAX-ACCESS read-only
			STATUS current
			DESCRIPTION
				"  The Avg. Value of CPU Load for 1 minute. "
			::= { sheSystemInfo 10 }

		
--  1.3.6.1.4.1.231.7.1.2.2.1.2.1.11
		sheSystem10MinCPULoad OBJECT-TYPE
			SYNTAX Integer32
			UNITS "%"
			MAX-ACCESS read-only
			STATUS current
			DESCRIPTION
				"  The Avg. Value of CPU Load for 1p minutes. "
			::= { sheSystemInfo 11 }

		
--  1.3.6.1.4.1.231.7.1.2.2.1.2.1.12
		sheSystemCPULoadThreshold OBJECT-TYPE
			SYNTAX Integer32 (20..100)
			UNITS "%"
			MAX-ACCESS read-only
			STATUS current
			DESCRIPTION
				"  The threshold of CPU Load. "
			DEFVAL { 50 }
			::= { sheSystemInfo 12 }

		
--  1.3.6.1.4.1.231.7.1.2.2.1.2.1.13
		sheSystemCPULoadThresholdInterval OBJECT-TYPE
			SYNTAX SheSystemThresholdIntervalType
			MAX-ACCESS read-only
			STATUS current
			DESCRIPTION
				"  The sampling interval of CPU Load. "
			DEFVAL { sec60 }
			::= { sheSystemInfo 13 }

		
--  1.3.6.1.4.1.231.7.1.2.2.1.2.1.14
		sheSystemTotalMemory OBJECT-TYPE
			SYNTAX Integer32
			UNITS "kBytes"
			MAX-ACCESS read-only
			STATUS current
			DESCRIPTION
				"  The Total memory of system. "
			::= { sheSystemInfo 14 }

		
--  1.3.6.1.4.1.231.7.1.2.2.1.2.1.15
		sheSystemUsedMemory OBJECT-TYPE
			SYNTAX Integer32
			UNITS "kBytes"
			MAX-ACCESS read-only
			STATUS current
			DESCRIPTION
				"  The Used memory of system. "
			::= { sheSystemInfo 15 }

		
--  1.3.6.1.4.1.231.7.1.2.2.1.2.1.16
		sheSystemFreeMemory OBJECT-TYPE
			SYNTAX Integer32
			UNITS "kBytes"
			MAX-ACCESS read-only
			STATUS current
			DESCRIPTION
				"  The Free memory of system. "
			::= { sheSystemInfo 16 }

		
--  1.3.6.1.4.1.231.7.1.2.2.1.2.1.17
		sheSystemMemoryThreshold OBJECT-TYPE
			SYNTAX Integer32
			UNITS "kBytes"
			MAX-ACCESS read-only
			STATUS current
			DESCRIPTION
				"  The threshold of Memory Usage. "
			::= { sheSystemInfo 17 }

		
--  1.3.6.1.4.1.231.7.1.2.2.1.2.1.18
		sheSystemMemoryThresholdInterval OBJECT-TYPE
			SYNTAX SheSystemThresholdIntervalType
			MAX-ACCESS read-only
			STATUS current
			DESCRIPTION
				"  The sampling interval of Memory Usage. "
			DEFVAL { sec60 }
			::= { sheSystemInfo 18 }

		
--  1.3.6.1.4.1.231.7.1.2.2.1.2.1.19
		sheSystemBootloaderVersion OBJECT-TYPE
			SYNTAX DisplayString
			MAX-ACCESS read-only
			STATUS current
			DESCRIPTION
				" Contains the version of bootloader."
			::= { sheSystemInfo 19 }

		
--  1.3.6.1.4.1.231.7.1.2.2.1.2.1.20
		sheSystemCliConnected OBJECT-TYPE
			SYNTAX SheSystemTmnConnectedType
			MAX-ACCESS read-only
			STATUS current
			DESCRIPTION
				"The value connected indicates that a CLI session is active. 
				SHE sends the trap sheSystemCliConnected to all known
				TMN systems to inform whether the CLI session has been setup or terminated. "
			::= { sheSystemInfo 20 }

		
		sheSystemStartupResult OBJECT-TYPE
			SYNTAX SheSystemStartupResultType
			MAX-ACCESS read-only
			STATUS current
			DESCRIPTION
				"Result of the last NE startup .
				Values:
				startupInProgress(1),
				startupFailed(2),
				startupFinished(3)"
			::= { sheSystemInfo 21 }
			
		sheSystemRunningOSVersion OBJECT-TYPE
			SYNTAX OCTET STRING
			MAX-ACCESS read-only
			STATUS current
			DESCRIPTION
				"Running OS version of the NE."				
			::= { sheSystemInfo 22 }			
			
		sheSystemTemperature OBJECT-TYPE
			SYNTAX OCTET STRING
			MAX-ACCESS read-only
			STATUS current
			DESCRIPTION
				"Temperature of the NE."				
			::= { sheSystemInfo 23 }	 
			
		sheSystemHostname OBJECT-TYPE
			SYNTAX OCTET STRING
			MAX-ACCESS read-only
			STATUS current
			DESCRIPTION
				"Hostname of the NE."				
			::= { sheSystemInfo 24 }			
			
			
                                          
--  1.3.6.1.4.1.231.7.1.2.2.1.2.1.25 
--  Host MIB : process status.
		sheSystemSwRunTable OBJECT-TYPE
			SYNTAX SEQUENCE OF SheSystemSwRunEntry
			MAX-ACCESS not-accessible
			STATUS current
			DESCRIPTION
				" Process Table of SHE. "
			::= { sheSystemInfo 25 }
                                  
--  1.3.6.1.4.1.231.7.1.2.2.1.2.1.25.1                               
		sheSystemSwRunEntry OBJECT-TYPE
			SYNTAX SheSystemSwRunEntry
			MAX-ACCESS not-accessible
			STATUS current
			DESCRIPTION
				" Entry of the sheSystemSwRunTable. "
			INDEX { sheSystemSwRunIndex }
			::= { sheSystemSwRunTable 1 }

		
		SheSystemSwRunEntry ::=
			SEQUENCE { 
				sheSystemSwRunIndex
					Unsigned32,
				sheSystemSwRunName
					DisplayString,
				sheSystemSwRunID
					Unsigned32,
				sheSystemSwRunPath
					OCTET STRING,
				sheSystemSwRunParam
					OCTET STRING,
				sheSystemSwRunType
					INTEGER,
				sheSystemSwRunPerfCpu
					Unsigned32,
				sheSystemSwRunPerfMem
					Unsigned32				
			 }

--  1.3.6.1.4.1.231.7.1.2.2.1.2.1.25.1.1
		sheSystemSwRunIndex OBJECT-TYPE  
			SYNTAX Unsigned32 (1..65535)
			MAX-ACCESS read-only
			STATUS current
			DESCRIPTION
				" The system SW index. "
			::= { sheSystemSwRunEntry 1 }		
		
		sheSystemSwRunName OBJECT-TYPE
			SYNTAX DisplayString
			MAX-ACCESS read-only
			STATUS current
			DESCRIPTION
				" The system SW name. "
			::= { sheSystemSwRunEntry 2 }
			
		sheSystemSwRunID OBJECT-TYPE 
			SYNTAX Unsigned32
			MAX-ACCESS read-only
			STATUS current
			DESCRIPTION
				" The system SW PID. "
			::= { sheSystemSwRunEntry 3 } 
					
		sheSystemSwRunPath OBJECT-TYPE
			SYNTAX 	OCTET STRING		
			MAX-ACCESS read-only
			STATUS current
			DESCRIPTION
				" The system SW path. "
			::= { sheSystemSwRunEntry 4 } 
			
		
		sheSystemSwRunParam OBJECT-TYPE
			SYNTAX 	OCTET STRING
			MAX-ACCESS read-only
			STATUS current
			DESCRIPTION
				" The system SW parameter. "
			::= { sheSystemSwRunEntry 5 } 

			
		sheSystemSwRunType OBJECT-TYPE
			SYNTAX 	INTEGER
			{
			 unknown(1),
			 operatingSystem(2),
			 deviceDriver(3),
			 application(4)
			}
			MAX-ACCESS read-only
			STATUS current
			DESCRIPTION
				" The system SW Type. "
			::= { sheSystemSwRunEntry 6 } 
			
			
		sheSystemSwRunPerfCpu OBJECT-TYPE
			SYNTAX 	Unsigned32
			MAX-ACCESS read-only
			STATUS current
			DESCRIPTION
				" The system SW CPU utilization. unit:% "
			::= { sheSystemSwRunEntry 7 }   
			
		sheSystemSwRunPerfMem OBJECT-TYPE     
			SYNTAX 	Unsigned32
			MAX-ACCESS read-only
			STATUS current
			DESCRIPTION
				" The system SW Memory utilization. unit:% "
			::= { sheSystemSwRunEntry 8 }
					
					
					
			
				
--  1.3.6.1.4.1.231.7.1.2.2.1.2.2
		sheSystemFile OBJECT IDENTIFIER ::= { sheSystem 2 }

		
--   --------------------------------------------------------------
-- System file management control subgroup
-- --------------------------------------------------------------
-- 1.3.6.1.4.1.231.7.1.2.2.1.2.2.1
		sheSystemFileControl OBJECT IDENTIFIER ::= { sheSystemFile 1 }

		
--  1.3.6.1.4.1.231.7.1.2.2.1.2.2.1.1
		sheSystemFileControlRequest OBJECT-TYPE
			SYNTAX SheSystemFileControlRequestType
			MAX-ACCESS read-write
			STATUS current
			DESCRIPTION
				"  File management commands :
				
				upload   : a file is uploaded to the FTP server from the SHE.
				download : a file is downloaded from a FTP server to the SHE
				
				uploadCardsAllOfType   : upload for all cards af the same type.
				downloadCardsAllOfType : download for all cards af the same type.
				
				
				Parameters specify the type of file and the FTP server.
				
				downloads SW to :
				- a singleCard : commands to load a new load either to 
				- all cards of the system 
				- all cards of a type
				- restoreFile (configuration files)
				- snmpcfg-file 
				
				uploads:
				- error log
				- restoreFile (congfiguration files)
				- remote inventory 
				- performance data   
				
				
				writeImage 
				- NOS image is write in os area by user.

				             
				Notifications : 
				   sheSystemFtp
				   sheSystemSwLoadPromoted   
				   ....
				   sheSystemWriteImageFinished                   
				
				Alarms:
				   sheSystemSwmFtpAccessError
				   sheSystemSwmFtpExternalAccessError                  
				
				   "
			::= { sheSystemFileControl 1 }

		
--  1.3.6.1.4.1.231.7.1.2.2.1.2.2.1.2
		sheSystemFileControlStatus OBJECT-TYPE
			SYNTAX SheControlStatusType
			MAX-ACCESS read-only
			STATUS current
			DESCRIPTION
				" The status of a control request. "
			::= { sheSystemFileControl 2 }

		
--  1.3.6.1.4.1.231.7.1.2.2.1.2.2.1.3
		sheSystemFileControlTimer OBJECT-TYPE
			SYNTAX Unsigned32
			MAX-ACCESS read-only
			STATUS current
			DESCRIPTION
				" The maximum wait time for the manager for command ending.
				For long running commands.
				The manager reads this value from the SHE. "
			::= { sheSystemFileControl 3 }

		
--  1.3.6.1.4.1.231.7.1.2.2.1.2.2.1.4
		sheSystemFileControlReqResult OBJECT-TYPE
			SYNTAX SheSystemFileControlRequestResultType
			MAX-ACCESS read-only
			STATUS current
			DESCRIPTION
				" The result of the last user command. "
			::= { sheSystemFileControl 4 }

		
--  1.3.6.1.4.1.231.7.1.2.2.1.2.2.1.5
		sheSystemFileControlTimeStamp OBJECT-TYPE
			SYNTAX Unsigned32
			UNITS "sec"
			MAX-ACCESS read-only
			STATUS current
			DESCRIPTION
				" The time stamp of the last command (end of command). "
			::= { sheSystemFileControl 5 }

		
--  1.3.6.1.4.1.231.7.1.2.2.1.2.2.1.6
		sheSystemFileControlTypeOfFile OBJECT-TYPE
			SYNTAX SheSystemTypeOfFile
			MAX-ACCESS read-write
			STATUS current
			DESCRIPTION
				" The file type definition:
				1..stored load,    (only download)
				2..error log,      (only upload)
				3..restoreFile     (both up/download)
				4..remoteInventory (only upload)
				5..performanceData (only upload)
				6..alarmLog        (only upload)
				7..uptimeLog       (only upload)
				"
			::= { sheSystemFileControl 6 }

		
--  1.3.6.1.4.1.231.7.1.2.2.1.2.2.1.7
		sheSystemFileControlPathName OBJECT-TYPE
			SYNTAX OCTET STRING (SIZE (0..128))
			MAX-ACCESS read-write
			STATUS current
			DESCRIPTION
				"Path name of file on FTP server. 
				This path should be set relative to the ftp-server root.
				Use only linux notation ( / ). 
				
				Spaces in pathnames are not allowed, because of possible problems with
				different FTP implementations (client and/or server)!!"
			::= { sheSystemFileControl 7 }

		
--  1.3.6.1.4.1.231.7.1.2.2.1.2.2.1.8
		sheSystemFileControlFileName OBJECT-TYPE
			SYNTAX OCTET STRING (SIZE (1..128))
			MAX-ACCESS read-write
			STATUS current
			DESCRIPTION
				" File name of file on FTP server. 
				Spaces in filenames are not allowed, because of possible problems with
				different FTP implementations (client and/or server)!!
				"
			::= { sheSystemFileControl 8 }

		
--  1.3.6.1.4.1.231.7.1.2.2.1.2.2.1.9
		sheSystemFileControlCardType OBJECT-TYPE
			SYNTAX SheCardType
			MAX-ACCESS read-write
			STATUS current
			DESCRIPTION
				" The card type to be upgraded. "
			::= { sheSystemFileControl 9 }

		
--  1.3.6.1.4.1.231.7.1.2.2.1.2.2.1.10
		sheSystemFileControlEntPhysicalIndex OBJECT-TYPE
			SYNTAX PhysicalIndex
			MAX-ACCESS read-write
			STATUS current
			DESCRIPTION
				" The entPhysicalIndex of the card to be loaded. "
			::= { sheSystemFileControl 10 }

		
--  1.3.6.1.4.1.231.7.1.2.2.1.2.2.1.12
		sheSystemFileControlLoadStatus OBJECT-TYPE
			SYNTAX SheSystemFileLoadStatusType
			MAX-ACCESS read-only
			STATUS current
			DESCRIPTION
				" Status of SHE download.                                              
				1..finished,                                                           
				2..running,                                                            
				3..broken,                                                             
				"
			::= { sheSystemFileControl 12 }

		
--  1.3.6.1.4.1.231.7.1.2.2.1.2.2.1.13
		sheSystemFileControlServerAddr OBJECT-TYPE
			SYNTAX OCTET STRING (SIZE (0..20))
			MAX-ACCESS read-write
			STATUS current
			DESCRIPTION
				" Address of FTP server (dotted notation).                               
				Attribute only valid in var bind list with correct sheSystemFileControlCommand.      
				Read-access will report an empty string."
			::= { sheSystemFileControl 13 }

		
--   read to this attribute will deliver 20 times sign '-'                         
-- 1.3.6.1.4.1.231.7.1.2.2.1.2.2.1.14
		sheSystemFileControlUsrName OBJECT-TYPE
			SYNTAX OCTET STRING (SIZE (0..20))
			MAX-ACCESS read-write
			STATUS current
			DESCRIPTION
				" Username for FTP access.                                                             
				Attribute only valid in var bind list with correct sheSystemFileControlCommand.
				Read-access will report an empty string. "
			::= { sheSystemFileControl 14 }

		
--   read to this attribute will deliver 20 times sign '-'                         
-- 1.3.6.1.4.1.231.7.1.2.2.1.2.2.1.15
		sheSystemFileControlPassword OBJECT-TYPE
			SYNTAX OCTET STRING (SIZE (0..20))
			MAX-ACCESS read-write
			STATUS current
			DESCRIPTION
				" Password for FTP access.                                                              
				Attribute only valid in var bind list with correct sheSystemFileControlCommand.
				Read-access will report an empty string. "
			::= { sheSystemFileControl 15 }

		sheSystemFileControlServiceType OBJECT-TYPE
			SYNTAX INTEGER
			{
			    ftp(0),
			    tftp(1)
			}
			MAX-ACCESS read-write
			STATUS current
			DESCRIPTION
			" The service type for upload/download. "
			::= { sheSystemFileControl 16 }


		
--   --------------------------------------------------------------
-- System file table 
-- --------------------------------------------------------------
-- 1.3.6.1.4.1.231.7.1.2.2.1.2.2.2
		sheSystemFileSwFileTable OBJECT-TYPE
			SYNTAX SEQUENCE OF SheSystemFileSwFileEntry
			MAX-ACCESS not-accessible
			STATUS current
			DESCRIPTION
				" File Table of SHE. 
				List of all files per card present on the SHE and their 
				counterpart on the FTP server
				
				Information about Primary and Secondary 
				loads is also found in this table. "
			::= { sheSystemFile 2 }

		
--  1.3.6.1.4.1.231.7.1.2.2.1.2.2.2.1
		sheSystemFileSwFileEntry OBJECT-TYPE
			SYNTAX SheSystemFileSwFileEntry
			MAX-ACCESS not-accessible
			STATUS current
			DESCRIPTION
				" An entry in the sheSystemFileSwTable.
				Notifications : none. "
			INDEX { entPhysicalIndex, sheSystemFileSwfIndex }
			::= { sheSystemFileSwFileTable 1 }

		
		SheSystemFileSwFileEntry ::=
			SEQUENCE { 
				sheSystemFileSwfIndex
					SheSystemFileIndexType,
				sheSystemFileSwfFileName
					OCTET STRING,
				sheSystemFileSwfTypeOfFile
					SheSystemTypeOfFile,
				sheSystemFileSwfVersion
					OCTET STRING,
				sheSystemFileSwfSize
					Integer32,
				sheSystemFileSwfTimeStamp
					Unsigned32
			 }

--  1.3.6.1.4.1.231.7.1.2.2.1.2.2.2.1.1
		sheSystemFileSwfIndex OBJECT-TYPE
			SYNTAX SheSystemFileIndexType
			MAX-ACCESS read-only
			STATUS current
			DESCRIPTION
				" Second Index of file table.  "
			::= { sheSystemFileSwFileEntry 1 }

		
--  1.3.6.1.4.1.231.7.1.2.2.1.2.2.2.1.2
		sheSystemFileSwfFileName OBJECT-TYPE
			SYNTAX OCTET STRING (SIZE (0..128))
			MAX-ACCESS read-only
			STATUS current
			DESCRIPTION
				" File name of file in SHE file system. "
			::= { sheSystemFileSwFileEntry 2 }

		
--  1.3.6.1.4.1.231.7.1.2.2.1.2.2.2.1.3
		sheSystemFileSwfTypeOfFile OBJECT-TYPE
			SYNTAX SheSystemTypeOfFile
			MAX-ACCESS read-only
			STATUS current
			DESCRIPTION
				" The file type definition: 
				1..stored load,    (only download) 
				2..error log,      (only upload)
				3..restoreFile     (both up/download)
				4..remoteInventory (only upload)
				5..performanceData (only upload)
				6..alarmLog        (only upload)
				7..uptimeLog       (only upload)"
			::= { sheSystemFileSwFileEntry 3 }

		
--  1.3.6.1.4.1.231.7.1.2.2.1.2.2.2.1.4
		sheSystemFileSwfVersion OBJECT-TYPE
			SYNTAX OCTET STRING (SIZE (0..20))
			MAX-ACCESS read-only
			STATUS current
			DESCRIPTION
				" File or software version of file in the SHE file system. "
			::= { sheSystemFileSwFileEntry 4 }

		
--  1.3.6.1.4.1.231.7.1.2.2.1.2.2.2.1.5
		sheSystemFileSwfSize OBJECT-TYPE
			SYNTAX Integer32
			MAX-ACCESS read-only
			STATUS current
			DESCRIPTION
				" Size of file in SHE file system. "
			::= { sheSystemFileSwFileEntry 5 }

		
--  1.3.6.1.4.1.231.7.1.2.2.1.2.2.2.1.6
		sheSystemFileSwfTimeStamp OBJECT-TYPE
			SYNTAX Unsigned32
			UNITS "sec"
			MAX-ACCESS read-only
			STATUS current
			DESCRIPTION
				" Time stamp of file in file system of SHE. 
				"
			::= { sheSystemFileSwFileEntry 6 }

		
--  1.3.6.1.4.1.231.7.1.2.2.1.2.3
		sheSystemNotifications OBJECT IDENTIFIER ::= { sheSystem 3 }

		
--   --------------------------------------------------------------
-- System notification subgroup
-- --------------------------------------------------------------
-- 1.3.6.1.4.1.231.7.1.2.2.1.2.3.1
		sheSystemEvents OBJECT IDENTIFIER ::= { sheSystemNotifications 1 }

		
--   Start up end event
-- 1.3.6.1.4.1.231.7.1.2.2.1.2.3.1.1
		sheSystemStartupEnd NOTIFICATION-TYPE
			OBJECTS { sheSystemExternalTime, sheSystemStartupType }
			STATUS current
			DESCRIPTION 
				" End of startup. "
			::= { sheSystemEvents 1 }

		
--  1.3.6.1.4.1.231.7.1.2.2.1.2.3.1.2
		sheSystemFtp NOTIFICATION-TYPE
			OBJECTS { sheSystemFileControlTimeStamp, sheSystemFileControlRequest, sheSystemFileControlTypeOfFile, sheSystemFileControlPathName, sheSystemFileControlFileName, 
				sheSystemFileControlEntPhysicalIndex, sheSystemFileControlLoadStatus, sheSystemFileControlReqResult, sheSystemFileControlServiceType }
			STATUS current
			DESCRIPTION 
				" Reports the result of a file up/download. 
				The sheSystemFileControlRequest reports either upload / download
				The sheSystemFileControlLoadStatus reports either 
				            finished / ongoing / broken.    
				"
			::= { sheSystemEvents 2 }

		
--  1.3.6.1.4.1.231.7.1.2.2.1.2.3.1.3
		sheSystemSwLoadPromoted NOTIFICATION-TYPE
			OBJECTS { sheSystemFileControlTimeStamp, entPhysicalIndex }
			STATUS current
			DESCRIPTION 
				" The upgraded load is promoted to be good/trusted. "
			::= { sheSystemEvents 3 }

		
--  1.3.6.1.4.1.231.7.1.2.2.1.2.3.1.4
		sheSystemSwLoadPromotionFailed NOTIFICATION-TYPE
			OBJECTS { sheSystemFileControlTimeStamp, entPhysicalIndex, sheSystemFileControlReqResult }
			STATUS current
			DESCRIPTION 
				" Sent when load promotion failed. 
				Card will restart with fallback load. The ReqResult should
				contain some detailed information about the error-reason (tbd.)."
			::= { sheSystemEvents 4 }

		
--   LCT connected event
-- 1.3.6.1.4.1.231.7.1.2.2.1.2.3.1.5
		sheSystemLctSession NOTIFICATION-TYPE
			OBJECTS { sheSystemExternalTime, sheSystemLctConnected }
			STATUS current
			DESCRIPTION 
				" A LCT session is connected or disconnected. "
			::= { sheSystemEvents 5 }

		
--  1.3.6.1.4.1.231.7.1.2.2.1.2.3.1.6
		sheSystemWriteDatatoFlashFinished NOTIFICATION-TYPE
			OBJECTS { sheSystemControlStatus, sheSystemControlReqResult, sheSystemControlTimeStamp }
			STATUS current
			DESCRIPTION 
				"Description."
			::= { sheSystemEvents 6 }

		
--  1.3.6.1.4.1.231.7.1.2.2.1.2.3.1.7
		sheSystemChangedCPULoadThreshold NOTIFICATION-TYPE
			OBJECTS { sheSystemControlStatus, sheSystemControlReqResult, sheSystemControlTimeStamp }
			STATUS current
			DESCRIPTION 
				"CPU Load Threshold change state by user."
			::= { sheSystemEvents 7 }

		
--  1.3.6.1.4.1.231.7.1.2.2.1.2.3.1.8
		sheSystemChangedMemoryThreshold NOTIFICATION-TYPE
			OBJECTS { sheSystemControlStatus, sheSystemControlReqResult, sheSystemControlTimeStamp }
			STATUS current
			DESCRIPTION 
				"Memory usage Threshold change state by user."
			::= { sheSystemEvents 8 }

		
		sheSystemCliSession NOTIFICATION-TYPE
			OBJECTS { sheSystemExternalTime, sheSystemCliConnected }
			STATUS current
			DESCRIPTION 
				" A CLI session is connected or disconnected. "
			::= { sheSystemEvents 9 }


--  1.3.6.1.4.1.231.7.1.2.2.1.2.3.1.10
		sheSystemChangedTemperatureThreshold NOTIFICATION-TYPE
			OBJECTS { sheSystemControlStatus, sheSystemControlReqResult, sheSystemControlTimeStamp }
			STATUS current
			DESCRIPTION 
				"Temperature Threshold change state by user."
			::= { sheSystemEvents 10 }


--  1.3.6.1.4.1.231.7.1.2.2.1.2.3.1.11
		sheSystemChangedHostname NOTIFICATION-TYPE
			OBJECTS { sheSystemControlStatus, sheSystemControlReqResult, sheSystemControlTimeStamp }
			STATUS current
			DESCRIPTION 
				"Hostname change state by user."
			::= { sheSystemEvents 11 }
                                           
--  1.3.6.1.4.1.231.7.1.2.2.1.2.3.1.12
		sheSystemWriteImageFinished NOTIFICATION-TYPE
			OBJECTS { sheSystemControlStatus, sheSystemControlReqResult, sheSystemControlTimeStamp, sheSystemControlFileName  }
			STATUS current
			DESCRIPTION 
				"."
			::= { sheSystemEvents 12 }

		
                                          
					
--   -----------------------------------------------------------------  
-- 1.3.6.1.4.1.231.7.1.2.2.1.2.3.2
		sheSystemAlarms OBJECT IDENTIFIER ::= { sheSystemNotifications 2 }

		
--  1.3.6.1.4.1.231.7.1.2.2.1.2.3.2.1
		sheSystemCPULoadThresholdExceeded NOTIFICATION-TYPE
			OBJECTS { sheAlarmTimeAndDate, sheAlarmReportingSource, sheAlarmReportingSourceType, sheAlarmSeverity }
			STATUS current
			DESCRIPTION 
				"Measured CPU load has exceeded the threshold in the given measuring interval."
			::= { sheSystemAlarms 1 }

		
--  1.3.6.1.4.1.231.7.1.2.2.1.2.3.2.2
		sheSystemMemoryThresholdExceeded NOTIFICATION-TYPE
			OBJECTS { sheAlarmTimeAndDate, sheAlarmReportingSource, sheAlarmReportingSourceType, sheAlarmSeverity }
			STATUS current
			DESCRIPTION 
				"Measured memory usage has exceeded the threshold in the given measuring interval."
			::= { sheSystemAlarms 2 }

--  1.3.6.1.4.1.231.7.1.2.2.1.2.3.2.3
		sheSystemTemperatureThresholdExceeded NOTIFICATION-TYPE
			OBJECTS { sheAlarmTimeAndDate, sheAlarmReportingSource, sheAlarmReportingSourceType, sheAlarmSeverity }
			STATUS current
			DESCRIPTION 
				"Measured temperature has exceeded the threshold in the given measuring interval."
			::= { sheSystemAlarms 3 }

--  1.3.6.1.4.1.231.7.1.2.2.1.2.3.2.4
		sheSystemDyingGasp NOTIFICATION-TYPE
			OBJECTS { sheAlarmTimeAndDate, sheAlarmReportingSource, sheAlarmReportingSourceType, sheAlarmSeverity }
			STATUS current
			DESCRIPTION 
				"NE detect Power disconnection."
			::= { sheSystemAlarms 4 }  
			
--  1.3.6.1.4.1.231.7.1.2.2.1.2.3.2.5
		sheSystemFanAbnormal NOTIFICATION-TYPE
			OBJECTS { sheAlarmTimeAndDate, sheAlarmReportingSource, sheAlarmReportingSourceType, sheAlarmSeverity }
			STATUS current
			DESCRIPTION 
				"NE detect fan abnormal."
			::= { sheSystemAlarms 5 }
			
		
--  1.3.6.1.4.1.231.7.1.2.2.1.2.5
		sheSystemNtpClient OBJECT IDENTIFIER ::= { sheSystem 5 }

		
--   --------------------------------------------------------------
-- System NTP Client/Server table 
-- --------------------------------------------------------------
-- 1.3.6.1.4.1.231.7.1.2.2.1.2.5.1
		sheSystemNtpClientEnabled OBJECT-TYPE
			SYNTAX INTEGER
				{
				false(0),
				true(1)
				}
			MAX-ACCESS read-only
			STATUS current
			DESCRIPTION
				"NTP Client enable status."
			::= { sheSystemNtpClient 1 }

		
--  1.3.6.1.4.1.231.7.1.2.2.1.2.5.2
		sheSystemNtpClientXmitInterval OBJECT-TYPE
			SYNTAX Integer32 (1..2160)
			UNITS "hour"
			MAX-ACCESS read-only
			STATUS current
			DESCRIPTION
				"NTP Client transmit-packet interval to request time information from NTP server..
				Valid range is 1 hour up to 2160 hours (3 months).
				The default value should be 24 hours."
			::= { sheSystemNtpClient 2 }

		
--  1.3.6.1.4.1.231.7.1.2.2.1.2.5.3
		sheSystemNtpClientServerTable OBJECT-TYPE
			SYNTAX SEQUENCE OF SheSystemNtpClientServerEntry
			MAX-ACCESS not-accessible
			STATUS current
			DESCRIPTION
				" NTP Client server Table of SHE."
			::= { sheSystemNtpClient 3 }

		
--  1.3.6.1.4.1.231.7.1.2.2.1.2.5.3.1
		sheSystemNtpClientServerEntry OBJECT-TYPE
			SYNTAX SheSystemNtpClientServerEntry
			MAX-ACCESS not-accessible
			STATUS current
			DESCRIPTION
				" An entry in the sheSystemNtpClientTable.
				Notifications : none. "
			INDEX { sheSystemNtpClientServerIndex }
			::= { sheSystemNtpClientServerTable 1 }

		
		SheSystemNtpClientServerEntry ::=
			SEQUENCE { 
				sheSystemNtpClientServerIndex
					Integer32,
				sheSystemNtpClientServerName
					OCTET STRING
			 }

--  1.3.6.1.4.1.231.7.1.2.2.1.2.5.3.1.1
		sheSystemNtpClientServerIndex OBJECT-TYPE
			SYNTAX Integer32 (1..100)
			MAX-ACCESS read-only
			STATUS current
			DESCRIPTION
				" Index of file table.  "
			::= { sheSystemNtpClientServerEntry 1 }

		
--  1.3.6.1.4.1.231.7.1.2.2.1.2.5.3.1.2
		sheSystemNtpClientServerName OBJECT-TYPE
			SYNTAX OCTET STRING (SIZE (1..64))
			MAX-ACCESS read-only
			STATUS current
			DESCRIPTION
				" Server name of NTP Client in SHE NTP Client system. "
			::= { sheSystemNtpClientServerEntry 2 }

		
--   --------------------------------------------------------------
-- System NtpClient management control subgroup
-- --------------------------------------------------------------
-- 1.3.6.1.4.1.231.7.1.2.2.1.2.5.4
		sheSystemNtpClientControl OBJECT IDENTIFIER ::= { sheSystemNtpClient 4 }

		
--  1.3.6.1.4.1.231.7.1.2.2.1.2.5.4.1
		sheSystemNtpClientControlRequest OBJECT-TYPE
			SYNTAX SheSystemNtpClientControlRequestType
			MAX-ACCESS read-write
			STATUS current
			DESCRIPTION
				"  NtpClient management commands :
				
				enabledNtpClient   : NtpClient client is enabled by users.
				disabledNtpClient  : NtpClient client is disabled bu users
				
				changedNtpClientXmitInterval   : NtpClient transmit-packet interval is changed by users.
				
				addedNtpClientServerName : NtpClient source hostname is added into source list.
				deletedNtpClientServerName : NtpClient source hostname is deleted in source list.
				
				Notifications: ZZZZZZ
					        "
			::= { sheSystemNtpClientControl 1 }

		
--  1.3.6.1.4.1.231.7.1.2.2.1.2.5.4.2
		sheSystemNtpClientControlStatus OBJECT-TYPE
			SYNTAX SheControlStatusType
			MAX-ACCESS read-only
			STATUS current
			DESCRIPTION
				" The status of a control request. "
			::= { sheSystemNtpClientControl 2 }

		
--  1.3.6.1.4.1.231.7.1.2.2.1.2.5.4.3
		sheSystemNtpClientControlTimer OBJECT-TYPE
			SYNTAX Unsigned32
			MAX-ACCESS read-only
			STATUS current
			DESCRIPTION
				" The maximum wait time for the manager for command ending.
				For long running commands.
				The manager reads this value from the SHE. "
			::= { sheSystemNtpClientControl 3 }

		
--  1.3.6.1.4.1.231.7.1.2.2.1.2.5.4.4
		sheSystemNtpClientControlReqResult OBJECT-TYPE
			SYNTAX SheSystemNtpClientControlRequestResultType
			MAX-ACCESS read-only
			STATUS current
			DESCRIPTION
				" The result of the last user command. "
			::= { sheSystemNtpClientControl 4 }

		
--  1.3.6.1.4.1.231.7.1.2.2.1.2.5.4.5
		sheSystemNtpClientControlTimeStamp OBJECT-TYPE
			SYNTAX Unsigned32
			UNITS "sec"
			MAX-ACCESS read-only
			STATUS current
			DESCRIPTION
				" The time stamp of the last command (end of command). "
			::= { sheSystemNtpClientControl 5 }

		
--  1.3.6.1.4.1.231.7.1.2.2.1.2.5.4.6
		sheSystemNtpClientControlXmitInterval OBJECT-TYPE
			SYNTAX Integer32 (1..2160)
			UNITS "hour"
			MAX-ACCESS read-write
			STATUS current
			DESCRIPTION
				"Configure NTP Client transmit-packet interval to request time information from NTP server..
				Valid range is 1 hour up to 2160 hours (3 months).
				The default value should be 24 hours."
			::= { sheSystemNtpClientControl 6 }

		
--  1.3.6.1.4.1.231.7.1.2.2.1.2.5.4.7
		sheSystemNtpClientControlServername OBJECT-TYPE
			SYNTAX OCTET STRING (SIZE (0..32))
			MAX-ACCESS read-write
			STATUS current
			DESCRIPTION
				"NtpClient Source hostname or Ip address to get current time."
			::= { sheSystemNtpClientControl 7 }

		
--  1.3.6.1.4.1.231.7.1.2.2.1.2.5.4.7
		sheSystemNtpClientControlServerIndex OBJECT-TYPE
			SYNTAX Integer32 (1..100)
			MAX-ACCESS read-write
			STATUS current
			DESCRIPTION
				"Index of the addressed table entry."
			::= { sheSystemNtpClientControl 8 }

		
--   --------------------------------------------------------------
-- System NtpClient management notification subgroup
-- --------------------------------------------------------------
-- 1.3.6.1.4.1.231.7.1.2.2.1.2.5.5
		sheSystemNtpClientNotifications OBJECT IDENTIFIER ::= { sheSystemNtpClient 5 }

		
--  1.3.6.1.4.1.231.7.1.2.2.1.2.5.5.1
		sheSystemNtpClientEnable NOTIFICATION-TYPE
			OBJECTS { sheSystemNtpClientControlStatus, sheSystemNtpClientControlReqResult, sheSystemNtpClientControlTimeStamp }
			STATUS current
			DESCRIPTION 
				"Description."
			::= { sheSystemNtpClientNotifications 1 }

		
--  1.3.6.1.4.1.231.7.1.2.2.1.2.5.5.2
		sheSystemNtpClientDisable NOTIFICATION-TYPE
			OBJECTS { sheSystemNtpClientControlStatus, sheSystemNtpClientControlReqResult, sheSystemNtpClientControlTimeStamp }
			STATUS current
			DESCRIPTION 
				"Description."
			::= { sheSystemNtpClientNotifications 2 }

		
--  1.3.6.1.4.1.231.7.1.2.2.1.2.5.5.3
		sheSystemNtpClientChangeXmitInterval NOTIFICATION-TYPE
			OBJECTS { sheSystemNtpClientControlStatus, sheSystemNtpClientControlReqResult, sheSystemNtpClientControlTimeStamp, sheSystemNtpClientControlXmitInterval }
			STATUS current
			DESCRIPTION 
				"Description."
			::= { sheSystemNtpClientNotifications 3 }

		
--  1.3.6.1.4.1.231.7.1.2.2.1.2.5.5.4
		sheSystemNtpClientAddServerName NOTIFICATION-TYPE
			OBJECTS { sheSystemNtpClientControlStatus, sheSystemNtpClientControlReqResult, sheSystemNtpClientControlTimeStamp, sheSystemNtpClientControlServerIndex, sheSystemNtpClientControlServername
				 }
			STATUS current
			DESCRIPTION 
				"Description."
			::= { sheSystemNtpClientNotifications 4 }

		
--  1.3.6.1.4.1.231.7.1.2.2.1.2.5.5.5
		sheSystemNtpClientDeleteServerName NOTIFICATION-TYPE
			OBJECTS { sheSystemNtpClientControlStatus, sheSystemNtpClientControlReqResult, sheSystemNtpClientControlTimeStamp, sheSystemNtpClientControlServerIndex, sheSystemNtpClientControlServername
				 }
			STATUS current
			DESCRIPTION 
				"Description."
			::= { sheSystemNtpClientNotifications 5 }

		
--  1.3.6.1.4.1.231.7.1.2.2.1.2.6
		sheSystemDnsServer OBJECT IDENTIFIER ::= { sheSystem 6 }

		
--   --------------------------------------------------------------
-- System DNS Server table 
-- --------------------------------------------------------------
-- 1.3.6.1.4.1.231.7.1.2.2.1.2.6.1
		sheSystemDnsServerTable OBJECT-TYPE
			SYNTAX SEQUENCE OF SheSystemDnsServerEntry
			MAX-ACCESS not-accessible
			STATUS current
			DESCRIPTION
				" DNS server Table of SHE."
			::= { sheSystemDnsServer 1 }

		
--  1.3.6.1.4.1.231.7.1.2.2.1.2.6.1.1
		sheSystemDnsServerEntry OBJECT-TYPE
			SYNTAX SheSystemDnsServerEntry
			MAX-ACCESS not-accessible
			STATUS current
			DESCRIPTION
				" An entry in the sheSystemDnsServerTable.
				Notifications : none. "
			INDEX { sheSystemDnsServerIndex }
			::= { sheSystemDnsServerTable 1 }

		
		SheSystemDnsServerEntry ::=
			SEQUENCE { 
				sheSystemDnsServerIndex
					Integer32,
				sheSystemDnsServerAddr
					OCTET STRING
			 }

--  1.3.6.1.4.1.231.7.1.2.2.1.2.6.1.1.1
		sheSystemDnsServerIndex OBJECT-TYPE
			SYNTAX Integer32 (1..100)
			MAX-ACCESS read-only
			STATUS current
			DESCRIPTION
				" Index of DnsServer table.  "
			::= { sheSystemDnsServerEntry 1 }

		
--  1.3.6.1.4.1.231.7.1.2.2.1.2.6.1.1.2
		sheSystemDnsServerAddr OBJECT-TYPE
			SYNTAX OCTET STRING (SIZE (0..32))
			MAX-ACCESS read-only
			STATUS current
			DESCRIPTION
				" IP address of DNS Server system. "
			::= { sheSystemDnsServerEntry 2 }

		
--   --------------------------------------------------------------
-- System DNS Server management control subgroup
-- --------------------------------------------------------------
-- 1.3.6.1.4.1.231.7.1.2.2.1.2.6.2
		sheSystemDnsServerControl OBJECT IDENTIFIER ::= { sheSystemDnsServer 2 }

		
--  1.3.6.1.4.1.231.7.1.2.2.1.2.6.2.1
		sheSystemDnsServerControlRequest OBJECT-TYPE
			SYNTAX SheSystemDnsServerControlRequestType
			MAX-ACCESS read-write
			STATUS current
			DESCRIPTION
				"  DNS Server management commands :
				
				addedDnsServerName : DNS Server IP Address is added into server list.
				deletedDnsServerName : DNS Server IP Address is deleted in server list.
				
				Notifications: ZZZZZZ
					        "
			::= { sheSystemDnsServerControl 1 }

		
--  1.3.6.1.4.1.231.7.1.2.2.1.2.6.2.2
		sheSystemDnsServerControlStatus OBJECT-TYPE
			SYNTAX SheControlStatusType
			MAX-ACCESS read-only
			STATUS current
			DESCRIPTION
				" The status of a control request. "
			::= { sheSystemDnsServerControl 2 }

		
--  1.3.6.1.4.1.231.7.1.2.2.1.2.6.2.3
		sheSystemDnsServerControlTimer OBJECT-TYPE
			SYNTAX Unsigned32
			MAX-ACCESS read-only
			STATUS current
			DESCRIPTION
				" The maximum wait time for the manager for command ending.
				For long running commands.
				The manager reads this value from the SHE. "
			::= { sheSystemDnsServerControl 3 }

		
--  1.3.6.1.4.1.231.7.1.2.2.1.2.6.2.4
		sheSystemDnsServerControlReqResult OBJECT-TYPE
			SYNTAX SheSystemDnsServerControlRequestResultType
			MAX-ACCESS read-only
			STATUS current
			DESCRIPTION
				" The result of the last user command. "
			::= { sheSystemDnsServerControl 4 }

		
--  1.3.6.1.4.1.231.7.1.2.2.1.2.6.2.5
		sheSystemDnsServerControlTimeStamp OBJECT-TYPE
			SYNTAX Unsigned32
			UNITS "sec"
			MAX-ACCESS read-only
			STATUS current
			DESCRIPTION
				" The time stamp of the last command (end of command). "
			::= { sheSystemDnsServerControl 5 }

		
--  1.3.6.1.4.1.231.7.1.2.2.1.2.6.2.6
		sheSystemDnsServerControlAddr OBJECT-TYPE
			SYNTAX OCTET STRING (SIZE (0..32))
			MAX-ACCESS read-write
			STATUS current
			DESCRIPTION
				"DNS Server Ip address."
			::= { sheSystemDnsServerControl 6 }

		
--  1.3.6.1.4.1.231.7.1.2.2.1.2.6.2.6
		sheSystemDnsServerControlIndex OBJECT-TYPE
			SYNTAX Integer32 (1..100)
			MAX-ACCESS read-write
			STATUS current
			DESCRIPTION
				"Index of the addressed table entry."
			::= { sheSystemDnsServerControl 7 }

		
--   --------------------------------------------------------------
-- System DNS Server management notification subgroup
-- --------------------------------------------------------------
-- 1.3.6.1.4.1.231.7.1.2.2.1.2.6.3
		sheSystemDnsServerNotifications OBJECT IDENTIFIER ::= { sheSystemDnsServer 3 }

		
--  1.3.6.1.4.1.231.7.1.2.2.1.2.6.3.1
		sheSystemDnsServerAddAddr NOTIFICATION-TYPE
			OBJECTS { sheSystemDnsServerControlStatus, sheSystemDnsServerControlReqResult, sheSystemDnsServerControlTimeStamp, sheSystemDnsServerControlAddr, sheSystemDnsServerControlIndex
				 }
			STATUS current
			DESCRIPTION 
				"Description."
			::= { sheSystemDnsServerNotifications 1 }

		
--  1.3.6.1.4.1.231.7.1.2.2.1.2.6.3.2
		sheSystemDnsServerDeleteAddr NOTIFICATION-TYPE
			OBJECTS { sheSystemDnsServerControlStatus, sheSystemDnsServerControlReqResult, sheSystemDnsServerControlTimeStamp, sheSystemDnsServerControlIndex }
			STATUS current
			DESCRIPTION 
				"Description."
			::= { sheSystemDnsServerNotifications 2 }

		
--  1.3.6.1.4.1.231.7.1.2.2.1.2.7
		sheSystemManagementSession OBJECT IDENTIFIER ::= { sheSystem 7 }

		
--   --------------------------------------------------------------
-- System Management Session group 
-- --------------------------------------------------------------
-- 1.3.6.1.4.1.231.7.1.2.2.1.2.7.1
		sheSystemManagementSessionSnmpAgingTime OBJECT-TYPE
			SYNTAX Integer32 (300..3600)
			MAX-ACCESS read-only
			STATUS current
			DESCRIPTION
				"Aging time for SNMP management session."
			::= { sheSystemManagementSession 1 }

		
--   -----------------------------------------------------------------
-- System Management Session Table
-- -----------------------------------------------------------------
-- 1.3.6.1.4.1.231.7.1.2.2.1.2.7.2
		sheSystemManagementSessionTable OBJECT-TYPE
			SYNTAX SEQUENCE OF SheSystemManagementSessionEntry
			MAX-ACCESS not-accessible
			STATUS current
			DESCRIPTION
				" Management session information table for SHE."
			::= { sheSystemManagementSession 2 }

		
--  1.3.6.1.4.1.231.7.1.2.2.1.2.7.2.1
		sheSystemManagementSessionEntry OBJECT-TYPE
			SYNTAX SheSystemManagementSessionEntry
			MAX-ACCESS not-accessible
			STATUS current
			DESCRIPTION
				" An entry in the sheSystemManagementSessionTable.
				Notifications : none. "
			INDEX { sheSystemManagementSessionIndex }
			::= { sheSystemManagementSessionTable 1 }

		
		SheSystemManagementSessionEntry ::=
			SEQUENCE { 
				sheSystemManagementSessionIndex
					Integer32,
				sheSystemManagementSessionType
					SheSystemManagementSessionType,
				sheSystemManagementSessionSnmpExpiredTime
					Integer32,
				sheSystemManagementSessionAddress
					IpAddress,  
				sheSystemManagementSessionServicePort
					Integer32,
				sheSystemManagementSessionElapsedTime
					Integer32
			 }

--  1.3.6.1.4.1.231.7.1.2.2.1.2.7.2.1.1
		sheSystemManagementSessionIndex OBJECT-TYPE
			SYNTAX Integer32 (1..100)
			MAX-ACCESS read-only
			STATUS current
			DESCRIPTION
				" Index of Management Session Table."
			::= { sheSystemManagementSessionEntry 1 }

		
--  1.3.6.1.4.1.231.7.1.2.2.1.2.7.2.1.2
		sheSystemManagementSessionType OBJECT-TYPE
			SYNTAX SheSystemManagementSessionType
			MAX-ACCESS read-only
			STATUS current
			DESCRIPTION
				" Management Session Type."
			::= { sheSystemManagementSessionEntry 2 }

		
--  1.3.6.1.4.1.231.7.1.2.2.1.2.7.2.1.3
		sheSystemManagementSessionSnmpExpiredTime OBJECT-TYPE
			SYNTAX Integer32
			MAX-ACCESS read-only
			STATUS current
			DESCRIPTION
				" Only SNMP Management Session expired Time.
				If the session is Telnet, this value is 0."
			::= { sheSystemManagementSessionEntry 3 }

		
--  1.3.6.1.4.1.231.7.1.2.2.1.2.7.2.1.4
		sheSystemManagementSessionAddress OBJECT-TYPE
			SYNTAX IpAddress
			MAX-ACCESS read-only
			STATUS current
			DESCRIPTION
				" Management Session IP Address."
			::= { sheSystemManagementSessionEntry 4 } 
			
--  1.3.6.1.4.1.231.7.1.2.2.1.2.7.2.1.5
		sheSystemManagementSessionServicePort OBJECT-TYPE
			SYNTAX Integer32
			MAX-ACCESS read-only
			STATUS current
			DESCRIPTION
				" Management Session Service Port."
			::= { sheSystemManagementSessionEntry 5 } 
			
			
--  1.3.6.1.4.1.231.7.1.2.2.1.2.7.2.1.6
		sheSystemManagementSessionElapsedTime OBJECT-TYPE
			SYNTAX Integer32
			MAX-ACCESS read-only
			STATUS current
			DESCRIPTION
				" Elapsed time after management session was established."
			::= { sheSystemManagementSessionEntry 6 }
		

		
--   --------------------------------------------------------------
-- System Management Session control subgroup
-- --------------------------------------------------------------
-- 1.3.6.1.4.1.231.7.1.2.2.1.2.7.3			
		sheSystemManagementSessionControl OBJECT IDENTIFIER ::= { sheSystemManagementSession 3 }

		
--  1.3.6.1.4.1.231.7.1.2.2.1.2.7.3.1
		sheSystemManagementSessionControlRequest OBJECT-TYPE
			SYNTAX SheSystemManagementSessionControlRequestType
			MAX-ACCESS read-write
			STATUS current
			DESCRIPTION
				"  Management Session global user commands :
				
				setSnmpSessionAgingTime : configuring SNMP session aging time.
				setSnmpSessionServiceLimit : configuring Management session service limitation.
				setSnmpSessionServicePort  : configuring Management session service port
				
				Notifications: sheSystemManagementSessionChangedSnmpAgingTime
					        "
			::= { sheSystemManagementSessionControl 1 }

		
--  1.3.6.1.4.1.231.7.1.2.2.1.2.7.3.2
		sheSystemManagementSessionControlStatus OBJECT-TYPE
			SYNTAX SheControlStatusType
			MAX-ACCESS read-only
			STATUS current
			DESCRIPTION
				" The status of a control request. "
			::= { sheSystemManagementSessionControl 2 }

		
--  1.3.6.1.4.1.231.7.1.2.2.1.2.7.3.3
		sheSystemManagementSessionControlTimer OBJECT-TYPE
			SYNTAX Unsigned32
			MAX-ACCESS read-only
			STATUS current
			DESCRIPTION
				" The maximum wait time for the manager for command ending.
				For long running commands.
				The manager reads this value from the SHE. "
			::= { sheSystemManagementSessionControl 3 }

		
--  1.3.6.1.4.1.231.7.1.2.2.1.2.7.3.4
		sheSystemManagementSessionControlReqResult OBJECT-TYPE
			SYNTAX SheSystemManagementSessionControlReqResultType
			MAX-ACCESS read-only
			STATUS current
			DESCRIPTION
				" The result of the last user command. "
			::= { sheSystemManagementSessionControl 4 }

		
--  1.3.6.1.4.1.231.7.1.2.2.1.2.7.3.5
		sheSystemManagementSessionControlTimeStamp OBJECT-TYPE
			SYNTAX Unsigned32
			UNITS "sec"
			MAX-ACCESS read-only
			STATUS current
			DESCRIPTION
				" The time stamp of the last command (end of command). "
			::= { sheSystemManagementSessionControl 5 }

		
--  1.3.6.1.4.1.231.7.1.2.2.1.2.7.3.6
		sheSystemManagementSessionControlSnmpAgingTime OBJECT-TYPE
			SYNTAX Integer32 (300..3600)
			UNITS "sec"
			MAX-ACCESS read-write
			STATUS current
			DESCRIPTION
				"SNMP Session Aging Time."
			::= { sheSystemManagementSessionControl 6 }

--  1.3.6.1.4.1.231.7.1.2.2.1.2.7.3.7
		sheSystemManagementSessionControlServiceType OBJECT-TYPE
			SYNTAX SheSystemManagementSessionType
			MAX-ACCESS read-write
			STATUS current
			DESCRIPTION
				"Session Type."
			::= { sheSystemManagementSessionControl 7 }
		                                               
--  1.3.6.1.4.1.231.7.1.2.2.1.2.7.3.8
		sheSystemManagementSessionControlServiceNumber OBJECT-TYPE
			SYNTAX Integer32
			MAX-ACCESS read-write
			STATUS current
			DESCRIPTION
				"Session number."
			::= { sheSystemManagementSessionControl 8 }		                                               
			
--  1.3.6.1.4.1.231.7.1.2.2.1.2.7.3.9
		sheSystemManagementSessionControlServiceTime OBJECT-TYPE
			SYNTAX Integer32
			MAX-ACCESS read-write
			STATUS current
			DESCRIPTION
				"Session time."
			::= { sheSystemManagementSessionControl 9 }		                                               
			
--  1.3.6.1.4.1.231.7.1.2.2.1.2.7.3.10
		sheSystemManagementSessionControlServicePort OBJECT-TYPE
			SYNTAX Integer32
			MAX-ACCESS read-write
			STATUS current
			DESCRIPTION
				"Session L4 port."
			::= { sheSystemManagementSessionControl 10 }				
			
			
--   --------------------------------------------------------------
-- System Management Session notification subgroup
-- --------------------------------------------------------------
-- 1.3.6.1.4.1.231.7.1.2.2.1.2.7.4
		sheSystemManagementSessionNotifications OBJECT IDENTIFIER ::= { sheSystemManagementSession 4 }

		
--  1.3.6.1.4.1.231.7.1.2.2.1.2.7.4.1
		sheSystemManagementSessionConnection NOTIFICATION-TYPE
			OBJECTS { sheSystemManagementSessionType, sheSystemManagementSessionSnmpExpiredTime, sheSystemManagementSessionAddress }
			STATUS current
			DESCRIPTION 
				"Management Session Connect event.
				When a new session is detected, the event occurs."
			::= { sheSystemManagementSessionNotifications 1 }

		
--  1.3.6.1.4.1.231.7.1.2.2.1.2.7.4.2
		sheSystemManagementSessionDisconnection NOTIFICATION-TYPE
			OBJECTS { sheSystemManagementSessionType, sheSystemManagementSessionSnmpExpiredTime, sheSystemManagementSessionAddress }
			STATUS current
			DESCRIPTION 
				"Management Session Disonnect event.
				When an existing session is diconnected, the event occurs.
				In case of SNMP sessions, when SNMP aging timer is expired, disconnection decision."
			::= { sheSystemManagementSessionNotifications 2 }

		
--  1.3.6.1.4.1.231.7.1.2.2.1.2.7.4.3
		sheSystemManagementSessionChangedSnmpAgingTime NOTIFICATION-TYPE
			OBJECTS { sheSystemManagementSessionControlSnmpAgingTime }
			STATUS current
			DESCRIPTION 
				"SNMP Management Session Aging Time Change Event."
			::= { sheSystemManagementSessionNotifications 3 }  
			
--  1.3.6.1.4.1.231.7.1.2.2.1.2.7.4.4
		sheSystemManagementSessionChangedServiceLimit NOTIFICATION-TYPE
			OBJECTS { sheSystemManagementSessionControlServiceType, sheSystemManagementSessionControlServiceNumber,  sheSystemManagementSessionControlServiceTime }
			STATUS current
			DESCRIPTION 
				"Management Session Service Limit Change Event."
			::= { sheSystemManagementSessionNotifications 4 }			

--  1.3.6.1.4.1.231.7.1.2.2.1.2.7.4.5
		sheSystemManagementSessionChangedServicePort NOTIFICATION-TYPE
			OBJECTS { sheSystemManagementSessionControlServiceType, sheSystemManagementSessionControlServicePort }
			STATUS current
			DESCRIPTION 
				"Management Session Service Port Change Event."
			::= { sheSystemManagementSessionNotifications 5 }	 
 
-- 1.3.6.1.4.1.231.7.1.2.2.1.2.7.5
		sheSystemManagementSessionTelnetNumber OBJECT-TYPE
			SYNTAX Integer32
			MAX-ACCESS read-only
			STATUS current
			DESCRIPTION
				"The number limit of telnet management session."
			::= { sheSystemManagementSession 5 }

-- 1.3.6.1.4.1.231.7.1.2.2.1.2.7.6
		sheSystemManagementSessionTelnetTime OBJECT-TYPE
			SYNTAX Integer32
			UNITS "sec"
			MAX-ACCESS read-only
			STATUS current
			DESCRIPTION
				"The time limit of telnet management session."
			::= { sheSystemManagementSession 6 }


-- 1.3.6.1.4.1.231.7.1.2.2.1.2.7.7
		sheSystemManagementSessionSshNumber OBJECT-TYPE
			SYNTAX Integer32
			MAX-ACCESS read-only
			STATUS current
			DESCRIPTION
				"The number limit of SSH management session."
			::= { sheSystemManagementSession 7 }

-- 1.3.6.1.4.1.231.7.1.2.2.1.2.7.8
		sheSystemManagementSessionSshTime OBJECT-TYPE
			SYNTAX Integer32  
			UNITS "sec"
			MAX-ACCESS read-only
			STATUS current
			DESCRIPTION
				"The time limit of SSH management session."
			::= { sheSystemManagementSession 8 }



		
--  1.3.6.1.4.1.231.7.1.2.2.1.2.8
		sheSystemConfigLog OBJECT IDENTIFIER ::= { sheSystem 8 }

		
--   --------------------------------------------------------------
-- System Config Log group 
-- --------------------------------------------------------------
-- 1.3.6.1.4.1.231.7.1.2.2.1.2.8.1
		sheSystemConfigLogGroup OBJECT IDENTIFIER ::= { sheSystemConfigLog 1 }

		
--  1.3.6.1.4.1.231.7.1.2.2.1.2.8.1.1
		sheSystemConfigLogEntryNumber OBJECT-TYPE
			SYNTAX Integer32 (0..1000)
			MAX-ACCESS read-only
			STATUS current
			DESCRIPTION
				"The number of the configuration log entries to keep.
				0: disable configuration logging
				"
			DEFVAL { 500 }
			::= { sheSystemConfigLogGroup 1 }

		
--  1.3.6.1.4.1.231.7.1.2.2.1.2.8.1.2
		sheSystemConfigLogFtpServerAddress OBJECT-TYPE
			SYNTAX IpAddress
			MAX-ACCESS read-only
			STATUS current
			DESCRIPTION
				"FTP server's IP address to which log file will be transferred.
				Default:0.0.0.0
				0.0.0.0: disable FTP transfer
				"
			::= { sheSystemConfigLogGroup 2 }

		
--  1.3.6.1.4.1.231.7.1.2.2.1.2.8.1.3
		sheSystemConfigLogFtpUser OBJECT-TYPE
			SYNTAX OCTET STRING (SIZE (0..128))
			MAX-ACCESS read-only
			STATUS current
			DESCRIPTION
				"User ID for FTP server.
				
				Merge-Info:
				Element is not needed. Read-access will report an empty string."
			::= { sheSystemConfigLogGroup 3 }

		
--  1.3.6.1.4.1.231.7.1.2.2.1.2.8.1.4
		sheSystemConfigLogFtpPassword OBJECT-TYPE
			SYNTAX OCTET STRING (SIZE (0..128))
			MAX-ACCESS read-only
			STATUS current
			DESCRIPTION
				"Password for FTP server.
				
				Merge-Info:
				Element is not needed. Read-access will report an empty string."
			::= { sheSystemConfigLogGroup 4 }

		
--  1.3.6.1.4.1.231.7.1.2.2.1.2.8.1.5
		sheSystemConfigLogFtpInterval OBJECT-TYPE
			SYNTAX Integer32 (0..2147483647)
			UNITS "sec"
			MAX-ACCESS read-only
			STATUS current
			DESCRIPTION
				"Timer interval between FTP transfers of log in second
				0: disable FTP transfer
				"
			DEFVAL { 300 }
			::= { sheSystemConfigLogGroup 5 }

		
--  1.3.6.1.4.1.231.7.1.2.2.1.2.8.1.6
		sheSystemConfigLogFtpPathName OBJECT-TYPE
			SYNTAX OCTET STRING (SIZE (0..128))
			MAX-ACCESS read-only
			STATUS current
			DESCRIPTION
				"Path name of file on FTP server. This path should be set relative to the ftp-server root. Use only linux notation ( / )."
			DEFVAL { "/" }
			::= { sheSystemConfigLogGroup 6 }

		
--  1.3.6.1.4.1.231.7.1.2.2.1.2.8.2
		sheSystemConfigLogControl OBJECT IDENTIFIER ::= { sheSystemConfigLog 2 }

		
--  1.3.6.1.4.1.231.7.1.2.2.1.2.8.2.1
		sheSystemConfigLogControlRequest OBJECT-TYPE
			SYNTAX SheSystemConfigLogControlRequestType
			MAX-ACCESS read-write
			STATUS current
			DESCRIPTION
				"Config log global user commands"
			::= { sheSystemConfigLogControl 1 }

		
--  1.3.6.1.4.1.231.7.1.2.2.1.2.8.2.2
		sheSystemConfigLogControlEntryNumber OBJECT-TYPE
			SYNTAX Integer32 (0..1000)
			MAX-ACCESS read-write
			STATUS current
			DESCRIPTION
				"The number of the configuration log entries to keep"
			::= { sheSystemConfigLogControl 2 }

		
--  1.3.6.1.4.1.231.7.1.2.2.1.2.8.2.3
		sheSystemConfigLogControlFtpAddress OBJECT-TYPE
			SYNTAX IpAddress
			MAX-ACCESS read-write
			STATUS current
			DESCRIPTION
				"FTP server's IP address to which log file will be transferred"
			::= { sheSystemConfigLogControl 3 }

		
--  1.3.6.1.4.1.231.7.1.2.2.1.2.8.2.4
		sheSystemConfigLogControlFtpUser OBJECT-TYPE
			SYNTAX OCTET STRING (SIZE (0..128))
			MAX-ACCESS read-write
			STATUS current
			DESCRIPTION
				"User ID for FTP server.
				Read-access will report an empty string. "
			::= { sheSystemConfigLogControl 4 }

		
--  1.3.6.1.4.1.231.7.1.2.2.1.2.8.2.5
		sheSystemConfigLogControlFtpPassword OBJECT-TYPE
			SYNTAX OCTET STRING (SIZE (0..128))
			MAX-ACCESS read-write
			STATUS current
			DESCRIPTION
				"Password for FTP server.
				Read-access will report an empty string."
			::= { sheSystemConfigLogControl 5 }

		
--  1.3.6.1.4.1.231.7.1.2.2.1.2.8.2.6
		sheSystemConfigLogControlFtpInterval OBJECT-TYPE
			SYNTAX Integer32 (0..2147483647)
			UNITS "sec"
			MAX-ACCESS read-write
			STATUS current
			DESCRIPTION
				"Timer interval between FTP transfers of log in second
				0: disable FTP transfer
				"
			::= { sheSystemConfigLogControl 6 }

		
--  1.3.6.1.4.1.231.7.1.2.2.1.2.8.2.7
		sheSystemConfigLogControlFtpPathName OBJECT-TYPE
			SYNTAX OCTET STRING (SIZE (0..128))
			MAX-ACCESS read-write
			STATUS current
			DESCRIPTION
				"Path name of file on FTP server. This path should be set relative to the ftp-server root. Use only linux notation ( / )."
			DEFVAL { "/" }
			::= { sheSystemConfigLogControl 7 }

		
--  1.3.6.1.4.1.231.7.1.2.2.1.2.8.2.8
		sheSystemConfigLogControlReqResult OBJECT-TYPE
			SYNTAX SheSystemControlRequestResultType
			MAX-ACCESS read-only
			STATUS current
			DESCRIPTION
				" The result of the last user command. "
			::= { sheSystemConfigLogControl 8 }

		
--  1.3.6.1.4.1.231.7.1.2.2.1.2.8.2.9
		sheSystemConfigLogControlStatus OBJECT-TYPE
			SYNTAX SheControlStatusType
			MAX-ACCESS read-only
			STATUS current
			DESCRIPTION
				" The status of a control request. "
			::= { sheSystemConfigLogControl 9 }

		
--  1.3.6.1.4.1.231.7.1.2.2.1.2.8.2.10
		sheSystemConfigLogControlTimeStamp OBJECT-TYPE
			SYNTAX Unsigned32
			UNITS "sec"
			MAX-ACCESS read-only
			STATUS current
			DESCRIPTION
				" The time stamp of the last command (end of command). "
			::= { sheSystemConfigLogControl 10 }

		
--  1.3.6.1.4.1.231.7.1.2.2.1.2.8.3
		sheSystemConfigLogNotifications OBJECT IDENTIFIER ::= { sheSystemConfigLog 3 }

		
--  1.3.6.1.4.1.231.7.1.2.2.1.2.8.3.1
		sheSystemConfigLogEntryNumberChanged NOTIFICATION-TYPE
			OBJECTS { sheSystemConfigLogEntryNumber }
			STATUS current
			DESCRIPTION 
				"Config entry number to keep is changed."
			::= { sheSystemConfigLogNotifications 1 }

		
--  1.3.6.1.4.1.231.7.1.2.2.1.2.8.3.2
		sheSystemConfigLogFtpLoginInfoChanged NOTIFICATION-TYPE
			OBJECTS { sheSystemConfigLogFtpServerAddress, sheSystemConfigLogFtpUser, sheSystemConfigLogFtpPassword, sheSystemConfigLogFtpPathName }
			STATUS current
			DESCRIPTION 
				"FTP server address and login information is changed."
			::= { sheSystemConfigLogNotifications 2 }

		
--  1.3.6.1.4.1.231.7.1.2.2.1.2.8.3.3
		sheSystemConfigLogFtpIntervalChanged NOTIFICATION-TYPE
			OBJECTS { sheSystemConfigLogFtpInterval }
			STATUS current
			DESCRIPTION 
				"Timer interval is changed."
			::= { sheSystemConfigLogNotifications 3 }

		
-- --------------------------------------------------------------
-- System Auto Config Backup group 
-- --------------------------------------------------------------
-- 1.3.6.1.4.1.231.7.1.2.2.1.2.9
-- 
-- Only contained for backward compatibility. 
-- Will never be supported by SHE R2.5 or higher!
		sheSystemAutoConfigBackup OBJECT IDENTIFIER ::= { sheSystem 9 }

		
--  1.3.6.1.4.1.231.7.1.2.2.1.2.9.1
		sheSystemAutoConfigBackupGroup OBJECT IDENTIFIER ::= { sheSystemAutoConfigBackup 1 }

		
--  1.3.6.1.4.1.231.7.1.2.2.1.2.9.1.1
		sheSystemAutoConfigBackupEnabled OBJECT-TYPE
			SYNTAX TruthValue
			MAX-ACCESS read-only
			STATUS current
			DESCRIPTION
				"Enable/disable auto configuration backup feature
				true: enable
				false: disable
				"
			DEFVAL { false }
			::= { sheSystemAutoConfigBackupGroup 1 }

		
--  1.3.6.1.4.1.231.7.1.2.2.1.2.9.1.2
		sheSystemAutoConfigBackupFtpServerAddress OBJECT-TYPE
			SYNTAX IpAddress
			MAX-ACCESS read-only
			STATUS current
			DESCRIPTION
				"FTP server's IP address to which config file will be transferred.
				Default:0.0.0.0
				0.0.0.0: disable FTP transfer
				"
			::= { sheSystemAutoConfigBackupGroup 2 }

		
--  1.3.6.1.4.1.231.7.1.2.2.1.2.9.1.3
		sheSystemAutoConfigBackupFtpUser OBJECT-TYPE
			SYNTAX OCTET STRING (SIZE (128))
			MAX-ACCESS read-only
			STATUS current
			DESCRIPTION
				"User ID for FTP server"
			::= { sheSystemAutoConfigBackupGroup 3 }

		
--  1.3.6.1.4.1.231.7.1.2.2.1.2.9.1.4
		sheSystemAutoConfigBackupFtpPassword OBJECT-TYPE
			SYNTAX OCTET STRING (SIZE (128))
			MAX-ACCESS read-only
			STATUS current
			DESCRIPTION
				"Password for FTP server"
			::= { sheSystemAutoConfigBackupGroup 4 }

		
--  1.3.6.1.4.1.231.7.1.2.2.1.2.9.1.5
		sheSystemAutoConfigBackupFtpPathName OBJECT-TYPE
			SYNTAX OCTET STRING (SIZE (128))
			MAX-ACCESS read-only
			STATUS current
			DESCRIPTION
				"Path name of file on FTP server. This path should be set relative to the ftp-server root. Use only linux notation ( / )
				Default: /
				"
			DEFVAL { "/" }
			::= { sheSystemAutoConfigBackupGroup 5 }

		
--  1.3.6.1.4.1.231.7.1.2.2.1.2.9.1.6
		sheSystemAutoConfigBackupTime OBJECT-TYPE
			SYNTAX Integer32 (30..2147483647)
			UNITS "sec"
			MAX-ACCESS read-only
			STATUS current
			DESCRIPTION
				"It indicates a time that ftp backup should be performed since autoconfiguration has been set."
			DEFVAL { 300 }
			::= { sheSystemAutoConfigBackupGroup 6 }

		
--  1.3.6.1.4.1.231.7.1.2.2.1.2.9.2
		sheSystemAutoConfigBackupControl OBJECT IDENTIFIER ::= { sheSystemAutoConfigBackup 2 }

		
--  1.3.6.1.4.1.231.7.1.2.2.1.2.9.2.1			                      
		sheSystemAutoConfigBackupControlRequest OBJECT-TYPE
			SYNTAX SheSystemAutoConfigBackupControlRequest
			MAX-ACCESS read-write
			STATUS current
			DESCRIPTION
				"AutoConfigBackup global user commands"
			::= { sheSystemAutoConfigBackupControl 1 }

		
--  1.3.6.1.4.1.231.7.1.2.2.1.2.9.2.2
		sheSystemAutoConfigBackupControlEnabled OBJECT-TYPE
			SYNTAX TruthValue
			MAX-ACCESS read-write
			STATUS current
			DESCRIPTION
				"Enable/disable auto configuration backup feature
				true: enabled
				false: disabled
				"
			DEFVAL { false }
			::= { sheSystemAutoConfigBackupControl 2 }

		
--  1.3.6.1.4.1.231.7.1.2.2.1.2.9.2.3
		sheSystemAutoConfigBackupControlFtpServerAddress OBJECT-TYPE
			SYNTAX IpAddress
			MAX-ACCESS read-write
			STATUS current
			DESCRIPTION
				"FTP server's IP address to which config file will be transferred."
			::= { sheSystemAutoConfigBackupControl 3 }

		
--  1.3.6.1.4.1.231.7.1.2.2.1.2.9.2.4
		sheSystemAutoConfigBackupControlFtpUser OBJECT-TYPE
			SYNTAX OCTET STRING (SIZE (128))
			MAX-ACCESS read-write
			STATUS current
			DESCRIPTION
				"User ID for FTP server"
			::= { sheSystemAutoConfigBackupControl 4 }

		
--  1.3.6.1.4.1.231.7.1.2.2.1.2.9.2.5
		sheSystemAutoConfigBackupControlFtpPassword OBJECT-TYPE
			SYNTAX OCTET STRING (SIZE (128))
			MAX-ACCESS read-write
			STATUS current
			DESCRIPTION
				"Password for FTP server"
			::= { sheSystemAutoConfigBackupControl 5 }

		
--  1.3.6.1.4.1.231.7.1.2.2.1.2.9.2.6
		sheSystemAutoConfigBackupControlFtpPathName OBJECT-TYPE
			SYNTAX OCTET STRING (SIZE (128))
			MAX-ACCESS read-write
			STATUS current
			DESCRIPTION
				"Path name of file on FTP server. This path should be set relative to the ftp-server root. Use only linux notation ( / ).
				Default: /
				"
			::= { sheSystemAutoConfigBackupControl 6 }

		
--  1.3.6.1.4.1.231.7.1.2.2.1.2.9.2.7
		sheSystemAutoConfigBackupControlBackupTime OBJECT-TYPE
			SYNTAX Integer32 (30..2147483647)
			MAX-ACCESS read-write
			STATUS current
			DESCRIPTION
				"It indicates a time that ftp backup should be performed since autoconfiguration has been set."
			::= { sheSystemAutoConfigBackupControl 7 }

		
--  1.3.6.1.4.1.231.7.1.2.2.1.2.9.3
		sheSystemAutoConfigBackupNotifications OBJECT IDENTIFIER ::= { sheSystemAutoConfigBackup 3 }

		
--  1.3.6.1.4.1.231.7.1.2.2.1.2.9.3.1
		sheSystemAutoConfigBackupEnabledChanged NOTIFICATION-TYPE
			OBJECTS { sheSystemAutoConfigBackupEnabled }
			STATUS current
			DESCRIPTION 
				"Auto configuration backup is enabled or disabled."
			::= { sheSystemAutoConfigBackupNotifications 1 }

		
--  1.3.6.1.4.1.231.7.1.2.2.1.2.9.3.2
		sheSystemAutoConfigBackupFtpLoginInfoChanged NOTIFICATION-TYPE
			OBJECTS { sheSystemAutoConfigBackupFtpServerAddress, sheSystemAutoConfigBackupFtpUser, sheSystemAutoConfigBackupFtpPassword, sheSystemAutoConfigBackupFtpPathName }
			STATUS current
			DESCRIPTION 
				"FTP server address and login information is changed."
			::= { sheSystemAutoConfigBackupNotifications 2 }

		
--  1.3.6.1.4.1.231.7.1.2.2.1.2.9.3.3
		sheSystemAutoConfigBackupTimeChanged NOTIFICATION-TYPE
			OBJECTS { sheSystemAutoConfigBackupTime }
			STATUS current
			DESCRIPTION 
				"Config backup time is changed."
			::= { sheSystemAutoConfigBackupNotifications 3 }

		
		sheSystemSnmp OBJECT IDENTIFIER ::= { sheSystem 10 }

		
		sheSystemNotificationCounter OBJECT-TYPE
			SYNTAX Unsigned32
			MAX-ACCESS read-only
			STATUS current
			DESCRIPTION
				"Number of last sended notification.
				
				This OID is last member of each sended notification from SHE NE. A TMN system should
				now be able to check, if all notification were received and if not a consistency check 
				could be performed.
				"
			::= { sheSystemSnmp 1 }     
			
		
		sheSystemSnmpInfo  OBJECT IDENTIFIER ::= { sheSystemSnmp 11 }        
		
		sheSystemSnmpBase  OBJECT IDENTIFIER ::= { sheSystemSnmpInfo 1 }
		
		sheSystemSnmpAgentAddress OBJECT-TYPE
			SYNTAX IpAddress
			MAX-ACCESS read-only
			STATUS current
			DESCRIPTION
				"Snmp agent address
				If this value is setted, sleAgentInterface value is NULL
				"
			::= { sheSystemSnmpBase 1 }
		
		sheSystemSnmpAgentInterface OBJECT-TYPE
			SYNTAX OCTET STRING
			MAX-ACCESS read-only
			STATUS current
			DESCRIPTION
				"Snmp agent interface
				If this value is setted, sleAgentAddress value is 0
				"
			::= { sheSystemSnmpBase 2 }

		sheSystemSnmpTrapSourceAddress OBJECT-TYPE
			SYNTAX IpAddress
			MAX-ACCESS read-only
			STATUS current
			DESCRIPTION
				"Snmp Trap Source address
				If this value is setted, sleTrapSourceInterface value is NULL
				"
			::= { sheSystemSnmpBase 3 }
			

		sheSystemSnmpTrapSourceInterface OBJECT-TYPE
			SYNTAX OCTET STRING
			MAX-ACCESS read-only
			STATUS current
			DESCRIPTION
				"Snmp Trap Source interface
				If this value is setted, sleTrapSourceAddress value is 0
				"
			::= { sheSystemSnmpBase 4 }   
			
			
		sheSystemSnmpBaseControl OBJECT IDENTIFIER ::= { sheSystemSnmpInfo 2 }
		
		sheSystemSnmpBaseControlRequest OBJECT-TYPE
			SYNTAX INTEGER
				{
				setSnmpAgentAddress(1),
				setSnmpAgentInterface(2),
				setSnmpTrapSourceAddress(3),
				setSnmpTrapSourceInterface(4)			
				}
			MAX-ACCESS read-write
			STATUS current
			DESCRIPTION
				"Description."
			::= { sheSystemSnmpBaseControl 1 }

		sheSystemSnmpBaseControlStatus OBJECT-TYPE
			SYNTAX SheControlStatusType
			MAX-ACCESS read-only
			STATUS current
			DESCRIPTION
				"Description."
			::= { sheSystemSnmpBaseControl 2 }

		
		sheSystemSnmpBaseControlControlTimer OBJECT-TYPE
			SYNTAX Gauge32
			MAX-ACCESS read-write
			STATUS current
			DESCRIPTION
				"Description."
			::= { sheSystemSnmpBaseControl 3 }

		
		sheSystemSnmpBaseControlTimeStamp OBJECT-TYPE
			SYNTAX TimeTicks
			MAX-ACCESS read-only
			STATUS current
			DESCRIPTION
				"Description."
			::= { sheSystemSnmpBaseControl 4 }

		
		sheSystemSnmpBaseControlReqResult OBJECT-TYPE
			SYNTAX SheSystemControlRequestResultType
			MAX-ACCESS read-only
			STATUS current
			DESCRIPTION
				"Description."
			::= { sheSystemSnmpBaseControl 5 }


		sheSystemSnmpBaseControlAgentAddress OBJECT-TYPE
			SYNTAX IpAddress
			MAX-ACCESS read-write
			STATUS current
			DESCRIPTION
				""
			::= { sheSystemSnmpBaseControl 6 }
 
		sheSystemSnmpBaseControlAgentInterface OBJECT-TYPE
			SYNTAX OCTET STRING
			MAX-ACCESS read-write
			STATUS current
			DESCRIPTION
				""
			::= { sheSystemSnmpBaseControl 7 }
 
		
		sheSystemSnmpBaseControlTrapSourceAddress OBJECT-TYPE
			SYNTAX IpAddress
			MAX-ACCESS read-write
			STATUS current
			DESCRIPTION
				"Snmp trap source interface"
			::= { sheSystemSnmpBaseControl 8 }


		sheSystemSnmpBaseControlTrapSourceInterface OBJECT-TYPE
			SYNTAX OCTET STRING
			MAX-ACCESS read-write
			STATUS current
			DESCRIPTION
				"Snmp trap source interface"
			::= { sheSystemSnmpBaseControl 9 }
		
		
		sheSystemSnmpInfoNotification OBJECT IDENTIFIER ::= { sheSystemSnmpInfo 3 }
		

-- community		
		sheSystemSnmpCommunity  OBJECT IDENTIFIER ::= { sheSystemSnmp 12 } 
		
		
		sheSystemSnmpCommunityTable OBJECT-TYPE
			SYNTAX SEQUENCE OF SheSystemSnmpCommunityEntry
			MAX-ACCESS not-accessible
			STATUS current
			DESCRIPTION
				"Description."
			::= { sheSystemSnmpCommunity 1 }

		
		sheSystemSnmpCommunityEntry OBJECT-TYPE
			SYNTAX SheSystemSnmpCommunityEntry
			MAX-ACCESS not-accessible
			STATUS current
			DESCRIPTION
				"Description."
			INDEX { sheSystemSnmpCommunityType, sheSystemSnmpCommunityValue }
			::= { sheSystemSnmpCommunityTable 1 }

		
		SheSystemSnmpCommunityEntry ::=
			SEQUENCE { 
				sheSystemSnmpCommunityType
					INTEGER,
				sheSystemSnmpCommunityValue
					OCTET STRING,
				sheSystemSnmpCommunityHost
					IpAddress,
				sheSystemSnmpCommunityOID
					OBJECT IDENTIFIER,
				sheSystemSnmpCommunityHostMaskLen
					Integer32
			 }

		sheSystemSnmpCommunityType OBJECT-TYPE
			SYNTAX INTEGER
				{
				readonly(1),
				readwrite(2)
				}
			MAX-ACCESS read-only
			STATUS current
			DESCRIPTION
				"Community Type"
			::= { sheSystemSnmpCommunityEntry 1 }

		
		sheSystemSnmpCommunityValue OBJECT-TYPE
			SYNTAX OCTET STRING
			MAX-ACCESS read-only
			STATUS current
			DESCRIPTION
				"Community key"
			::= { sheSystemSnmpCommunityEntry 2 }

		
		-- 1.3.6.1.4.1.6296.101.8.4.1.1.3
		sheSystemSnmpCommunityHost OBJECT-TYPE
			SYNTAX IpAddress
			MAX-ACCESS read-only
			STATUS current
			DESCRIPTION
				"Accessable host address"
			::= { sheSystemSnmpCommunityEntry 3 }

		
		sheSystemSnmpCommunityOID OBJECT-TYPE
			SYNTAX OBJECT IDENTIFIER
			MAX-ACCESS read-only
			STATUS current
			DESCRIPTION
				"Accessable Object ID"
			::= { sheSystemSnmpCommunityEntry 4 }

		
		sheSystemSnmpCommunityHostMaskLen OBJECT-TYPE
			SYNTAX Integer32
			MAX-ACCESS read-only
			STATUS current
			DESCRIPTION
				"Mask length for host address"
			::= { sheSystemSnmpCommunityEntry 5 }

		
		sheSystemSnmpCommunityControl OBJECT IDENTIFIER ::= { sheSystemSnmpCommunity 2 }

		sheSystemSnmpCommunityControlRequest OBJECT-TYPE
			SYNTAX INTEGER
				{
				createCommunity(1),
				destroyCommunity(2)
				}
			MAX-ACCESS read-write
			STATUS current
			DESCRIPTION
				"Description."
			::= { sheSystemSnmpCommunityControl 1 }

		
		sheSystemSnmpCommunityControlStatus OBJECT-TYPE
			SYNTAX SheControlStatusType
			MAX-ACCESS read-only
			STATUS current
			DESCRIPTION
				"Description."
			::= { sheSystemSnmpCommunityControl 2 }

		
		sheSystemSnmpCommunityControlTimer OBJECT-TYPE
			SYNTAX Gauge32
			MAX-ACCESS read-write
			STATUS current
			DESCRIPTION
				"Description."
			::= { sheSystemSnmpCommunityControl 3 }

		
		sheSystemSnmpCommunityControlTimeStamp OBJECT-TYPE
			SYNTAX TimeTicks
			MAX-ACCESS read-only
			STATUS current
			DESCRIPTION
				"Description."
			::= { sheSystemSnmpCommunityControl 4 }

		
		sheSystemSnmpCommunityControlReqResult OBJECT-TYPE
			SYNTAX SheSystemControlRequestResultType
			MAX-ACCESS read-only
			STATUS current
			DESCRIPTION
				"Result of the last command"
			::= { sheSystemSnmpCommunityControl 5 }


		sheSystemSnmpCommunityControlType OBJECT-TYPE
			SYNTAX INTEGER
				{
				readonly(1),
				readwrite(2)
				}
			MAX-ACCESS read-write
			STATUS current
			DESCRIPTION
				"Community Type"
			::= { sheSystemSnmpCommunityControl 6 }


		sheSystemSnmpCommunityControlValue OBJECT-TYPE
			SYNTAX OCTET STRING
			MAX-ACCESS read-write
			STATUS current
			DESCRIPTION
				"Community key"
			::= { sheSystemSnmpCommunityControl 7 }


		sheSystemSnmpCommunityControlHost OBJECT-TYPE
			SYNTAX IpAddress
			MAX-ACCESS read-write
			STATUS current
			DESCRIPTION
				"Accessable host address"
			::= { sheSystemSnmpCommunityControl 8 }

		sheSystemSnmpCommunityControlOID OBJECT-TYPE
			SYNTAX OBJECT IDENTIFIER
			MAX-ACCESS read-write
			STATUS current
			DESCRIPTION
				"Accessable Object ID"
			::= { sheSystemSnmpCommunityControl 9 }

		
		sheSystemSnmpCommunityControlHostMaskLen OBJECT-TYPE
			SYNTAX Integer32
			MAX-ACCESS read-write
			STATUS current
			DESCRIPTION
				"Mask length for host address"
			::= { sheSystemSnmpCommunityControl 10 }

		sheSystemSnmpCommunityNotification OBJECT IDENTIFIER ::= { sheSystemSnmpCommunity 3 }

		
		
		sheSystemSnmpTrapHost  OBJECT IDENTIFIER ::= { sheSystemSnmp 13 } 
	
		sheSystemSnmpTrapHostTable OBJECT-TYPE
			SYNTAX SEQUENCE OF SheSystemSnmpTrapHostEntry
			MAX-ACCESS not-accessible
			STATUS current
			DESCRIPTION
				"Description."
			::= { sheSystemSnmpTrapHost 1 }

		
		sheSystemSnmpTrapHostEntry OBJECT-TYPE
			SYNTAX SheSystemSnmpTrapHostEntry
			MAX-ACCESS not-accessible
			STATUS current
			DESCRIPTION
				"Description."
			INDEX { sheSystemSnmpTrapHostType, sheSystemSnmpTrapHostAddress }
			::= { sheSystemSnmpTrapHostTable 1 }

		
		SheSystemSnmpTrapHostEntry ::=
			SEQUENCE { 
				sheSystemSnmpTrapHostType
					INTEGER,
				sheSystemSnmpTrapHostAddress
					IpAddress,
				sheSystemSnmpTrapHostCommunity
					OCTET STRING,
				sheSystemSnmpTrapHostPort
					Integer32
			 }

		sheSystemSnmpTrapHostType OBJECT-TYPE
			SYNTAX INTEGER
				{
				trapHost(1),
				trap2Host(2),
				informTrapHost(3),
				trap3Host(4)
				}
			MAX-ACCESS read-only
			STATUS current
			DESCRIPTION
				"Description."
			::= { sheSystemSnmpTrapHostEntry 1 }

		
		sheSystemSnmpTrapHostAddress OBJECT-TYPE
			SYNTAX IpAddress
			MAX-ACCESS read-only
			STATUS current
			DESCRIPTION
				"Host address for received traps"
			::= { sheSystemSnmpTrapHostEntry 2 }

		
		sheSystemSnmpTrapHostCommunity OBJECT-TYPE
			SYNTAX OCTET STRING
			MAX-ACCESS read-only
			STATUS current
			DESCRIPTION
				"Trap commnity"
			::= { sheSystemSnmpTrapHostEntry 3 }

		
		sheSystemSnmpTrapHostPort OBJECT-TYPE
			SYNTAX Integer32
			MAX-ACCESS read-only
			STATUS current
			DESCRIPTION
				"Trap commnunication port. (advanced)"
			::= { sheSystemSnmpTrapHostEntry 4 }

		
		sheSystemSnmpTrapHostControl OBJECT IDENTIFIER ::= { sheSystemSnmpTrapHost 2 }

		
		sheSystemSnmpTrapHostControlRequest OBJECT-TYPE
			SYNTAX INTEGER
				{
				createTrapHost(1),
				destroyTrapHost(2)
				}
			MAX-ACCESS read-write
			STATUS current
			DESCRIPTION
				"Description."
			::= { sheSystemSnmpTrapHostControl 1 }

		
		sheSystemSnmpTrapHostControlStatus OBJECT-TYPE
			SYNTAX SheControlStatusType
			MAX-ACCESS read-only
			STATUS current
			DESCRIPTION
				"Description."
			::= { sheSystemSnmpTrapHostControl 2 }

		
		sheSystemSnmpTrapHostControlTimer OBJECT-TYPE
			SYNTAX Gauge32
			MAX-ACCESS read-write
			STATUS current
			DESCRIPTION
				"Description."
			::= { sheSystemSnmpTrapHostControl 3 }

		
		sheSystemSnmpTrapHostControlTimeStamp OBJECT-TYPE
			SYNTAX TimeTicks
			MAX-ACCESS read-only
			STATUS current
			DESCRIPTION
				"Description."
			::= { sheSystemSnmpTrapHostControl 4 }

		
		sheSystemSnmpTrapHostControlReqResult OBJECT-TYPE
			SYNTAX SheSystemControlRequestResultType
			MAX-ACCESS read-only
			STATUS current
			DESCRIPTION
				"Description."
			::= { sheSystemSnmpTrapHostControl 5 }

		
		sheSystemSnmpTrapHostControlType OBJECT-TYPE
			SYNTAX INTEGER
				{
				trapHost(1),
				trap2Host(2),
				informTrapHost(3),
				trap3Host(4)
				}
			MAX-ACCESS read-write
			STATUS current
			DESCRIPTION
				"Description."
			::= { sheSystemSnmpTrapHostControl 6 }

		
		sheSystemSnmpTrapHostControlAddress OBJECT-TYPE
			SYNTAX IpAddress
			MAX-ACCESS read-write
			STATUS current
			DESCRIPTION
				"Host address for received traps"
			::= { sheSystemSnmpTrapHostControl 7 }

		
		sheSystemSnmpTrapHostControlCommunity OBJECT-TYPE
			SYNTAX OCTET STRING
			MAX-ACCESS read-write
			STATUS current
			DESCRIPTION
				"Description."
			::= { sheSystemSnmpTrapHostControl 8 }

		
		sheSystemSnmpTrapHostControlPort OBJECT-TYPE
			SYNTAX INTEGER (0..65535)
			MAX-ACCESS read-write
			STATUS current
			DESCRIPTION
				"Description."
			::= { sheSystemSnmpTrapHostControl 9 }

		
		sheSystemSnmpTrapHostNotification OBJECT IDENTIFIER ::= { sheSystemSnmpTrapHost 3 }

		
		
		
		sheSystemSnmpViewTreeFamily  OBJECT IDENTIFIER ::= { sheSystemSnmp 14 } 
		
		sheSystemSnmpViewTreeFamilyTable OBJECT-TYPE
			SYNTAX SEQUENCE OF SheSystemSnmpViewTreeFamilyEntry
			MAX-ACCESS not-accessible
			STATUS current
			DESCRIPTION
				"Description."
			::= { sheSystemSnmpViewTreeFamily 1 }

		
		sheSystemSnmpViewTreeFamilyEntry OBJECT-TYPE
			SYNTAX SheSystemSnmpViewTreeFamilyEntry
			MAX-ACCESS not-accessible
			STATUS current
			DESCRIPTION
				"Description."
			INDEX { sheSystemSnmpViewTreeFamilyName, sheSystemSnmpViewTreeFamilySubtree }
			::= { sheSystemSnmpViewTreeFamilyTable 1 }

		
		SheSystemSnmpViewTreeFamilyEntry ::=
			SEQUENCE { 
				sheSystemSnmpViewTreeFamilyName
					OCTET STRING,
				sheSystemSnmpViewTreeFamilySubtree
					OBJECT IDENTIFIER,
				sheSystemSnmpViewTreeFamilyMask
					OCTET STRING,
				sheSystemSnmpViewTreeFamilyType
					INTEGER
			 }

		sheSystemSnmpViewTreeFamilyName OBJECT-TYPE
			SYNTAX OCTET STRING
			MAX-ACCESS read-only
			STATUS current
			DESCRIPTION
				"View Name"
			::= { sheSystemSnmpViewTreeFamilyEntry 1 }

		
		sheSystemSnmpViewTreeFamilySubtree OBJECT-TYPE
			SYNTAX OBJECT IDENTIFIER
			MAX-ACCESS read-only
			STATUS current
			DESCRIPTION
				"The MIB subtree which when combined with 
				the corresponding instance of ViewTreeFamilyMask 
				defines a family of view subtrees."
			::= { sheSystemSnmpViewTreeFamilyEntry 2 }

		
		sheSystemSnmpViewTreeFamilyMask OBJECT-TYPE
			SYNTAX OCTET STRING
			MAX-ACCESS read-only
			STATUS current
			DESCRIPTION
				"The bit mask which, in combination with 
				the corresponding instance of ViewTreeFamilySubtree,
				defines a family of view subtrees."
			::= { sheSystemSnmpViewTreeFamilyEntry 3 }

		
		sheSystemSnmpViewTreeFamilyType OBJECT-TYPE
			SYNTAX INTEGER
				{
				included(1),
				excluded(2)
				}
			MAX-ACCESS read-only
			STATUS current
			DESCRIPTION
				"Indicates whether the corresponding
				instances of ViewTreeFamilySubtree and ViewTreeFamilyMask
				define a family of view subtrees which is included in or 
				excluded from the MIB view."
			::= { sheSystemSnmpViewTreeFamilyEntry 4 }

		
		sheSystemSnmpViewTreeFamilyControl OBJECT IDENTIFIER ::= { sheSystemSnmpViewTreeFamily 2 }

		
		sheSystemSnmpViewTreeFamilyControlRequest OBJECT-TYPE
			SYNTAX INTEGER
				{
				createViewTreeFamily(1),
				destroyViewTreeFamily(2)
				}
			MAX-ACCESS read-write
			STATUS current
			DESCRIPTION
				"Description."
			::= { sheSystemSnmpViewTreeFamilyControl 1 }

		
		sheSystemSnmpViewTreeFamilyControlStatus OBJECT-TYPE
			SYNTAX SheControlStatusType
			MAX-ACCESS read-only
			STATUS current
			DESCRIPTION
				"Description."
			::= { sheSystemSnmpViewTreeFamilyControl 2 }

		
		sheSystemSnmpViewTreeFamilyControlTimer OBJECT-TYPE
			SYNTAX Gauge32
			MAX-ACCESS read-write
			STATUS current
			DESCRIPTION
				"Description."
			::= { sheSystemSnmpViewTreeFamilyControl 3 }

		
		sheSystemSnmpViewTreeFamilyControlTimeStamp OBJECT-TYPE
			SYNTAX TimeTicks
			MAX-ACCESS read-only
			STATUS current
			DESCRIPTION
				"Description."
			::= { sheSystemSnmpViewTreeFamilyControl 4 }

		
		sheSystemSnmpViewTreeFamilyControlReqResult OBJECT-TYPE
			SYNTAX SheSystemControlRequestResultType
			MAX-ACCESS read-only
			STATUS current
			DESCRIPTION
				"Description."
			::= { sheSystemSnmpViewTreeFamilyControl 5 }

		
		sheSystemSnmpViewTreeFamilyControlName OBJECT-TYPE
			SYNTAX OCTET STRING
			MAX-ACCESS read-write
			STATUS current
			DESCRIPTION
				"View Name"
			::= { sheSystemSnmpViewTreeFamilyControl 6 }

		
		sheSystemSnmpViewTreeFamilyControlSubtree OBJECT-TYPE
			SYNTAX OBJECT IDENTIFIER
			MAX-ACCESS read-write
			STATUS current
			DESCRIPTION
				"Description."
			::= { sheSystemSnmpViewTreeFamilyControl 7 }

		
		sheSystemSnmpViewTreeFamilyControlMask OBJECT-TYPE
			SYNTAX OCTET STRING
			MAX-ACCESS read-write
			STATUS current
			DESCRIPTION
				"Description."
			::= { sheSystemSnmpViewTreeFamilyControl 8 }

		
		sheSystemSnmpViewTreeFamilyControlType OBJECT-TYPE
			SYNTAX INTEGER
				{
				included(1),
				excluded(2)
				}
			MAX-ACCESS read-write
			STATUS current
			DESCRIPTION
				"Description."
			::= { sheSystemSnmpViewTreeFamilyControl 9 }

		
		sheSystemSnmpViewTreeFamilyNotification OBJECT IDENTIFIER ::= { sheSystemSnmpViewTreeFamily 3 }


		
		sheSystemSnmpAccess  OBJECT IDENTIFIER ::= { sheSystemSnmp 15 } 
		
		sheSystemSnmpAccessTable OBJECT-TYPE
			SYNTAX SEQUENCE OF SheSystemSnmpAccessEntry
			MAX-ACCESS not-accessible
			STATUS current
			DESCRIPTION
				"Description."
			::= { sheSystemSnmpAccess 1 }

		
		sheSystemSnmpAccessEntry OBJECT-TYPE
			SYNTAX SheSystemSnmpAccessEntry
			MAX-ACCESS not-accessible
			STATUS current
			DESCRIPTION
				"Description."
			INDEX { sheSystemSnmpAccessGroupName }
			::= { sheSystemSnmpAccessTable 1 }

		
		SheSystemSnmpAccessEntry ::=
			SEQUENCE { 
				sheSystemSnmpAccessGroupName
					OCTET STRING,
				sheSystemSnmpAccessSecurityModel
					INTEGER,
				sheSystemSnmpAccessSecurityLevel
					INTEGER,
				sheSystemSnmpAccessReadViewName
					OCTET STRING,
				sheSystemSnmpAccessWriteViewName
					OCTET STRING,
				sheSystemSnmpAccessNotifyViewName
					OCTET STRING
			 }

		sheSystemSnmpAccessGroupName OBJECT-TYPE
			SYNTAX OCTET STRING
			MAX-ACCESS read-only
			STATUS current
			DESCRIPTION
				"The name of the group to which this entry belongs"
			::= { sheSystemSnmpAccessEntry 1 }

		
		sheSystemSnmpAccessSecurityModel OBJECT-TYPE
			SYNTAX INTEGER
				{
				any(0),
				snmpV1(1),
				snmpV2(2),
				usm(3)
				}
			MAX-ACCESS read-write
			STATUS current
			DESCRIPTION
				"Security Model"
			::= { sheSystemSnmpAccessEntry 2 }

		
		sheSystemSnmpAccessSecurityLevel OBJECT-TYPE
			SYNTAX INTEGER
				{
				noAuthNoPrivn(1),
				authNoPriv(2),
				authPriv(3)
				}
			MAX-ACCESS read-only
			STATUS current
			DESCRIPTION
				"Security Level"
			::= { sheSystemSnmpAccessEntry 3 }

		
		sheSystemSnmpAccessReadViewName OBJECT-TYPE
			SYNTAX OCTET STRING
			MAX-ACCESS read-only
			STATUS current
			DESCRIPTION
				"The value of an instance of this object
				identifies the MIB view of the SNMP context to which 
				this conceptual row authorizes read access."
			::= { sheSystemSnmpAccessEntry 4 }

		
		sheSystemSnmpAccessWriteViewName OBJECT-TYPE
			SYNTAX OCTET STRING
			MAX-ACCESS read-only
			STATUS current
			DESCRIPTION
				"The value of an instance of this object identifies 
				the MIB view of the SNMP context to which 
				this conceptual row authorizes write access."
			::= { sheSystemSnmpAccessEntry 5 }

		
		sheSystemSnmpAccessNotifyViewName OBJECT-TYPE
			SYNTAX OCTET STRING
			MAX-ACCESS read-only
			STATUS current
			DESCRIPTION
				"The value of an instance of this object identifies
				the MIB view of the SNMP context to which this 
				conceptual row authorizes access for notifications."
			::= { sheSystemSnmpAccessEntry 6 }

		
		sheSystemSnmpAccessControl OBJECT IDENTIFIER ::= { sheSystemSnmpAccess 2 }

		
		sheSystemSnmpAccessControlRequest OBJECT-TYPE
			SYNTAX INTEGER
				{
				createAccess(1),
				destroyAccess(2),
				setAccessProfile(3)
				}
			MAX-ACCESS read-write
			STATUS current
			DESCRIPTION
				"Description."
			::= { sheSystemSnmpAccessControl 1 }

		
		sheSystemSnmpAccessControlStatus OBJECT-TYPE
			SYNTAX SheControlStatusType
			MAX-ACCESS read-only
			STATUS current
			DESCRIPTION
				"Description."
			::= { sheSystemSnmpAccessControl 2 }

		
		sheSystemSnmpAccessControlTimer OBJECT-TYPE
			SYNTAX Gauge32
			MAX-ACCESS read-write
			STATUS current
			DESCRIPTION
				"Description."
			::= { sheSystemSnmpAccessControl 3 }

		sheSystemSnmpAccessControlTimeStamp OBJECT-TYPE
			SYNTAX TimeTicks
			MAX-ACCESS read-only
			STATUS current
			DESCRIPTION
				"Description."
			::= { sheSystemSnmpAccessControl 4 }

		
		sheSystemSnmpAccessControlReqResult OBJECT-TYPE
			SYNTAX SheSystemControlRequestResultType
			MAX-ACCESS read-only
			STATUS current
			DESCRIPTION
				"Description."
			::= { sheSystemSnmpAccessControl 5 }

		
		sheSystemSnmpAccessControlGroupName OBJECT-TYPE
			SYNTAX OCTET STRING
			MAX-ACCESS read-write
			STATUS current
			DESCRIPTION
				"Description."
			::= { sheSystemSnmpAccessControl 6 }

		
		sheSystemSnmpAccessControlSecurityModel OBJECT-TYPE
			SYNTAX INTEGER
				{
				any(0),
				snmpV1(1),
				snmpV2(2),
				usm(3)
				}
			MAX-ACCESS read-write
			STATUS current
			DESCRIPTION
				"Security Model"
			::= { sheSystemSnmpAccessControl 7 }

		
		sheSystemSnmpAccessControlSecurityLevel OBJECT-TYPE
			SYNTAX INTEGER
				{
				noAuthNoPrivn(1),
				authNoPriv(2),
				authPriv(3)
				}
			MAX-ACCESS read-write
			STATUS current
			DESCRIPTION
				"Security Level"
			::= { sheSystemSnmpAccessControl 8 }

		
		sheSystemSnmpAccessControlReadViewName OBJECT-TYPE
			SYNTAX OCTET STRING
			MAX-ACCESS read-write
			STATUS current
			DESCRIPTION
				"The value of an instance of this object identifies
				the MIB view of the SNMP context to which this 
				conceptual row authorizes read access."
			::= { sheSystemSnmpAccessControl 9 }

		
		sheSystemSnmpAccessControlWriteViewName OBJECT-TYPE
			SYNTAX OCTET STRING
			MAX-ACCESS read-write
			STATUS current
			DESCRIPTION
				"The value of an instance of this object identifies 
				the MIB view of the SNMP context to which this 
				conceptual row authorizes write access."
			::= { sheSystemSnmpAccessControl 10 }

		
		sheSystemSnmpAccessControlNotifyViewName OBJECT-TYPE
			SYNTAX OCTET STRING
			MAX-ACCESS read-write
			STATUS current
			DESCRIPTION
				"The value of an instance of this object identifies 
				the MIB view of the SNMP context to which this 
				conceptual row authorizes access for notifications."
			::= { sheSystemSnmpAccessControl 11 }

		
		sheSystemSnmpAccessNotification OBJECT IDENTIFIER ::= { sheSystemSnmpAccess 3 }


		
		sheSystemSnmpSecToGroup  OBJECT IDENTIFIER ::= { sheSystemSnmp 16 }    
		
		sheSystemSnmpSecurityToGroupTable OBJECT-TYPE
			SYNTAX SEQUENCE OF SheSystemSnmpSecurityToGroupEntry
			MAX-ACCESS not-accessible
			STATUS current
			DESCRIPTION
				"Description."
			::= { sheSystemSnmpSecToGroup 1 }

		
		sheSystemSnmpSecurityToGroupEntry OBJECT-TYPE
			SYNTAX SheSystemSnmpSecurityToGroupEntry
			MAX-ACCESS not-accessible
			STATUS current
			DESCRIPTION
				"Description."
			INDEX { sheSystemSnmpSecurityToGroupGName, sheSystemSnmpSecurityToGroupModel }
			::= { sheSystemSnmpSecurityToGroupTable 1 }

		
		SheSystemSnmpSecurityToGroupEntry ::=
			SEQUENCE { 
				sheSystemSnmpSecurityToGroupSName
					OCTET STRING,
				sheSystemSnmpSecurityToGroupModel
					INTEGER,
				sheSystemSnmpSecurityToGroupGName
					OCTET STRING
			 }

		sheSystemSnmpSecurityToGroupSName OBJECT-TYPE
			SYNTAX OCTET STRING
			MAX-ACCESS read-only
			STATUS current
			DESCRIPTION
				"The name of the group to which this entry belongs."
			::= { sheSystemSnmpSecurityToGroupEntry 1 }

		
		sheSystemSnmpSecurityToGroupModel OBJECT-TYPE
			SYNTAX INTEGER
				{
				any(0),
				snmpV1(1),
				snmpV2(2),
				usm(3)
				}
			MAX-ACCESS read-only
			STATUS current
			DESCRIPTION
				"Security Model"
			::= { sheSystemSnmpSecurityToGroupEntry 2 }

		
		sheSystemSnmpSecurityToGroupGName OBJECT-TYPE
			SYNTAX OCTET STRING
			MAX-ACCESS read-only
			STATUS current
			DESCRIPTION
				"The securityName for the principal, 
				which is mapped by this entry to a groupName."
			::= { sheSystemSnmpSecurityToGroupEntry 3 }

		
		sheSystemSnmpSecurityToGroupControl OBJECT IDENTIFIER ::= { sheSystemSnmpSecToGroup 2 }

		
		sheSystemSnmpSecurityToGroupControlRequest OBJECT-TYPE
			SYNTAX INTEGER
				{
				createSecurityToGroup(1),
				destroySecurityToGroup(2),
				setSecurityToGroupProfile(3)
				}
			MAX-ACCESS read-write
			STATUS current
			DESCRIPTION
				"Description."
			::= { sheSystemSnmpSecurityToGroupControl 1 }

		
		sheSystemSnmpSecurityToGroupControlStatus OBJECT-TYPE
			SYNTAX SheControlStatusType
			MAX-ACCESS read-only
			STATUS current
			DESCRIPTION
				"Description."
			::= { sheSystemSnmpSecurityToGroupControl 2 }

		
		sheSystemSnmpSecurityToGroupControlTimer OBJECT-TYPE
			SYNTAX Gauge32
			MAX-ACCESS read-write
			STATUS current
			DESCRIPTION
				"Description."
			::= { sheSystemSnmpSecurityToGroupControl 3 }

		
		sheSystemSnmpSecurityToGroupControlTimeStamp OBJECT-TYPE
			SYNTAX TimeTicks
			MAX-ACCESS read-only
			STATUS current
			DESCRIPTION
				"Time stamp attribute set at the end of a command"
			::= { sheSystemSnmpSecurityToGroupControl 4 }

		
		sheSystemSnmpSecurityToGroupControlReqResult OBJECT-TYPE
			SYNTAX SheSystemControlRequestResultType
			MAX-ACCESS read-only
			STATUS current
			DESCRIPTION
				"Description."
			::= { sheSystemSnmpSecurityToGroupControl 5 }

		
		sheSystemSnmpSecurityToGroupControlGName OBJECT-TYPE
			SYNTAX OCTET STRING
			MAX-ACCESS read-write
			STATUS current
			DESCRIPTION
				"The name of the group to which this entry belongs."
			::= { sheSystemSnmpSecurityToGroupControl 6 }

		
		sheSystemSnmpSecurityToGroupControlModel OBJECT-TYPE
			SYNTAX INTEGER
				{
				any(0),
				snmpV1(1),
				snmpV2(2),
				usm(3)
				}
			MAX-ACCESS read-write
			STATUS current
			DESCRIPTION
				"Description."
			::= { sheSystemSnmpSecurityToGroupControl 7 }

		
		sheSystemSnmpSecurityToGroupControlSName OBJECT-TYPE
			SYNTAX OCTET STRING
			MAX-ACCESS read-write
			STATUS current
			DESCRIPTION
				"The securityName for the principal, 
				which is mapped by this entry to a groupName."
			::= { sheSystemSnmpSecurityToGroupControl 8 }

		
		sheSystemSnmpSecurityToGroupNotification OBJECT IDENTIFIER ::= { sheSystemSnmpSecToGroup 3 }


		
		sheSystemSnmpUsm  OBJECT IDENTIFIER ::= { sheSystemSnmp 17 } 		
		
		sheSystemUsmTable OBJECT-TYPE
			SYNTAX SEQUENCE OF SheSystemUsmEntry
			MAX-ACCESS not-accessible
			STATUS current
			DESCRIPTION
				"Description."
			::= { sheSystemSnmpUsm 1 }

		
		sheSystemUsmEntry OBJECT-TYPE
			SYNTAX SheSystemUsmEntry
			MAX-ACCESS not-accessible
			STATUS current
			DESCRIPTION
				"Description."
			INDEX { sheSystemUsmName }
			::= { sheSystemUsmTable 1 }

		
		SheSystemUsmEntry ::=
			SEQUENCE { 
				sheSystemUsmName
					OCTET STRING,
				sheSystemUsmAuthType
					INTEGER,
				sheSystemUsmAuthKey
					OCTET STRING,
				sheSystemUsmPrivType
					INTEGER,
				sheSystemUsmPrivKey
					OCTET STRING
			 }

		sheSystemUsmName OBJECT-TYPE
			SYNTAX OCTET STRING
			MAX-ACCESS read-only
			STATUS current
			DESCRIPTION
				"User name"
			::= { sheSystemUsmEntry 1 }

		
		sheSystemUsmAuthType OBJECT-TYPE
			SYNTAX INTEGER
				{
				md5(1),
				sha(2)
				}
			MAX-ACCESS read-only
			STATUS current
			DESCRIPTION
				"Authentication type"
			::= { sheSystemUsmEntry 2 }

		
		sheSystemUsmAuthKey OBJECT-TYPE
			SYNTAX OCTET STRING
			MAX-ACCESS read-only
			STATUS current
			DESCRIPTION
				"Authentication key (length >=8)"
			::= { sheSystemUsmEntry 3 }

		
		sheSystemUsmPrivType OBJECT-TYPE
			SYNTAX INTEGER
				{
				noPrivacy(1),
				des(2)
				}
			MAX-ACCESS read-only
			STATUS current
			DESCRIPTION
				"Privacy type"
			::= { sheSystemUsmEntry 4 }

		
		sheSystemUsmPrivKey OBJECT-TYPE
			SYNTAX OCTET STRING
			MAX-ACCESS read-only
			STATUS current
			DESCRIPTION
				"Privacy key (length >=8)"
			::= { sheSystemUsmEntry 5 }

		
		sheSystemUsmControl OBJECT IDENTIFIER ::= { sheSystemSnmpUsm 2 }

		
		sheSystemUsmControlRequest OBJECT-TYPE
			SYNTAX INTEGER
				{
				createUser(1),
				destroyUser(2)
				}
			MAX-ACCESS read-write
			STATUS current
			DESCRIPTION
				"Description."
			::= { sheSystemUsmControl 1 }

		
		sheSystemUsmControlStatus OBJECT-TYPE
			SYNTAX SheControlStatusType
			MAX-ACCESS read-only
			STATUS current
			DESCRIPTION
				"Description."
			::= { sheSystemUsmControl 2 }

		
		sheSystemUsmControlTimer OBJECT-TYPE
			SYNTAX Gauge32
			MAX-ACCESS read-write
			STATUS current
			DESCRIPTION
				"Description."
			::= { sheSystemUsmControl 3 }

		
		sheSystemUsmControlTimeStamp OBJECT-TYPE
			SYNTAX TimeTicks
			MAX-ACCESS read-only
			STATUS current
			DESCRIPTION
				"Description."
			::= { sheSystemUsmControl 4 }

		
		sheSystemUsmControlReqResult OBJECT-TYPE
			SYNTAX SheSystemControlRequestResultType
			MAX-ACCESS read-only
			STATUS current
			DESCRIPTION
				"Description."
			::= { sheSystemUsmControl 5 }

		
		sheSystemUsmControlName OBJECT-TYPE
			SYNTAX OCTET STRING
			MAX-ACCESS read-write
			STATUS current
			DESCRIPTION
				"User name"
			::= { sheSystemUsmControl 6 }

		
		sheSystemUsmControlAuthType OBJECT-TYPE
			SYNTAX INTEGER
				{
				md5(1),
				sha(2)
				}
			MAX-ACCESS read-write
			STATUS current
			DESCRIPTION
				"Authentication type"
			::= { sheSystemUsmControl 7 }

		
		sheSystemUsmControlAuthKey OBJECT-TYPE
			SYNTAX OCTET STRING
			MAX-ACCESS read-write
			STATUS current
			DESCRIPTION
				"Authentication key (length >=8)"
			::= { sheSystemUsmControl 8 }

		
		sheSystemUsmControlPrivType OBJECT-TYPE
			SYNTAX INTEGER
				{
				noPrivacy(1),
				des(2)
				}
			MAX-ACCESS read-write
			STATUS current
			DESCRIPTION
				"Privacy type"
			::= { sheSystemUsmControl 9 }

		
		sheSystemUsmControlPrivKey OBJECT-TYPE
			SYNTAX OCTET STRING
			MAX-ACCESS read-write
			STATUS current
			DESCRIPTION
				"Privacy key (length >=8)"
			::= { sheSystemUsmControl 10 }

		
		sheSystemUsmNotification OBJECT IDENTIFIER ::= { sheSystemSnmpUsm 3 }

		
		

		
--  Configuration and status information for automatic sw upgrade and db backup controls.
		sheSystemMaintenance OBJECT IDENTIFIER ::= { sheSystem 11 }

		
		sheSystemSwMaintenance OBJECT IDENTIFIER ::= { sheSystemMaintenance 1 }

		
		sheSystemSwMaintenanceBase OBJECT IDENTIFIER ::= { sheSystemSwMaintenance 1 }

		
		sheSystemSwmSapsServerAddr OBJECT-TYPE
			SYNTAX OCTET STRING (SIZE (0..20))
			MAX-ACCESS read-only
			STATUS current
			DESCRIPTION
				"Address of SAPS FTP server (dotted notation)."
			::= { sheSystemSwMaintenanceBase 1 }

		
		sheSystemSwmSapsPathName OBJECT-TYPE
			SYNTAX OCTET STRING (SIZE (0..128))
			MAX-ACCESS read-only
			STATUS current
			DESCRIPTION
				"Path name of SAPS file on FTP server. 
				This path should be set relative to the ftp-server root.
				Use only linux notation ( / ). 
				
				Spaces in pathnames are not allowed, because of possible problems with
				different FTP implementations (client and/or server)!!"
			::= { sheSystemSwMaintenanceBase 2 }

		
		sheSystemSwmSapsFileName OBJECT-TYPE
			SYNTAX OCTET STRING (SIZE (1..128))
			MAX-ACCESS read-only
			STATUS current
			DESCRIPTION
				"File name of SAPS file on FTP server. 
				
				Spaces in filenames are not allowed, because of possible problems with
				different FTP implementations (client and/or server)!!
				"
			::= { sheSystemSwMaintenanceBase 3 }

		
		sheSystemSwmAdminState OBJECT-TYPE
			SYNTAX SheSystemAdminState
			MAX-ACCESS read-only
			STATUS current
			DESCRIPTION
				"This state describes the current usage of automatic sw upgrade.
				The following states are supported:
				
				unlocked(1)  -> saps handling used
				locked(2)    -> saps handling not used (default)
				
				Important Note: If the automatic sw upgrade system is enabled, the sheSystemFileControl group
				for single sw upgrades is always busy!! If a sw upgrade should be start for a single Card or a single
				card type, the sheSystemSwmAdminState has to be locked and then the sheSystemFileControl could be used!"
			DEFVAL { 2 }
			::= { sheSystemSwMaintenanceBase 4 }


		sheSystemSwmSapsInterval OBJECT-TYPE
			SYNTAX Integer32
			MAX-ACCESS read-only
			STATUS current
			DESCRIPTION
				"!"			
			::= { sheSystemSwMaintenanceBase 5 }

	
		sheSystemSwmServiceType OBJECT-TYPE
			SYNTAX INTEGER
			{
			    ftp(0),
			    tftp(1)
			}
			MAX-ACCESS read-only
			STATUS current
			DESCRIPTION
			" The service type for upload/download. "
			::= { sheSystemSwMaintenanceBase 6 }
	
--    --------------------------------------------------------------
-- SW Upgrade Task Table
-- --------------------------------------------------------------
-- 
		sheSystemSwMaintenanceTaskTable OBJECT-TYPE
			SYNTAX SEQUENCE OF SheSystemSwMaintenanceTaskEntry
			MAX-ACCESS not-accessible
			STATUS current
			DESCRIPTION
				"Table of the current active or failed tasks of SW upgrade.
				This table is used to display the automatic upgrade status for single plugin
				units at the TMN. "
			::= { sheSystemSwMaintenance 2 }

		
--    info-IMPL:    V2.0->
		sheSystemSwMaintenanceTaskEntry OBJECT-TYPE
			SYNTAX SheSystemSwMaintenanceTaskEntry
			MAX-ACCESS not-accessible
			STATUS current
			DESCRIPTION
				"Entry of the SW upgrade task table.
				"
			INDEX { sheSystemSwmTIndex }
			::= { sheSystemSwMaintenanceTaskTable 1 }

		
		SheSystemSwMaintenanceTaskEntry ::=
			SEQUENCE { 
				sheSystemSwmTIndex
					Unsigned32,
				sheSystemSwmTCardType
					SheCardType,
				sheSystemSwmTEntPhysicalIndex
					PhysicalIndex,
				sheSystemSwmTTimeStamp
					Unsigned32,
				sheSystemSwmTUpgradeState
					SheSystemMaintenanceControlReqResult,
				sheSystemSwmTUpgradeResult
					SheSystemMaintenanceControlReqResult,
				sheSystemSwmTSwVersion
					OCTET STRING,
				sheSystemSwmTSwVersionNeed
					OCTET STRING
			 }

		sheSystemSwmTIndex OBJECT-TYPE
			SYNTAX Unsigned32 (1..255)
			MAX-ACCESS read-only
			STATUS current
			DESCRIPTION
				"Unique value to identify an entry of this table. "
			::= { sheSystemSwMaintenanceTaskEntry 1 }

		
		sheSystemSwmTCardType OBJECT-TYPE
			SYNTAX SheCardType
			MAX-ACCESS read-only
			STATUS current
			DESCRIPTION
				" Indicates the plug-in unit type to be upgraded. "
			::= { sheSystemSwMaintenanceTaskEntry 2 }

		
		sheSystemSwmTEntPhysicalIndex OBJECT-TYPE
			SYNTAX PhysicalIndex
			MAX-ACCESS read-only
			STATUS current
			DESCRIPTION
				"The entPhysicalIndex of PIU to be loaded."
			::= { sheSystemSwMaintenanceTaskEntry 3 }

		
		sheSystemSwmTTimeStamp OBJECT-TYPE
			SYNTAX Unsigned32
			UNITS "sec"
			MAX-ACCESS read-only
			STATUS current
			DESCRIPTION
				"The time stamp of the task. It is updated anytime the upgrade task state changes. "
			::= { sheSystemSwMaintenanceTaskEntry 4 }

		
		sheSystemSwmTUpgradeState OBJECT-TYPE
			SYNTAX SheSystemMaintenanceControlReqResult
			MAX-ACCESS read-only
			STATUS current
			DESCRIPTION
				"Identifies the current processing state of the upgrade task: 
				- sutInitialized
				- sutToDo
				- sutStarted
				- sutCrashed
				- sutFtpDone
				- sutDone
				- sutReadyForReset
				- sutResetInProgress
				- sutObsolete"
			::= { sheSystemSwMaintenanceTaskEntry 5 }

		
		sheSystemSwmTUpgradeResult OBJECT-TYPE
			SYNTAX SheSystemMaintenanceControlReqResult
			MAX-ACCESS read-only
			STATUS current
			DESCRIPTION
				"This read-only attribute informs about the result of the performed upgrade
				(in case of failed upgrade the error reason). "
			::= { sheSystemSwMaintenanceTaskEntry 6 }

		
		sheSystemSwmTSwVersion OBJECT-TYPE
			SYNTAX OCTET STRING (SIZE (0..128))
			MAX-ACCESS read-only
			STATUS current
			DESCRIPTION
				"String containing the APS version which is loaded into the plug-in unit. "
			::= { sheSystemSwMaintenanceTaskEntry 7 }

		
		sheSystemSwmTSwVersionNeed OBJECT-TYPE
			SYNTAX OCTET STRING (SIZE (0..128))
			MAX-ACCESS read-only
			STATUS current
			DESCRIPTION
				"String containing the APS version which should be loaded into the plug-in unit. "
			::= { sheSystemSwMaintenanceTaskEntry 8 }

		
--  --------------------------------------------------------------
-- SW maintenance control subgroup
-- --------------------------------------------------------------
-- This managed entity represents the control group for saps sw maintenance user commands.
-- The following user commands are implemented :
-- 
-- setSystemMaintenanceBase
-- Set needed ftp access information for automatic SAPS request's.
-- 
-- setSwmAdminState
-- Enable/Disable the automatic saps sw maintenance system.
-- 
-- swmUpgrStartRequest:    
-- Start upgrade for the sytem in the background including sw activation.
-- 
-- swmUpgrStartRequestNoReset:    
-- Start upgrade for the sytem in the background without sw activation.
-- To activate new sw versions, the piu's should be made a reset.
-- 
-- swmReadSAPSContentFile : 
-- The SAPS (Sytem Application Software) content file describes an assignment of
-- available SW loads to loadable PIUs inclusively the CXU .
-- If there is a new SAPs content file at the FTP server f.ex. because of bug fix
-- release the crafts person has to request the reading of the SAPS content file
-- so that the information is available in the DSLAM.
-- The SAPS content file is automatically read after reload or after activation
-- of a CXU load.
-- 
-- 
		sheSystemSwMaintenanceControl OBJECT IDENTIFIER ::= { sheSystemSwMaintenance 3 }

		
		sheSystemSwmControlRequest OBJECT-TYPE
			SYNTAX SheSystemMaintenanceControlReq
			MAX-ACCESS read-write
			STATUS current
			DESCRIPTION
				"SW upgrade command requests from TMN.
				
				setSystemMaintenanceBase(50), 
				- Set needed ftp access information for automatic SAPS request's.
				notifications: 
				  sheSystemSwmBaseSet
				
				setSwmAdminState(51),
				- lock or unlock the automatic saps system
				notifications:                       
				  sheSystemSwmBaseAdminStateSet
				  sheSystemReadSAPSContentFileReady (if set to unlock)
				  sheSystemSwmFTPError              (if ftp could not reached)
				
				swmUpgrStartRequest(100),
				- start new upgrade procedure including automatic load activation
				notifications:
				 sheSystemSwmFTPError
				 sheSystemSwmUpgradeStartResult
				
				swmUpgrStartRequestNoReset(101),
				- start new upgrade procedure without automatic load activation
				notifications:
				 sheSystemSwmReadyForReset
				 sheSystemSwmFTPError
				 sheSystemUpgradeCanceled (bad case only) 
				 sheSystemSwmUpgradeStartResult
				
				
				swmReadSAPSContentFile(102),
				- start request of new SAPS file from server, no download action is started 
				notification:
				 sheSystemReadSAPSContentFileReady
				 sheSystemSwmFTPError   
				 
				swmSetUpgrInterval
				-  Set interval of the scheduled NOS upgrade. If zero, scheduled upgrade shall be disabled.
			
				"
			::= { sheSystemSwMaintenanceControl 1 }

		
		sheSystemSwmControlStatus OBJECT-TYPE
			SYNTAX SheControlStatusType
			MAX-ACCESS read-only
			STATUS current
			DESCRIPTION
				" The status of the current request. "
			::= { sheSystemSwMaintenanceControl 2 }

		
		sheSystemSwmControlTimer OBJECT-TYPE
			SYNTAX Unsigned32
			MAX-ACCESS read-only
			STATUS current
			DESCRIPTION
				"Wait time in seconds after complete upgrade for a unit type. "
			::= { sheSystemSwMaintenanceControl 3 }

		
		sheSystemSwmControlReqResult OBJECT-TYPE
			SYNTAX SheSystemMaintenanceControlReqResult
			MAX-ACCESS read-only
			STATUS current
			DESCRIPTION
				"The result of the last user command."
			::= { sheSystemSwMaintenanceControl 4 }

		
		sheSystemSwmControlTimeStamp OBJECT-TYPE
			SYNTAX Unsigned32
			UNITS "sec"
			MAX-ACCESS read-only
			STATUS current
			DESCRIPTION
				" The time stamp of the last command (end of command). "
			::= { sheSystemSwMaintenanceControl 5 }

		
		sheSystemSwmControlSapsServerAddr OBJECT-TYPE
			SYNTAX OCTET STRING (SIZE (0..20))
			MAX-ACCESS read-write
			STATUS current
			DESCRIPTION
				"Address of SAPS FTP server (dotted notation)."
			::= { sheSystemSwMaintenanceControl 6 }

		
		sheSystemSwmControlSapsPathName OBJECT-TYPE
			SYNTAX OCTET STRING (SIZE (0..128))
			MAX-ACCESS read-write
			STATUS current
			DESCRIPTION
				"Path name of SAPS file on FTP server. 
				This path should be set relative to the ftp-server root.
				Use only linux notation ( / ). 
				
				Spaces in pathnames are not allowed, because of possible problems with
				different FTP implementations (client and/or server)!!"
			::= { sheSystemSwMaintenanceControl 7 }

		
		sheSystemSwmControlSapsFileName OBJECT-TYPE
			SYNTAX OCTET STRING (SIZE (1..128))
			MAX-ACCESS read-write
			STATUS current
			DESCRIPTION
				"File name of SAPS file on FTP server. 
				
				Spaces in filenames are not allowed, because of possible problems with
				different FTP implementations (client and/or server)!!
				"
			::= { sheSystemSwMaintenanceControl 8 }

		
		sheSystemSwmControlSapsUsrName OBJECT-TYPE
			SYNTAX OCTET STRING (SIZE (0..20))
			MAX-ACCESS read-write
			STATUS current
			DESCRIPTION
				"Username for SAPS FTP access.                                                             
				
				Read-access to this attribute will deliver 20 times sign '-'  "
			::= { sheSystemSwMaintenanceControl 9 }

		
		sheSystemSwmControlSapsPassword OBJECT-TYPE
			SYNTAX OCTET STRING (SIZE (0..20))
			MAX-ACCESS read-write
			STATUS current
			DESCRIPTION
				"Password for SAPS FTP access.                                                              
				
				Read-access to this attribute will deliver 20 times sign '-'  "
			::= { sheSystemSwMaintenanceControl 10 }

		
		sheSystemSwmControlAdminState OBJECT-TYPE
			SYNTAX SheSystemAdminState
			MAX-ACCESS read-write
			STATUS current
			DESCRIPTION
				"This set the current usage of automatic sw upgrade.
				The following states are supported:
				
				unlocked(1)  -> saps handling used
				locked(2)    -> saps handling not used (default)
				
				"
			::= { sheSystemSwMaintenanceControl 11 }

		sheSystemSwmControlSapsInterval OBJECT-TYPE
			SYNTAX Integer32
			MAX-ACCESS read-write
			STATUS current
			DESCRIPTION
				""
			::= { sheSystemSwMaintenanceControl 12 }

		sheSystemSwmControlServiceType OBJECT-TYPE
			SYNTAX INTEGER
                        {
                             ftp(0),
                             tftp(1)
                        }
			MAX-ACCESS read-write
			STATUS current
			DESCRIPTION
                        " The service type for upload/download. "
			::= { sheSystemSwMaintenanceControl 13 }

		sheSystemSwMaintenanceNotifications OBJECT IDENTIFIER ::= { sheSystemSwMaintenance 4 }

		
		sheSystemSwmBaseSet NOTIFICATION-TYPE
			OBJECTS { sheSystemSwmControlStatus, sheSystemSwmControlReqResult, sheSystemSwmControlTimeStamp }
			STATUS current
			DESCRIPTION 
				"Configuration trap for SAPS basic ftp access settings."
			::= { sheSystemSwMaintenanceNotifications 1 }

		
		sheSystemSwmAdminStateSet NOTIFICATION-TYPE
			OBJECTS { sheSystemSwmControlStatus, sheSystemSwmControlReqResult, sheSystemSwmControlTimeStamp, sheSystemSwmAdminState }
			STATUS current
			DESCRIPTION 
				"Configuration trap for SAPS basic admin state settings."
			::= { sheSystemSwMaintenanceNotifications 2 }

		
		sheSystemReadSAPSContentFileReady NOTIFICATION-TYPE
			OBJECTS { sheSystemSwmControlStatus, sheSystemSwmControlReqResult, sheSystemSwmControlTimeStamp }
			STATUS current
			DESCRIPTION 
				"Result trap for request of new SAPS file from server."
			::= { sheSystemSwMaintenanceNotifications 3 }

		
		sheSystemSwmReadyForReset NOTIFICATION-TYPE
			OBJECTS { sheSystemSwmControlStatus, sheSystemSwmControlReqResult, sheSystemSwmControlTimeStamp, sheSystemSwmTEntPhysicalIndex }
			STATUS current
			DESCRIPTION 
				"Trap will be send after succesfull SwUpgrade for a single card if a sw upgrade
				was started without automatic load activation."
			::= { sheSystemSwMaintenanceNotifications 4 }

		
		sheSystemSwmFTPError NOTIFICATION-TYPE
			OBJECTS { sheSystemSwmControlStatus, sheSystemSwmControlReqResult, sheSystemSwmControlTimeStamp }
			STATUS current
			DESCRIPTION 
				"Result trap for sw upgrade (T)FTP access."
			::= { sheSystemSwMaintenanceNotifications 5 }

		
		sheSystemSwmUpgradeStartResult NOTIFICATION-TYPE
			OBJECTS { sheSystemSwmControlRequest, sheSystemSwmControlStatus, sheSystemSwmControlReqResult, sheSystemSwmControlTimeStamp }
			STATUS current
			DESCRIPTION 
				"Configuration result trap for long running command."
			::= { sheSystemSwMaintenanceNotifications 6 }

		sheSystemSwmIntervalChanged NOTIFICATION-TYPE
			OBJECTS { sheSystemSwmControlRequest, sheSystemSwmControlStatus, sheSystemSwmControlReqResult, sheSystemSwmControlTimeStamp,
			sheSystemSwmControlSapsInterval }
			STATUS current
			DESCRIPTION 
				"Configuration result trap for long running command."
			::= { sheSystemSwMaintenanceNotifications 7 }

		
		sheSystemSwMaintenanceAlarms OBJECT IDENTIFIER ::= { sheSystemSwMaintenance 5 }

		
		sheSystemSwmFtpAccessError NOTIFICATION-TYPE
			OBJECTS { sheAlarmTimeAndDate, sheAlarmReportingSource, sheAlarmReportingSourceType, sheAlarmSeverity }
			STATUS current
			DESCRIPTION 
				" Alarm will be set because of failures during read or write during the NE internal (T)FTP communication. 
				A successful ftp process will clear this alarm.
				Alarm will be used by manual download and automatic saps upgrade."
			::= { sheSystemSwMaintenanceAlarms 1 }

		
		sheSystemSwmFtpExternalAccessError NOTIFICATION-TYPE
			OBJECTS { sheAlarmTimeAndDate, sheAlarmReportingSource, sheAlarmReportingSourceType, sheAlarmSeverity }
			STATUS current
			DESCRIPTION 
			"Alarm will be set because of failures during read or write during the NE external (T)FTP communication 
			(access to external ftp server failed). A successful ftp process will clear this alarm.
			Alarm will be used by manual download and automatic saps upgrade
			"
			::= { sheSystemSwMaintenanceAlarms 2 }

		
		sheSystemDbMaintenance OBJECT IDENTIFIER ::= { sheSystemMaintenance 2 }

		
		sheSystemDbMaintenanceBase OBJECT IDENTIFIER ::= { sheSystemDbMaintenance 1 }

		
		sheSystemDbmServerAddr OBJECT-TYPE
			SYNTAX OCTET STRING (SIZE (0..20))
			MAX-ACCESS read-only
			STATUS current
			DESCRIPTION
				"Address of DB FTP server (dotted notation)."
			::= { sheSystemDbMaintenanceBase 1 }

		
		sheSystemDbmPathName OBJECT-TYPE
			SYNTAX OCTET STRING (SIZE (0..128))
			MAX-ACCESS read-only
			STATUS current
			DESCRIPTION
				"Path name of DB backup files on FTP server. 
				This path should be set relative to the ftp-server root.
				Use only linux notation ( / ). 
				
				Spaces in pathnames are not allowed, because of possible problems with
				different FTP implementations (client and/or server)!!"
			::= { sheSystemDbMaintenanceBase 2 }

		
		sheSystemDbmRemoteBackupAdminState OBJECT-TYPE
			SYNTAX SheSystemAdminState
			MAX-ACCESS read-only
			STATUS current
			DESCRIPTION
				"This state describes the current usage of automatic remote db backup.
				The following states are supported:
				
				unlocked(1)  -> remote db backup handling used
				locked(2)    -> remote db backup handling not used (default)"
			DEFVAL { 2 }
			::= { sheSystemDbMaintenanceBase 3 }

		
		sheSystemDbmBackupStartTime OBJECT-TYPE
			SYNTAX Unsigned32 (0..1439)
			UNITS "minute"
			MAX-ACCESS read-only
			STATUS current
			DESCRIPTION
				"Start time basis for remote DB backup after system restart, backup timer 
				reconfigurations or system clock reset.
				The first backup will be started at this time + sheSystemDbmBackupPeriod and
				will then be repeated each sheSystemDbmBackupPeriod.
				Range: 0 (0 am) .. 1439 (23.59 pm). 
				Default: 0  
				Reminder: NE uses always a UTC time base."
			DEFVAL { 0 }
			::= { sheSystemDbMaintenanceBase 4 }

		
		sheSystemDbmBackupPeriod OBJECT-TYPE
			SYNTAX Unsigned32 (1..48)
			UNITS "hour"
			MAX-ACCESS read-only
			STATUS current
			DESCRIPTION
				"Interval between two remote backup operations in hours. 
				Backup is started only if there were relevant configuration
				changes during the last period.
				Default: 24 hours "
			DEFVAL { 24 }
			::= { sheSystemDbMaintenanceBase 5 }

		
		sheSystemDbmBackupWaitingPeriod OBJECT-TYPE
			SYNTAX Unsigned32 (1..59)
			UNITS "minute"
			MAX-ACCESS read-only
			STATUS current
			DESCRIPTION
				"Waiting period in minutes before next local backup, in case of configuration changes.
				Default value : 5 minutes. "
			DEFVAL { 5 }
			::= { sheSystemDbMaintenanceBase 6 }

		
		sheSystemDbmBackupMaxFileNumber OBJECT-TYPE
			SYNTAX Unsigned32 (1..32)
			MAX-ACCESS read-only
			STATUS current
			DESCRIPTION
				"This number describes the maximum set of different backup files on the remote ftp site.
				Default number is 5."
			DEFVAL { 5 }
			::= { sheSystemDbMaintenanceBase 7 }

		
		sheSystemDbmLocalBackupAdminState OBJECT-TYPE
			SYNTAX SheSystemAdminState
			MAX-ACCESS read-only
			STATUS current
			DESCRIPTION
				"This value administrate the automatic local db backup after sheSystemDbmBackupWaitingPeriod
				in case of configuration actions.
				Default: unlocked  (automatic local backup is enabled)"
			DEFVAL { 1 }
			::= { sheSystemDbMaintenanceBase 8 }

		
		sheSystemDbBackupFilesTable OBJECT-TYPE
			SYNTAX SEQUENCE OF SheSystemDbBackupFilesEntry
			MAX-ACCESS not-accessible
			STATUS current
			DESCRIPTION
				" Table shows the DB backup files at the FTP server 
				with time and date of their creation.
				The table is empty per default and can be updated 
				with user command refreshDbBackupFilesTable.
				This command searches all existing DB backup files
				at the FTP server. "
			::= { sheSystemDbMaintenance 2 }

		
--   info-IMPL:    V3.0->
		sheSystemDbBackupFilesEntry OBJECT-TYPE
			SYNTAX SheSystemDbBackupFilesEntry
			MAX-ACCESS not-accessible
			STATUS current
			DESCRIPTION
				" Entry of the xldv20DbBackupFilesTable.
				Notifications :  . "
			INDEX { sheSystemDbBackupFileIndex }
			::= { sheSystemDbBackupFilesTable 1 }

		
		SheSystemDbBackupFilesEntry ::=
			SEQUENCE { 
				sheSystemDbBackupFileIndex
					Unsigned32,
				sheSystemDbBackupFileName
					DisplayString,
				sheSystemDbBackupFileTimeStamp
					Unsigned32
			 }

		sheSystemDbBackupFileIndex OBJECT-TYPE
			SYNTAX Unsigned32 (1..32)
			MAX-ACCESS read-only
			STATUS current
			DESCRIPTION
				"Unique value to identify an entry of this table. "
			::= { sheSystemDbBackupFilesEntry 1 }

		
		sheSystemDbBackupFileName OBJECT-TYPE
			SYNTAX DisplayString (SIZE (0..128))
			MAX-ACCESS read-only
			STATUS current
			DESCRIPTION
				" The name of the DB backup file. "
			::= { sheSystemDbBackupFilesEntry 2 }

		
		sheSystemDbBackupFileTimeStamp OBJECT-TYPE
			SYNTAX Unsigned32
			UNITS "sec"
			MAX-ACCESS read-only
			STATUS current
			DESCRIPTION
				" The time stamp of the DB backup file, i.e. the time and
				date when the DB backup file has been created. "
			::= { sheSystemDbBackupFilesEntry 3 }

		
--   ==============================================================
-- D a t a B a s e   M a n a g e m e n t   G r o u p
-- ==============================================================
-- --------------------------------------------------------------
--       DataBase Management control subgroup
-- --------------------------------------------------------------
		sheSystemDbmControl OBJECT IDENTIFIER ::= { sheSystemDbMaintenance 3 }

		
--  This managed entity manages the control request for storage
-- of the database.
		sheSystemDbmControlRequest OBJECT-TYPE
			SYNTAX SheSystemMaintenanceControlReq
			MAX-ACCESS read-write
			STATUS current
			DESCRIPTION
				"  Database Management commands :
				
				setSystemMaintenanceBase:
				- Set needed ftp access information for automatic DB request's.
				notifications: 
				  sheSystemDbmBaseSet
				
				backupDb : 
				- The command for a manual database backup
				  into the FEPROM of the DSLAM and to the FTP server.
				  The return value commExecStarted indicates the beginning
				  of DB storage.
				notification:
				 sheSystemDbmResult
				 
				refreshDbBackupFilesTable :
				- The DSLAM supports several
				  backup files. The command retrieves the backup files 
				  at the FTP server and provides their file names and  
				  time and date of creation in the table sheSystemDbBackFilesTable.
				notification:
				 sheSystemRefreshDbmBackupFilesTable
				 
				dbReloadSpecificFile:
				- Reload a specific file from sheSystemDbBackFilesTable
				  into the DSLAM. If successful, the CXU perform a reset 
				  for activation.
				notification:
				 sheSystemDbmResult
				
				setBackupPeriod:
				- Configure the backup period settings for automatic remote 
				  backup to ftp server and local backup to EEPROM.   
				notification:
				 sheSystemDbmBackupPeriodSet
				
				setLocalBackupAdminState:
				- Enables or disables the automatic local backup feature.
				notification:
				 sheSystemDbmLocalBackupAdminstateSet
				
				setRemoteBackupAdminState:
				- Enables or disables the automatic remote backup feature.
				notification:
				 sheSystemDbmRemoteBackupAdminstateSet
				
				"
			::= { sheSystemDbmControl 1 }

		
		sheSystemDbmControlStatus OBJECT-TYPE
			SYNTAX SheControlStatusType
			MAX-ACCESS read-only
			STATUS current
			DESCRIPTION
				" The status of the control request. "
			::= { sheSystemDbmControl 2 }

		
		sheSystemDbmControlTimer OBJECT-TYPE
			SYNTAX Unsigned32
			MAX-ACCESS read-only
			STATUS current
			DESCRIPTION
				" The maximum wait time for the manager when a DB storage
				request cannot be executed immediately (value commExecStarted
				in the result attribute sheSystemMaintenanceControlReqResult).
				The manager reads this value from the DSLAM.
				The end of request indicates the trap sheSystemTrDbBackup. "
			::= { sheSystemDbmControl 3 }

		
		sheSystemDbmControlReqResultLocal OBJECT-TYPE
			SYNTAX SheSystemMaintenanceControlReqResult
			MAX-ACCESS read-only
			STATUS current
			DESCRIPTION
				" The result of the local backup request. "
			::= { sheSystemDbmControl 4 }

		
		sheSystemDbmControlReqResultRemote OBJECT-TYPE
			SYNTAX SheSystemMaintenanceControlReqResult
			MAX-ACCESS read-only
			STATUS current
			DESCRIPTION
				" The result of the last remote backup request. "
			::= { sheSystemDbmControl 5 }

		
		sheSystemDbmControlTimeStamp OBJECT-TYPE
			SYNTAX Unsigned32
			UNITS "sec"
			MAX-ACCESS read-only
			STATUS current
			DESCRIPTION
				" The time stamp of the last command (end of command). "
			::= { sheSystemDbmControl 6 }

		
		sheSystemDbmControlServerAddr OBJECT-TYPE
			SYNTAX OCTET STRING (SIZE (0..20))
			MAX-ACCESS read-write
			STATUS current
			DESCRIPTION
				"Address of DB FTP server (dotted notation)."
			::= { sheSystemDbmControl 7 }

		
		sheSystemDbmControlPathName OBJECT-TYPE
			SYNTAX OCTET STRING (SIZE (0..128))
			MAX-ACCESS read-write
			STATUS current
			DESCRIPTION
				"Path name of DB backup files on FTP server. 
				This path should be set relative to the ftp-server root.
				Use only linux notation ( / ). 
				
				Spaces in pathnames are not allowed, because of possible problems with
				different FTP implementations (client and/or server)!!"
			::= { sheSystemDbmControl 8 }

		
		sheSystemDbmControlUsrName OBJECT-TYPE
			SYNTAX OCTET STRING (SIZE (0..20))
			MAX-ACCESS read-write
			STATUS current
			DESCRIPTION
				"Username for DB backup FTP access.                                                             
				
				Read-access to this attribute will deliver 20 times sign '-'  "
			::= { sheSystemDbmControl 9 }

		
		sheSystemDbmControlPassword OBJECT-TYPE
			SYNTAX OCTET STRING (SIZE (0..20))
			MAX-ACCESS read-write
			STATUS current
			DESCRIPTION
				"Password for DB backup FTP access.                                                              
				
				Read-access to this attribute will deliver 20 times sign '-'  "
			::= { sheSystemDbmControl 10 }

		
		sheSystemDbmControlRemoteBackupAdminState OBJECT-TYPE
			SYNTAX SheSystemAdminState
			MAX-ACCESS read-write
			STATUS current
			DESCRIPTION
				"This set the current usage of automatic remote db backup.
				The following states are supported:
				
				unlocked(1)  -> remote db backup handling used
				locked(2)    -> remote db backup handling not used (default)"
			::= { sheSystemDbmControl 11 }

		
		sheSystemDbmControlBackupStartTime OBJECT-TYPE
			SYNTAX Unsigned32 (0..1439)
			UNITS "minute"
			MAX-ACCESS read-write
			STATUS current
			DESCRIPTION
				"Start time basis for remote DB backup after system restart, backup timer 
				reconfigurations or system clock reset.
				The first backup will be started at this time + sheSystemDbmBackupPeriod and
				will then be repeated each sheSystemDbmBackupPeriod.
				Range: 0 (0 am) .. 1439 (23.59 pm).
				Reminder: NE uses always a UTC time base.
				"
			::= { sheSystemDbmControl 12 }

		
		sheSystemDbmControlBackupPeriod OBJECT-TYPE
			SYNTAX Unsigned32 (1..48)
			UNITS "hour"
			MAX-ACCESS read-write
			STATUS current
			DESCRIPTION
				"Interval between two remote backup operations in hours. 
				Backup is started only if there were relevant configuration
				changes during the last period."
			::= { sheSystemDbmControl 13 }

		
		sheSystemDbmControlBackupWaitingPeriod OBJECT-TYPE
			SYNTAX Unsigned32 (1..59)
			UNITS "minute"
			MAX-ACCESS read-write
			STATUS current
			DESCRIPTION
				"Waiting period in minutes before next local backup, in case of configuration changes."
			::= { sheSystemDbmControl 14 }

		
		sheSystemDbmControlBackupMaxFileNumber OBJECT-TYPE
			SYNTAX Unsigned32 (1..32)
			MAX-ACCESS read-write
			STATUS current
			DESCRIPTION
				"This number describes the maximum set of different backup files on the remote ftp site.
				"
			::= { sheSystemDbmControl 15 }

		
		sheSystemDbmControlLocalBackupAdminState OBJECT-TYPE
			SYNTAX SheSystemAdminState
			MAX-ACCESS read-write
			STATUS current
			DESCRIPTION
				"This value administrate the automatic local db backup after sheSystemDbmBackupWaitingPeriod
				in case of configuration actions.
				Default: unlocked  (automatic local backup is enabled)"
			::= { sheSystemDbmControl 16 }

		
		sheSystemDbmControlBackupFileIndex OBJECT-TYPE
			SYNTAX Integer32 (1..32)
			MAX-ACCESS read-write
			STATUS current
			DESCRIPTION
				"The index selects the DB backup file in the sheSystemDbBackupFilesTable which shall be loaded
				into the DSLAM from the FTP server with user command dbReloadSpecificFile. "
			::= { sheSystemDbmControl 17 }

		
		sheSystemDbMaintenanceNotifications OBJECT IDENTIFIER ::= { sheSystemDbMaintenance 4 }

		
		sheSystemDbmBaseSet NOTIFICATION-TYPE
			OBJECTS { sheSystemDbmControlStatus, sheSystemDbmControlTimeStamp, sheSystemDbmControlReqResultRemote, sheSystemDbmControlServerAddr, sheSystemDbmControlPathName
				 }
			STATUS current
			DESCRIPTION 
				"Configuration trap for remote DB basic access settings."
			::= { sheSystemDbMaintenanceNotifications 1 }

		
		sheSystemDbmResult NOTIFICATION-TYPE
			OBJECTS { sheSystemDbmControlTimeStamp, sheSystemDbmControlReqResultLocal, sheSystemDbmControlReqResultRemote, sheSystemDbmControlStatus }
			STATUS current
			DESCRIPTION 
				"Indicates the end and the result of the database backup or restore."
			::= { sheSystemDbMaintenanceNotifications 3 }

		
		sheSystemDbmBackupFilesTableRefreshed NOTIFICATION-TYPE
			OBJECTS { sheSystemDbmControlTimeStamp, sheSystemDbmControlStatus, sheSystemDbmControlReqResultRemote }
			STATUS current
			DESCRIPTION 
				"Indicates end of user command refreshDbmBackupFilesTable."
			::= { sheSystemDbMaintenanceNotifications 4 }

		
		sheSystemDbmBackupPeriodSet NOTIFICATION-TYPE
			OBJECTS { sheSystemDbmControlTimeStamp, sheSystemDbmControlStatus, sheSystemDbmBackupMaxFileNumber, sheSystemDbmControlReqResultLocal, sheSystemDbmBackupPeriod, 
				sheSystemDbmBackupStartTime, sheSystemDbmBackupWaitingPeriod }
			STATUS current
			DESCRIPTION 
				"Settings for automatic backup period are set."
			::= { sheSystemDbMaintenanceNotifications 5 }

		
		sheSystemDbmLocalBackupAdminstateSet NOTIFICATION-TYPE
			OBJECTS { sheSystemDbmControlTimeStamp, sheSystemDbmControlReqResultLocal, sheSystemDbmControlStatus, sheSystemDbmLocalBackupAdminState }
			STATUS current
			DESCRIPTION 
				"Configuration notification for local db backup."
			::= { sheSystemDbMaintenanceNotifications 6 }

		
		sheSystemDbmRemoteBackupAdminstateSet NOTIFICATION-TYPE
			OBJECTS { sheSystemDbmControlTimeStamp, sheSystemDbmControlStatus, sheSystemDbmControlReqResultRemote, sheSystemDbmControlRemoteBackupAdminState }
			STATUS current
			DESCRIPTION 
				"Configuration notification for local db backup."
			::= { sheSystemDbMaintenanceNotifications 7 }

		
		sheSystemDbMaintenanceAlarms OBJECT IDENTIFIER ::= { sheSystemDbMaintenance 5 }

		
		sheSystemLocalDbInvalid NOTIFICATION-TYPE
			OBJECTS { sheAlarmTimeAndDate, sheAlarmReportingSource, sheAlarmReportingSourceType, sheAlarmSeverity }
			STATUS current
			DESCRIPTION 
				"Alarm will be set if the local DB is invalid because of failures during
				read/write local DB or if the local DB was not updated yet after a 
				configuration sequence."
			::= { sheSystemDbMaintenanceAlarms 1 }

		
		sheSystemRemoteDbInvalid NOTIFICATION-TYPE
			OBJECTS { sheAlarmTimeAndDate, sheAlarmReportingSource, sheAlarmReportingSourceType, sheAlarmSeverity }
			STATUS current
			DESCRIPTION 
				"Alarm will be set if the remote DB is invalid because of failures during 
				read/write remote DB or if the remote DB was not updated yet after a 
				configuration sequence."
			::= { sheSystemDbMaintenanceAlarms 2 }

		
		sheSystemDbFtpAccessError NOTIFICATION-TYPE
			OBJECTS { sheAlarmTimeAndDate, sheAlarmReportingSource, sheAlarmReportingSourceType, sheAlarmSeverity }
			STATUS current
			DESCRIPTION 
				"Alarm will be set because of failures during read or write on DB Ftp server."
			::= { sheSystemDbMaintenanceAlarms 3 }

		
-- New supported with SHE R2.6.
		sheSystemIpConfig OBJECT IDENTIFIER ::= { sheSystem 12 }

		
		sheSystemIpHostTable OBJECT-TYPE
			SYNTAX SEQUENCE OF SheSystemIpHostEntry
			MAX-ACCESS not-accessible
			STATUS current
			DESCRIPTION
				"This table contains attributes for each IP host interface."
			::= { sheSystemIpConfig 1 }

		
		sheSystemIpHostEntry OBJECT-TYPE
			SYNTAX SheSystemIpHostEntry
			MAX-ACCESS not-accessible
			STATUS current
			DESCRIPTION
				"An entry represents a set of configurations in sheSystemIpHostTable. 
				"
			INDEX { sheSystemIpHostIndex }
			::= { sheSystemIpHostTable 1 }

		
		SheSystemIpHostEntry ::=
			SEQUENCE { 
				sheSystemIpHostIndex
					Unsigned32,
				sheSystemIpHostName
					DisplayString,
				sheSystemIpHostUseDhcp
					SheSystemIpHostUseDhcpType,
				sheSystemIpHostIpAddress
					IpAddress,
				sheSystemIpHostSubnetMask
					IpAddress,
				sheSystemIpHostOuterVlanId
					Unsigned32,
				sheSystemIpHostInnerVlanId
					Unsigned32,
				sheSystemIpHostDescription
					OCTET STRING
			 }

		sheSystemIpHostIndex OBJECT-TYPE
			SYNTAX Unsigned32
			MAX-ACCESS read-only
			STATUS current
			DESCRIPTION
				"Table index. Each index uniquely identifies one Ip host table entry."
			::= { sheSystemIpHostEntry 1 }

		
		sheSystemIpHostName OBJECT-TYPE
			SYNTAX DisplayString (SIZE (1..32))
			MAX-ACCESS read-only
			STATUS current
			DESCRIPTION
				"A descriptional name that uniquely identifies a entry of this table.
				The name is selected by the NE and identify the interface also on CLI."
			::= { sheSystemIpHostEntry 2 }

		
		sheSystemIpHostUseDhcp OBJECT-TYPE
			SYNTAX SheSystemIpHostUseDhcpType
			MAX-ACCESS read-only
			STATUS current
			DESCRIPTION
				"Either to use Dhcp or not. If set to 0 (default) no DHCP will be used.
				Valid values:
				noUseDhcp(0),
				useDhcp(1)
				
				Note: Currently no support planed."
			DEFVAL { noUseDhcp }
			::= { sheSystemIpHostEntry 3 }

		
		sheSystemIpHostIpAddress OBJECT-TYPE
			SYNTAX IpAddress
			MAX-ACCESS read-only
			STATUS current
			DESCRIPTION
				"IpAddress. Assigned by operator request or by DHCP if used."
			::= { sheSystemIpHostEntry 4 }

		
		sheSystemIpHostSubnetMask OBJECT-TYPE
			SYNTAX IpAddress
			MAX-ACCESS read-only
			STATUS current
			DESCRIPTION
				"subnet mask"
			::= { sheSystemIpHostEntry 5 }

		
		sheSystemIpHostOuterVlanId OBJECT-TYPE
			SYNTAX Unsigned32 (0 | 1..4093)
			MAX-ACCESS read-only
			STATUS current
			DESCRIPTION
				"The host vlan for these ip interface which should be used as outer tag in double tagging mode
				or in single tagging mode.
				Set to 0 if no host VLAN should be used."
			DEFVAL { 0 }
			::= { sheSystemIpHostEntry 6 }

		
		sheSystemIpHostInnerVlanId OBJECT-TYPE
			SYNTAX Unsigned32 (0 | 1..4093)
			MAX-ACCESS read-only
			STATUS current
			DESCRIPTION
				"The host vlan for these ip interface which should be used as inner tag if the NE
				run in double tagging mode.
				Set to 0 if no host VLAN should be used or if the NE uses single tag mode."
			DEFVAL { 0 }
			::= { sheSystemIpHostEntry 7 }

		
		sheSystemIpHostDescription OBJECT-TYPE
			SYNTAX OCTET STRING (SIZE (0..32))
			MAX-ACCESS read-only
			STATUS current
			DESCRIPTION
				"Could describe who uses this ip interface. This description could be used
				by the operator to store information about the intended interface usage. The
				parameter will not be evaluated by the NE."
			::= { sheSystemIpHostEntry 8 }

		
		sheSystemIpHostControl OBJECT IDENTIFIER ::= { sheSystemIpConfig 2 }

		
		sheSystemIpHostControlRequest OBJECT-TYPE
			SYNTAX SheSystemIpControlReqType
			MAX-ACCESS read-write
			STATUS current
			DESCRIPTION
				"The request of a user command.
				createSystemIpHost    (50)
				      sheSystemIpHostControlUseDhcp
				      sheSystemIpHostControlIpAddress
				      sheSystemIpHostControlSubnetMask
				      sheSystemIpHostControlOuterVlanId
				      sheSystemIpHostControlInnerVlanId
				      sheSystemIpHostControlDescription      
				 
				deleteSystemIpHost    (51), 
				      sheSystemIpHostControlIndex 
				 
				modifySystemIpHost    (52), 
				      sheSystemIpHostControlIndex 
				      sheSystemIpHostControlUseDhcp
				      sheSystemIpHostControlIpAddress
				      sheSystemIpHostControlSubnetMask
				      sheSystemIpHostControlOuterVlanId
				      sheSystemIpHostControlInnerVlanId
				      sheSystemIpHostControlDescription"
			::= { sheSystemIpHostControl 1 }

		
		sheSystemIpHostControlIndex OBJECT-TYPE
			SYNTAX Unsigned32
			MAX-ACCESS read-write
			STATUS current
			DESCRIPTION
				"Table index"
			::= { sheSystemIpHostControl 2 }

		
		sheSystemIpHostControlStatus OBJECT-TYPE
			SYNTAX SheControlStatusType
			MAX-ACCESS read-only
			STATUS current
			DESCRIPTION
				"The status of a user command."
			::= { sheSystemIpHostControl 3 }

		
		sheSystemIpHostControlReqResult OBJECT-TYPE
			SYNTAX SheSystemControlRequestResultType
			MAX-ACCESS read-only
			STATUS current
			DESCRIPTION
				"The result of the last user command."
			::= { sheSystemIpHostControl 4 }

		
		sheSystemIpHostControlTimer OBJECT-TYPE
			SYNTAX Gauge32
			MAX-ACCESS read-only
			STATUS current
			DESCRIPTION
				"The maximum wait time for the manager for a long running user command."
			::= { sheSystemIpHostControl 5 }

		
		sheSystemIpHostControlTimeStamp OBJECT-TYPE
			SYNTAX Unsigned32
			UNITS "sec"
			MAX-ACCESS read-only
			STATUS current
			DESCRIPTION
				"The time stamp of the last command (end of command)."
			::= { sheSystemIpHostControl 6 }

		
		sheSystemIpHostControlName OBJECT-TYPE
			SYNTAX DisplayString (SIZE (1..32))
			MAX-ACCESS read-only
			STATUS current
			DESCRIPTION
				"A descriptional name that uniquely identifies an entry of this table. 
				This name was selected by the NE and identifies the interface also on CLI."
			::= { sheSystemIpHostControl 7 }

		
		sheSystemIpHostControlUseDhcp OBJECT-TYPE
			SYNTAX SheSystemIpHostUseDhcpType
			MAX-ACCESS read-write
			STATUS current
			DESCRIPTION
				"Either to use Dhcp or not. If set to 0 (default) no DHCP will be used.
				Valid values:
				noUseDhcp(0),
				useDhcp(1)
				
				Note: Currently no support planed."
			::= { sheSystemIpHostControl 8 }

		
		sheSystemIpHostControlIpAddress OBJECT-TYPE
			SYNTAX IpAddress
			MAX-ACCESS read-write
			STATUS current
			DESCRIPTION
				"Ipaddress if no Dhcp is used."
			::= { sheSystemIpHostControl 9 }

		
		sheSystemIpHostControlSubnetMask OBJECT-TYPE
			SYNTAX IpAddress
			MAX-ACCESS read-write
			STATUS current
			DESCRIPTION
				"Subnet mask"
			::= { sheSystemIpHostControl 10 }

		
		sheSystemIpHostControlOuterVlanId OBJECT-TYPE
			SYNTAX Unsigned32 (0 | 1..4093)
			MAX-ACCESS read-write
			STATUS current
			DESCRIPTION
				"The host vlan for these ip interface which should be used as outer tag in double tagging mode
				or in single tagging mode.
				Set to 0 if no host VLAN should be used."
			::= { sheSystemIpHostControl 11 }

		
		sheSystemIpHostControlInnerVlanId OBJECT-TYPE
			SYNTAX Unsigned32 (0 | 1..4093)
			MAX-ACCESS read-write
			STATUS current
			DESCRIPTION
				"The host vlan for these ip interface which should be used as inner tag if the NE
				run in double tagging mode.
				Set to 0 if no host VLAN should be used or if the NE uses single tag mode."
			::= { sheSystemIpHostControl 12 }

		
		sheSystemIpHostControlDescription OBJECT-TYPE
			SYNTAX OCTET STRING (SIZE (0..32))
			MAX-ACCESS read-write
			STATUS current
			DESCRIPTION
				"Could describe who uses this ip interface. This description could be used
				by the operator to store information about the intended interface usage. The
				parameter will not be evaluated by the NE."
			::= { sheSystemIpHostControl 13 }

		
		sheSystemIpRouteTable OBJECT-TYPE
			SYNTAX SEQUENCE OF SheSystemIpRouteEntry
			MAX-ACCESS not-accessible
			STATUS current
			DESCRIPTION
				"This table contains attributes for each static configured IP route.
				Learned routes from routing protocols will not be shown here!"
			::= { sheSystemIpConfig 3 }

		
		sheSystemIpRouteEntry OBJECT-TYPE
			SYNTAX SheSystemIpRouteEntry
			MAX-ACCESS not-accessible
			STATUS current
			DESCRIPTION
				"An entry represents a set of configurations in sheSystemIpRouteTable. 
				"
			INDEX { sheSystemIpRouteIndex }
			::= { sheSystemIpRouteTable 1 }

		
		SheSystemIpRouteEntry ::=
			SEQUENCE { 
				sheSystemIpRouteIndex
					Unsigned32,
				sheSystemIpRouteName
					DisplayString,
				sheSystemIpRouteDestIpAddress
					IpAddress,
				sheSystemIpRouteSubnetMask
					IpAddress,
				sheSystemIpRouteGatewayIpAddress
					IpAddress,
				sheSystemIpRouteMetric
					Integer32
			 }

		sheSystemIpRouteIndex OBJECT-TYPE
			SYNTAX Unsigned32
			MAX-ACCESS read-only
			STATUS current
			DESCRIPTION
				"Table index. Each index uniquely identifies one an Ip route table entry."
			::= { sheSystemIpRouteEntry 1 }

		
		sheSystemIpRouteName OBJECT-TYPE
			SYNTAX DisplayString (SIZE (1..32))
			MAX-ACCESS read-only
			STATUS current
			DESCRIPTION
				"A describable name that uniquely identifies an  entry of this table.
				The name is user specified.
				Special characters like space ? . are not allowed."
			::= { sheSystemIpRouteEntry 2 }

		
		sheSystemIpRouteDestIpAddress OBJECT-TYPE
			SYNTAX IpAddress
			MAX-ACCESS read-only
			STATUS current
			DESCRIPTION
				"Destination IpAddress fotr this route."
			::= { sheSystemIpRouteEntry 4 }

		
		sheSystemIpRouteSubnetMask OBJECT-TYPE
			SYNTAX IpAddress
			MAX-ACCESS read-only
			STATUS current
			DESCRIPTION
				"subnet mask 
				"
			::= { sheSystemIpRouteEntry 5 }

		
		sheSystemIpRouteGatewayIpAddress OBJECT-TYPE
			SYNTAX IpAddress
			MAX-ACCESS read-only
			STATUS current
			DESCRIPTION
				"Gateway IpAddress for this route."
			::= { sheSystemIpRouteEntry 6 }

		
		sheSystemIpRouteMetric OBJECT-TYPE
			SYNTAX Integer32
			MAX-ACCESS read-only
			STATUS current
			DESCRIPTION
				"The routing metric for this route.
				If this metric is not used, its value should be set to -1."
			DEFVAL { -1 }
			::= { sheSystemIpRouteEntry 7 }

		
		sheSystemIpRouteControl OBJECT IDENTIFIER ::= { sheSystemIpConfig 4 }

		
		sheSystemIpRouteControlRequest OBJECT-TYPE
			SYNTAX SheSystemIpControlReqType
			MAX-ACCESS read-write
			STATUS current
			DESCRIPTION
				"The request of a user command.  
				createSystemIpRoute    (55), 
				   sheSystemIpRouteControlName 
				   sheSystemIpRouteControlDestIpAddress
				   sheSystemIpRouteControlGatewayIpAddress  			       	            
				   sheSystemIpRouteControlSubnetMask
				   sheSystemIpRouteControlMetric 			        	 
				         			   
				deleteSystemIpRoute    (56), 
				  sheSystemIpRouteControlIndex 
					 
				modifySystemIpRoute    (57), 
				  sheSystemIpRouteControlIndex 				              
				  sheSystemIpRouteControlDestIpAddress
				  sheSystemIpRouteControlGatewayIpAddress  			       	            
				  sheSystemIpRouteControlSubnetMask 
				  sheSystemIpRouteControlMetric"
			::= { sheSystemIpRouteControl 1 }

		
		sheSystemIpRouteControlIndex OBJECT-TYPE
			SYNTAX Unsigned32
			MAX-ACCESS read-write
			STATUS current
			DESCRIPTION
				"Table index"
			::= { sheSystemIpRouteControl 2 }

		
		sheSystemIpRouteControlStatus OBJECT-TYPE
			SYNTAX SheControlStatusType
			MAX-ACCESS read-only
			STATUS current
			DESCRIPTION
				"The status of a user command."
			::= { sheSystemIpRouteControl 3 }

		
		sheSystemIpRouteControlReqResult OBJECT-TYPE
			SYNTAX SheSystemControlRequestResultType
			MAX-ACCESS read-only
			STATUS current
			DESCRIPTION
				"The result of the last user command."
			::= { sheSystemIpRouteControl 4 }

		
		sheSystemIpRouteControlTimer OBJECT-TYPE
			SYNTAX Gauge32
			MAX-ACCESS read-only
			STATUS current
			DESCRIPTION
				"The maximum wait time for the manager for a  
				long running user command."
			::= { sheSystemIpRouteControl 5 }

		
		sheSystemIpRouteControlTimeStamp OBJECT-TYPE
			SYNTAX Unsigned32
			UNITS "sec"
			MAX-ACCESS read-only
			STATUS current
			DESCRIPTION
				"The time stamp of the last command (end of command)."
			::= { sheSystemIpRouteControl 6 }

		
		sheSystemIpRouteControlName OBJECT-TYPE
			SYNTAX DisplayString (SIZE (1..32))
			MAX-ACCESS read-write
			STATUS current
			DESCRIPTION
				"A describable name that uniquely identifies a entry of this table.
				The route name is user specified."
			::= { sheSystemIpRouteControl 7 }

		
		sheSystemIpRouteControlDestIpAddress OBJECT-TYPE
			SYNTAX IpAddress
			MAX-ACCESS read-write
			STATUS current
			DESCRIPTION
				"Destination Ipaddress."
			::= { sheSystemIpRouteControl 8 }

		
		sheSystemIpRouteControlSubnetMask OBJECT-TYPE
			SYNTAX IpAddress
			MAX-ACCESS read-write
			STATUS current
			DESCRIPTION
				"Subnet mask."
			::= { sheSystemIpRouteControl 9 }

		
		sheSystemIpRouteControlGatewayIpAddress OBJECT-TYPE
			SYNTAX IpAddress
			MAX-ACCESS read-write
			STATUS current
			DESCRIPTION
				"Gateway Ipaddress ."
			::= { sheSystemIpRouteControl 10 }

		
		sheSystemIpRouteControlMetric OBJECT-TYPE
			SYNTAX Integer32
			MAX-ACCESS read-write
			STATUS current
			DESCRIPTION
				"The routing metric for this route.
				If this metric is not used, its value should be
				set to -1."
			::= { sheSystemIpRouteControl 11 }

		
		sheSystemIpHostNotification OBJECT IDENTIFIER ::= { sheSystemIpConfig 5 }

		
		sheSystemIpHostCreated NOTIFICATION-TYPE
			OBJECTS { sheSystemIpHostControlIndex, sheSystemIpHostControlReqResult, sheSystemIpHostControlTimeStamp, sheSystemIpHostControlName, sheSystemIpHostControlUseDhcp, 
				sheSystemIpHostControlIpAddress, sheSystemIpHostControlSubnetMask, sheSystemIpHostControlOuterVlanId, sheSystemIpHostControlInnerVlanId, sheSystemIpHostControlDescription
				 }
			STATUS current
			DESCRIPTION 
				"Configuration trap."
			::= { sheSystemIpHostNotification 1 }

		
		sheSystemIpHostDeleted NOTIFICATION-TYPE
			OBJECTS { sheSystemIpHostControlIndex, sheSystemIpHostControlTimeStamp }
			STATUS current
			DESCRIPTION 
				"Configuration trap."
			::= { sheSystemIpHostNotification 2 }

		
		sheSystemIpHostModified NOTIFICATION-TYPE
			OBJECTS { sheSystemIpHostControlIndex, sheSystemIpHostControlReqResult, sheSystemIpHostControlTimeStamp, sheSystemIpHostControlName, sheSystemIpHostControlUseDhcp, 
				sheSystemIpHostControlIpAddress, sheSystemIpHostControlSubnetMask, sheSystemIpHostControlOuterVlanId, sheSystemIpHostControlInnerVlanId, sheSystemIpHostControlDescription
				 }
			STATUS current
			DESCRIPTION 
				"Configuration trap."
			::= { sheSystemIpHostNotification 3 }

		
		sheSystemIpRouteCreated NOTIFICATION-TYPE
			OBJECTS { sheSystemIpRouteControlIndex, sheSystemIpRouteControlReqResult, sheSystemIpRouteControlTimeStamp, sheSystemIpRouteControlName, sheSystemIpRouteControlDestIpAddress, 
				sheSystemIpRouteControlSubnetMask, sheSystemIpRouteControlGatewayIpAddress, sheSystemIpRouteControlMetric }
			STATUS current
			DESCRIPTION 
				"Configuration trap."
			::= { sheSystemIpHostNotification 4 }

		
		sheSystemIpRouteDeleted NOTIFICATION-TYPE
			OBJECTS { sheSystemIpRouteControlIndex, sheSystemIpRouteControlTimeStamp }
			STATUS current
			DESCRIPTION 
				"Configuration trap."
			::= { sheSystemIpHostNotification 5 }

		
		sheSystemIpRouteModified NOTIFICATION-TYPE
			OBJECTS { sheSystemIpRouteControlIndex, sheSystemIpRouteControlReqResult, sheSystemIpRouteControlTimeStamp, sheSystemIpRouteControlName, sheSystemIpRouteControlDestIpAddress, 
				sheSystemIpRouteControlSubnetMask, sheSystemIpRouteControlGatewayIpAddress, sheSystemIpRouteControlMetric }
			STATUS current
			DESCRIPTION 
				"Configuration trap."
			::= { sheSystemIpHostNotification 6 }
        
        
		sheSystemIpTtl OBJECT IDENTIFIER ::= { sheSystemIpConfig 6 }

		sheSystemIpTtlValue OBJECT-TYPE
			SYNTAX Integer32
			MAX-ACCESS read-only
			STATUS current
			DESCRIPTION
				"The IP TTL value. default 128."
			::= { sheSystemIpTtl 1 }

		sheSystemIpTtlControl OBJECT IDENTIFIER ::= { sheSystemIpTtl 2 }
		
		sheSystemIpTtlControlRequest OBJECT-TYPE
			SYNTAX SheSystemIpControlReqType
			MAX-ACCESS read-write
			STATUS current
			DESCRIPTION
				"The request of a user command.  
				modifySystemIpTtl    (58), 
				  sheSystemIpTtlControlValue"
			::= { sheSystemIpTtlControl 1 }

		
		sheSystemIpTtlControlStatus OBJECT-TYPE
			SYNTAX SheControlStatusType
			MAX-ACCESS read-only
			STATUS current
			DESCRIPTION
				"The status of a user command."
			::= { sheSystemIpTtlControl 2 }
		
		sheSystemIpTtlControlTimer OBJECT-TYPE
			SYNTAX Gauge32
			MAX-ACCESS read-only
			STATUS current
			DESCRIPTION
				"The maximum wait time for the manager for a  
				long running user command."
			::= { sheSystemIpTtlControl 3 }
		
		sheSystemIpTtlControlReqResult OBJECT-TYPE
			SYNTAX SheSystemControlRequestResultType
			MAX-ACCESS read-only
			STATUS current
			DESCRIPTION
				"The result of the last user command."
			::= { sheSystemIpTtlControl 4 }
		
		sheSystemIpTtlControlTimeStamp OBJECT-TYPE
			SYNTAX Unsigned32
			UNITS "sec"
			MAX-ACCESS read-only
			STATUS current
			DESCRIPTION
				"The time stamp of the last command (end of command)."
			::= { sheSystemIpTtlControl 5 }
			
		sheSystemIpTtlControlValue OBJECT-TYPE
			SYNTAX Unsigned32
			MAX-ACCESS read-write
			STATUS current
			DESCRIPTION
				"TTL Value"
			::= { sheSystemIpTtlControl 6 }			
		
		
		sheSystemIpTtlNotification OBJECT IDENTIFIER ::= { sheSystemIpTtl 3 }
		
		sheSystemIpTtlModified NOTIFICATION-TYPE
			OBJECTS { sheSystemIpTtlControlValue, sheSystemIpTtlControlReqResult, sheSystemIpTtControlTimeStamp }
			STATUS current
			DESCRIPTION 
				"Configuration trap."
			::= { sheSystemIpTtlNotification 1 }

     
--		syslog Mgmt feature
        sheSystemSyslog OBJECT IDENTIFIER ::= { sheSystem 13 }

		sheSystemSyslogAdminStatus OBJECT-TYPE
			SYNTAX INTEGER
			{
			enable(1),
			disable(2)			
			}
			MAX-ACCESS read-only
			STATUS current
			DESCRIPTION
				"Syslog status."
			::= { sheSystemSyslog 1 }	           
		           
		           
		sheSystemSyslogBindAddress OBJECT-TYPE
			SYNTAX IpAddress
			MAX-ACCESS read-only
			STATUS current
			DESCRIPTION
				"Syslog bind address."
			::= { sheSystemSyslog 2 }	           
		          
		           
		sheSystemSyslogBindInterface OBJECT-TYPE
			SYNTAX OCTET STRING
			MAX-ACCESS read-only
			STATUS current
			DESCRIPTION
				"Syslog bind interface."
			::= { sheSystemSyslog 3 }	
			
        
		sheSystemSyslogLocalCode OBJECT-TYPE
			SYNTAX INTEGER (-1 | 0..7)
			MAX-ACCESS read-only
			STATUS current
			DESCRIPTION
				"Syslog Local code."
			::= { sheSystemSyslog 4 }
					                      
		sheSystemSyslogMaxSize OBJECT-TYPE
			SYNTAX Integer32
			MAX-ACCESS read-only
			STATUS current
			DESCRIPTION
				"Syslog local storage max-size."
			::= { sheSystemSyslog 5 }
					                      
		sheSystemSyslogConfTable OBJECT-TYPE
			SYNTAX SEQUENCE OF SheSystemSyslogConfEntry
			MAX-ACCESS not-accessible
			STATUS current
			DESCRIPTION
				"Description."
			::= { sheSystemSyslog 11 }

		
		sheSystemSyslogConfEntry OBJECT-TYPE
			SYNTAX SheSystemSyslogConfEntry
			MAX-ACCESS not-accessible
			STATUS current
			DESCRIPTION
				"Description."
			INDEX { sheSystemSyslogConfIndex }
			::= { sheSystemSyslogConfTable 1 }

		
		SheSystemSyslogConfEntry ::=
			SEQUENCE { 
				sheSystemSyslogConfIndex
					Integer32,
				sheSystemSyslogConfMode
					INTEGER,
				sheSystemSyslogConfFacility
					INTEGER,
				sheSystemSyslogConfSeverity
					INTEGER,
				sheSystemSyslogConfTarget
					INTEGER,
				sheSystemSyslogConfStorage
					INTEGER,
				sheSystemSyslogConfTargetAddress
					IpAddress
			 }

					                      
		sheSystemSyslogConfIndex OBJECT-TYPE
			SYNTAX Integer32 (1..255)
			MAX-ACCESS read-only
			STATUS current
			DESCRIPTION
				"Message index"
			::= { sheSystemSyslogConfEntry 1 }

		
		sheSystemSyslogConfMode OBJECT-TYPE
			SYNTAX INTEGER
				{
				general(0),
				priority(1)
				}
			MAX-ACCESS read-only
			STATUS current
			DESCRIPTION
				"Name of the facility that generated message."
			::= { sheSystemSyslogConfEntry 2 }

		
		sheSystemSyslogConfFacility OBJECT-TYPE
			SYNTAX INTEGER
				{
				auth(0),
				authpriv(1),
				kern(2),
				local0(3),
				local1(4),
				local2(5),
				local3(6),
				local4(7),
				local5(8),
				local6(9),
				local7(10),
				syslog(11),
				user(12),
				nomap(99)
				}
			MAX-ACCESS read-only
			STATUS current
			DESCRIPTION
				"Name of the facility that generated message.
				16~23: local"
			::= { sheSystemSyslogConfEntry 3 }

		
		sheSystemSyslogConfSeverity OBJECT-TYPE
			SYNTAX INTEGER
				{
				emergency(0),
				alert(1),
				critical(2),
				error(3),
				warning(4),
				notice(5),
				info(6),
				debug(7),
				other(99)
				}
			MAX-ACCESS read-only
			STATUS current
			DESCRIPTION
				"The severity of the message"
			::= { sheSystemSyslogConfEntry 4 }

		
		sheSystemSyslogConfTarget OBJECT-TYPE
			SYNTAX INTEGER
				{
				local(1),
				consol(2),
				remote(3)
				}
			MAX-ACCESS read-only
			STATUS current
			DESCRIPTION
				"Target type"
			::= { sheSystemSyslogConfEntry 5 }

		sheSystemSyslogConfStorage OBJECT-TYPE
			SYNTAX INTEGER
				{
				notAvailable(-1),
				volatile(0),
				nonvolatile(1)
				}
			MAX-ACCESS read-only
			STATUS current
			DESCRIPTION
				"Description."
			::= { sheSystemSyslogConfEntry 6 }

		
		sheSystemSyslogConfTargetAddress OBJECT-TYPE
			SYNTAX IpAddress
			MAX-ACCESS read-only
			STATUS current
			DESCRIPTION
				"Description."
			::= { sheSystemSyslogConfEntry 7 }


		sheSystemSyslogConfControl OBJECT IDENTIFIER ::= { sheSystemSyslog 12 }

		sheSystemSyslogConfControlRequest OBJECT-TYPE
			SYNTAX INTEGER
				{         
				setSyslogStatus(1),
				setSyslogBindAddress(2),
				setSyslogBindInterface(3),
				setSyslogMaxSize(4),
				setSyslogLocalCode(5),
				createSyslogConf(6),
				destroySyslogConf(7)
				}
			MAX-ACCESS read-write
			STATUS current
			DESCRIPTION
				"Description."
			::= { sheSystemSyslogConfControl 1 }

		sheSystemSyslogConfControlStatus OBJECT-TYPE
			SYNTAX SheControlStatusType
			MAX-ACCESS read-only
			STATUS current
			DESCRIPTION
				"Description."
			::= { sheSystemSyslogConfControl 2 }

		sheSystemSyslogConfControlTimer OBJECT-TYPE
			SYNTAX Gauge32
			MAX-ACCESS read-write
			STATUS current
			DESCRIPTION
				"Description."
			::= { sheSystemSyslogConfControl 3 }

		
		sheSystemSyslogConfControlTimeStamp OBJECT-TYPE
			SYNTAX TimeTicks
			MAX-ACCESS read-only
			STATUS current
			DESCRIPTION
				"Description."
			::= { sheSystemSyslogConfControl 4 }

		sheSystemSyslogConfControlReqResult OBJECT-TYPE
			SYNTAX SheSystemControlRequestResultType
			MAX-ACCESS read-only
			STATUS current
			DESCRIPTION
				"Description."
			::= { sheSystemSyslogConfControl 5 }
			
			
		sheSystemSyslogConfControlAdminStatus OBJECT-TYPE
			SYNTAX INTEGER
			{
			enable(1),
			disable(2)			
			}
			MAX-ACCESS read-write
			STATUS current
			DESCRIPTION
				"Syslog status."
			::= { sheSystemSyslogConfControl 6 }	           
		           
		           
		sheSystemSyslogConfControlBindAddress OBJECT-TYPE
			SYNTAX IpAddress
			MAX-ACCESS read-write
			STATUS current
			DESCRIPTION
				"Syslog bind address."
			::= { sheSystemSyslogConfControl 7 }	           
		          
		           
		sheSystemSyslogConfControlBindInterface OBJECT-TYPE
			SYNTAX OCTET STRING
			MAX-ACCESS read-write
			STATUS current
			DESCRIPTION
				"Syslog bind interface."
			::= { sheSystemSyslogConfControl 8 }	
			
        sheSystemSyslogConfControlMaxSize OBJECT-TYPE
			SYNTAX Integer32
			MAX-ACCESS read-write
			STATUS current
			DESCRIPTION
				"Syslog local storage max-size."
			::= { sheSystemSyslogConfControl 9 }
			
		sheSystemSyslogConfControlLocalCode OBJECT-TYPE
			SYNTAX INTEGER (-1 | 0..7)
			MAX-ACCESS read-write
			STATUS current
			DESCRIPTION
				"Syslog Local code."
			::= { sheSystemSyslogConfControl 10 }
			

		sheSystemSyslogConfControlIndex OBJECT-TYPE
			SYNTAX Integer32
			MAX-ACCESS read-write
			STATUS current
			DESCRIPTION
				"Description."
			::= { sheSystemSyslogConfControl 11 }

		
		sheSystemSyslogConfControlMode OBJECT-TYPE
			SYNTAX INTEGER
				{
				general(0),
				priority(1)
				}
			MAX-ACCESS read-write
			STATUS current
			DESCRIPTION
				"Description."
			::= { sheSystemSyslogConfControl 12 }

		sheSystemSyslogConfControlSeverity OBJECT-TYPE
			SYNTAX INTEGER
				{
				emergency(0),
				alert(1),
				critical(2),
				error(3),
				warning(4),
				notice(5),
				info(6),
				debug(7),
				other(99)
				}
			MAX-ACCESS read-write
			STATUS current
			DESCRIPTION
				"Description."
			::= { sheSystemSyslogConfControl 13 }

		sheSystemSyslogConfControlFacility OBJECT-TYPE
			SYNTAX INTEGER
				{
				auth(0),
				authpriv(1),
				kern(2),
				local0(3),
				local1(4),
				local2(5),
				local3(6),
				local4(7),
				local5(8),
				local6(9),
				local7(10),
				syslog(11),
				user(12),
				nomap(99)
				}
			MAX-ACCESS read-write
			STATUS current
			DESCRIPTION
				"Description."
			::= { sheSystemSyslogConfControl 14 }

		sheSystemSyslogConfControlTarget OBJECT-TYPE
			SYNTAX INTEGER
				{
				local(1),
				consol(2),
				remote(3)
				}
			MAX-ACCESS read-write
			STATUS current
			DESCRIPTION
				"Target type"
			::= { sheSystemSyslogConfControl 15 }


		sheSystemSyslogConfControlStorage OBJECT-TYPE
			SYNTAX INTEGER
				{
				notAvailable(-1),
				volatile(0),
				nonvolatile(1)
				}
			MAX-ACCESS read-write
			STATUS current
			DESCRIPTION
				"Description"
			::= { sheSystemSyslogConfControl 16 }

		
		sheSystemSyslogConfControlTargetAddress OBJECT-TYPE
			SYNTAX IpAddress
			MAX-ACCESS read-write
			STATUS current
			DESCRIPTION
				"Description"
			::= { sheSystemSyslogConfControl 17 }
		   

		sheSystemSyslogConfNotification OBJECT IDENTIFIER ::= { sheSystemSyslog 13 }
		
		
		sheSystemSyslogConfAdminStatusChanged NOTIFICATION-TYPE
			OBJECTS { sheSystemSyslogConfControlRequest, sheSystemSyslogConfControlReqResult, sheSystemSyslogConfControlTimeStamp,
			sheSystemSyslogConfControlAdminStatus	}
			STATUS current
			DESCRIPTION 
				"Description."
			::= { sheSystemSyslogConfNotification 1 }

 		sheSystemSyslogConfBindAddressChanged NOTIFICATION-TYPE
			OBJECTS { sheSystemSyslogConfControlRequest, sheSystemSyslogConfControlReqResult, sheSystemSyslogConfControlTimeStamp,
			sheSystemSyslogConfControlBindAddress	}
			STATUS current
			DESCRIPTION 
				"Description."
			::= { sheSystemSyslogConfNotification 2 }


 		sheSystemSyslogConfBindInterfaceChanged NOTIFICATION-TYPE
			OBJECTS { sheSystemSyslogConfControlRequest, sheSystemSyslogConfControlReqResult, sheSystemSyslogConfControlTimeStamp,
			sheSystemSyslogConfControlBindInterface	}
			STATUS current
			DESCRIPTION 
				"Description."
			::= { sheSystemSyslogConfNotification 3 }

 		sheSystemSyslogConfLocalCodeChanged NOTIFICATION-TYPE
			OBJECTS { sheSystemSyslogConfControlRequest, sheSystemSyslogConfControlReqResult, sheSystemSyslogConfControlTimeStamp,
			sheSystemSyslogConfControlLocalCode	}
			STATUS current
			DESCRIPTION 
				"Description."
			::= { sheSystemSyslogConfNotification 4 }


		sheSystemSyslogConfCreated NOTIFICATION-TYPE
			OBJECTS { sheSystemSyslogConfControlRequest, sheSystemSyslogConfControlReqResult, sheSystemSyslogConfControlTimeStamp, sheSystemSyslogConfMode, sheSystemSyslogConfFacility, 
				sheSystemSyslogConfSeverity, sheSystemSyslogConfTarget, sheSystemSyslogConfStorage, sheSystemSyslogConfTargetAddress }
			STATUS current
			DESCRIPTION 
				"Description."
			::= { sheSystemSyslogConfNotification 5 }

		
		sheSystemSyslogConfDestroyed NOTIFICATION-TYPE
			OBJECTS { sheSystemSyslogConfControlRequest, sheSystemSyslogConfControlReqResult, sheSystemSyslogConfControlTimeStamp, sheSystemSyslogConfControlIndex }
			STATUS current
			DESCRIPTION 
				"Description."
			::= { sheSystemSyslogConfNotification 6 }


--		user Mgmt feature
        sheSystemUser OBJECT IDENTIFIER ::= { sheSystem 14 }
        
		sheSystemUserTable OBJECT-TYPE
			SYNTAX SEQUENCE OF SheSystemUserEntry
			MAX-ACCESS not-accessible
			STATUS current
			DESCRIPTION
				"Description."
			::= { sheSystemUser 1 }

		
		sheSystemUserEntry OBJECT-TYPE
			SYNTAX SheSystemUserEntry
			MAX-ACCESS not-accessible
			STATUS current
			DESCRIPTION
				"Description."
			INDEX { sheSystemUserName }
			::= { sheSystemUserTable 1 }

		
		SheSystemUserEntry ::=
			SEQUENCE { 
				sheSystemUserName
					OCTET STRING,
				sheSystemUserLevel
					INTEGER,
				sheSystemUserPassword
					OCTET STRING,
				sheSystemUserDesc
					OCTET STRING
			 }

		sheSystemUserName OBJECT-TYPE
			SYNTAX OCTET STRING (SIZE (1..255))
			MAX-ACCESS read-only
			STATUS current
			DESCRIPTION
				"User Name. where 'admin' is reserved name."
			::= { sheSystemUserEntry 1 }

		
		sheSystemUserLevel OBJECT-TYPE
			SYNTAX INTEGER (0..15)
			MAX-ACCESS read-only
			STATUS current
			DESCRIPTION
				"User's level"
			::= { sheSystemUserEntry 2 }

		
		sheSystemUserPassword OBJECT-TYPE
			SYNTAX OCTET STRING (SIZE (0..255))
			MAX-ACCESS read-only
			STATUS current
			DESCRIPTION
				"User's password (always encrypted)"
			::= { sheSystemUserEntry 3 }

		sheSystemUserDesc OBJECT-TYPE
			SYNTAX OCTET STRING (SIZE (0..255))
			MAX-ACCESS read-only
			STATUS current
			DESCRIPTION
				"User Description"
			::= { sheSystemUserEntry 4 }

		
		sheSystemUserControl OBJECT IDENTIFIER ::= { sheSystemUser 2 }

		sheSystemUserControlRequest OBJECT-TYPE
			SYNTAX INTEGER
				{
				addUser(1),
				renameUser(2),
				setPassword(3),
				deleteUser(4)
				}
			MAX-ACCESS read-write
			STATUS current
			DESCRIPTION
				"Description."
			::= { sheSystemUserControl 1 }

		sheSystemUserControlStatus OBJECT-TYPE
			SYNTAX SheControlStatusType
			MAX-ACCESS read-only
			STATUS current
			DESCRIPTION
				"Description."
			::= { sheSystemUserControl 2 }

		sheSystemUserControlTimer OBJECT-TYPE
			SYNTAX Gauge32
			MAX-ACCESS read-write
			STATUS current
			DESCRIPTION
				"Description."
			::= { sheSystemUserControl 3 }

		
		sheSystemUserControlTimeStamp OBJECT-TYPE
			SYNTAX TimeTicks
			MAX-ACCESS read-only
			STATUS current
			DESCRIPTION
				"Description."
			::= { sheSystemUserControl 4 }

		
		sheSystemUserControlReqResult OBJECT-TYPE
			SYNTAX SheSystemControlRequestResultType
			MAX-ACCESS read-only
			STATUS current
			DESCRIPTION
				"Result of the last command."
			::= { sheSystemUserControl 5 }

		
		sheSystemUserControlName OBJECT-TYPE
			SYNTAX OCTET STRING (SIZE (1..255))
			MAX-ACCESS read-write
			STATUS current
			DESCRIPTION
				"User Name. where 'admin' is reserved name."
			::= { sheSystemUserControl 6 }

		
		sheSystemUserControlRename OBJECT-TYPE
			SYNTAX OCTET STRING (SIZE (1..255))
			MAX-ACCESS read-write
			STATUS current
			DESCRIPTION
				"New User Name. where 'admin' is reserved name. (when rename user.)"
			::= { sheSystemUserControl 7 }

		
		sheSystemUserControlLevel OBJECT-TYPE
			SYNTAX INTEGER (0..15)
			MAX-ACCESS read-write
			STATUS current
			DESCRIPTION
				"User's level"
			::= { sheSystemUserControl 8 }

		
		sheSystemUserControlPwType OBJECT-TYPE
			SYNTAX INTEGER
				{
				plain(1),
				encrypt(2)
				}
			MAX-ACCESS read-write
			STATUS current
			DESCRIPTION
				"Description."
			::= { sheSystemUserControl 9 }

		
		sheSystemUserControlPassword OBJECT-TYPE
			SYNTAX OCTET STRING (SIZE (0..255))
			MAX-ACCESS read-write
			STATUS current
			DESCRIPTION
				"User's password"
			::= { sheSystemUserControl 10 }

		
		sheSystemUserControlDesc OBJECT-TYPE
			SYNTAX OCTET STRING (SIZE (0..255))
			MAX-ACCESS read-write
			STATUS current
			DESCRIPTION
				"User Description"
			::= { sheSystemUserControl 11 }

		
		sheSystemUserNotification OBJECT IDENTIFIER ::= { sheSystemUser 3 }

		
		sheSystemUserCreated NOTIFICATION-TYPE
			OBJECTS { sheSystemUserControlRequest, sheSystemUserControlTimeStamp, sheSystemUserControlReqResult, sheSystemUserLevel, sheSystemUserPassword, 
				sheSystemUserDesc }
			STATUS current
			DESCRIPTION 
				"addUser"
			::= { sheSystemUserNotification 1 }

		
		sheSystemUserNameChanged NOTIFICATION-TYPE
			OBJECTS { sheSystemUserControlRequest, sheSystemUserControlTimeStamp, sheSystemUserControlReqResult, sheSystemUserControlName, sheSystemUserControlRename
				 }
			STATUS current
			DESCRIPTION 
				"renameUser"
			::= { sheSystemUserNotification 2 }

		
		sheSystemUserPasswordChanged NOTIFICATION-TYPE
			OBJECTS { sheSystemUserControlRequest, sheSystemUserControlTimeStamp, sheSystemUserControlReqResult, sheSystemUserPassword }
			STATUS current
			DESCRIPTION 
				"setPassword"
			::= { sheSystemUserNotification 3 }

		
		sheSystemUserDestroyed NOTIFICATION-TYPE
			OBJECTS { sheSystemUserControlRequest, sheSystemUserControlTimeStamp, sheSystemUserControlReqResult, sheSystemUserControlName }
			STATUS current
			DESCRIPTION 
				"deleteUser"
			::= { sheSystemUserNotification 4 }

                   
                   
--		security Mgmt feature  : RADIUS/TACACS/dot1x/ACL(arule)
        sheSystemSecurity OBJECT IDENTIFIER ::= { sheSystem 15 }

        sheSystemAcl	  OBJECT IDENTIFIER ::= { sheSystemSecurity 1 }    
            
		sheSystemAclTable OBJECT-TYPE
			SYNTAX SEQUENCE OF SheSystemAclEntry
			MAX-ACCESS not-accessible
			STATUS current
			DESCRIPTION
				"Description"
			::= { sheSystemAcl 1 }

		
		-- 1.3.6.1.4.1.6296.101.7.5.1.1
		sheSystemAclEntry OBJECT-TYPE
			SYNTAX SheSystemAclEntry
			MAX-ACCESS not-accessible
			STATUS current
			DESCRIPTION
				"Description."
			INDEX { sheSystemAclName }
			::= { sheSystemAclTable 1 }

		
		SheSystemAclEntry ::=
			SEQUENCE { 
				sheSystemAclName
					OCTET STRING,
				sheSystemAclSrcIpAddr
					IpAddress,
				sheSystemAclSrcPrefixLength
					Integer32,
				sheSystemAclDstIpAddr
					IpAddress,
				sheSystemAclDstPrefixLength
					Integer32,
				sheSystemAclDscp
					Integer32,
				sheSystemAclProtocolType
					Integer32,
				sheSystemAclTcpFlag
					BITS,
				sheSystemAclSrcL4Port
					Integer32,
				sheSystemAclDstL4Port
					Integer32,
				sheSystemAclPktLen
					Integer32,
				sheSystemAclValidFlags
					BITS,
				sheSystemAclMatchFlags
					BITS,
				sheSystemAclMatchAction
					INTEGER,
				sheSystemAclNomatchAction
					INTEGER,
				sheSystemAclPriority
					INTEGER
			 }

		-- 1.3.6.1.4.1.6296.101.7.5.1.1.1
		sheSystemAclName OBJECT-TYPE
			SYNTAX OCTET STRING (SIZE (0..63))
			MAX-ACCESS read-only
			STATUS current
			DESCRIPTION
				"Description"
			::= { sheSystemAclEntry 1 }

		
		-- 1.3.6.1.4.1.6296.101.7.5.1.1.2
		sheSystemAclSrcIpAddr OBJECT-TYPE
			SYNTAX IpAddress
			MAX-ACCESS read-only
			STATUS current
			DESCRIPTION
				"Description"
			::= { sheSystemAclEntry 2 }

		
		-- 1.3.6.1.4.1.6296.101.7.5.1.1.3
		sheSystemAclSrcPrefixLength OBJECT-TYPE
			SYNTAX Integer32 (0..31)
			MAX-ACCESS read-only
			STATUS current
			DESCRIPTION
				"Description"
			::= { sheSystemAclEntry 3 }

		
		-- 1.3.6.1.4.1.6296.101.7.5.1.1.4
		sheSystemAclDstIpAddr OBJECT-TYPE
			SYNTAX IpAddress
			MAX-ACCESS read-only
			STATUS current
			DESCRIPTION
				"Description"
			::= { sheSystemAclEntry 4 }

		
		-- 1.3.6.1.4.1.6296.101.7.5.1.1.5
		sheSystemAclDstPrefixLength OBJECT-TYPE
			SYNTAX Integer32 (0..31)
			MAX-ACCESS read-only
			STATUS current
			DESCRIPTION
				"Description"
			::= { sheSystemAclEntry 5 }

		
		-- 1.3.6.1.4.1.6296.101.7.5.1.1.6
		sheSystemAclDscp OBJECT-TYPE
			SYNTAX Integer32
			MAX-ACCESS read-only
			STATUS current
			DESCRIPTION
				"Description"
			DEFVAL { -1 }
			::= { sheSystemAclEntry 6 }

		
		-- 1.3.6.1.4.1.6296.101.7.5.1.1.7
		sheSystemAclProtocolType OBJECT-TYPE
			SYNTAX Integer32 (1..255)
			MAX-ACCESS read-only
			STATUS current
			DESCRIPTION
				"Description"
			::= { sheSystemAclEntry 7 }

		
		-- 1.3.6.1.4.1.6296.101.7.5.1.1.8
		sheSystemAclTcpFlag OBJECT-TYPE
			SYNTAX BITS
				{
				reserv(0),
				reserv1(1),
				urg(2),
				ack(3),
				psh(4),
				rst(5),
				syn(6),
				fin(7)
				}
			MAX-ACCESS read-only
			STATUS current
			DESCRIPTION
				"Description"
			::= { sheSystemAclEntry 8 }

		
		-- 1.3.6.1.4.1.6296.101.7.5.1.1.9
		sheSystemAclSrcL4Port OBJECT-TYPE
			SYNTAX Integer32 (1..65535)
			MAX-ACCESS read-only
			STATUS current
			DESCRIPTION
				"Description"
			::= { sheSystemAclEntry 9 }

		
		-- 1.3.6.1.4.1.6296.101.7.5.1.1.10
		sheSystemAclDstL4Port OBJECT-TYPE
			SYNTAX Integer32 (1..65535)
			MAX-ACCESS read-only
			STATUS current
			DESCRIPTION
				"Description"
			::= { sheSystemAclEntry 10 }

		
		-- 1.3.6.1.4.1.6296.101.7.5.1.1.11
		sheSystemAclPktLen OBJECT-TYPE
			SYNTAX Integer32 (21..65535)
			MAX-ACCESS read-only
			STATUS current
			DESCRIPTION
				"Description"
			::= { sheSystemAclEntry 11 }

		
		-- 1.3.6.1.4.1.6296.101.7.5.1.1.12
		sheSystemAclValidFlags OBJECT-TYPE
			SYNTAX BITS
				{
				aclSrcIpAddress(0),
				aclSrcPrefixLegth(1),
				aclDstIpAddress(2),
				aclDstPrefixLegth(3),
				aclDscp(4),
				aclProtocolType(5),
				aclTcpFlags(6),
				aclSrcL4Port(7),
				aclDstL4Port(8),
				aclPacketLength(9)
				}
			MAX-ACCESS read-only
			STATUS current
			DESCRIPTION
				"Description"
			::= { sheSystemAclEntry 12 }

		
		-- 1.3.6.1.4.1.6296.101.7.5.1.1.13
		sheSystemAclMatchFlags OBJECT-TYPE
			SYNTAX BITS
				{
				aclSrcIpAddress(0),
				aclSrcPrefixLegth(1),
				aclDstIpAddress(2),
				aclDstPrefixLength(3),
				aclDscp(4),
				aclProtocolType(5),
				aclTcpFlag(6),
				aclSrcL4Port(7),
				aclDstL4Port(8),
				aclPacketLength(9)
				}
			MAX-ACCESS read-only
			STATUS current
			DESCRIPTION
				"Description"
			::= { sheSystemAclEntry 13 }

		
		-- 1.3.6.1.4.1.6296.101.7.5.1.1.14
		sheSystemAclMatchAction OBJECT-TYPE
			SYNTAX INTEGER
				{
				permit(1),
				deny(2)
				}
			MAX-ACCESS read-only
			STATUS current
			DESCRIPTION
				"Description"
			::= { sheSystemAclEntry 14 }

		
		-- 1.3.6.1.4.1.6296.101.7.5.1.1.15
		sheSystemAclNomatchAction OBJECT-TYPE
			SYNTAX INTEGER
				{
				permit(1),
				deny(2)
				}
			MAX-ACCESS read-only
			STATUS current
			DESCRIPTION
				"DescriptionDescription"
			::= { sheSystemAclEntry 15 }

		
		-- 1.3.6.1.4.1.6296.101.7.5.1.1.16
		sheSystemAclPriority OBJECT-TYPE
			SYNTAX INTEGER
				{
				low(1),
				medium(2),
				high(3),
				highest(4)
				}
			MAX-ACCESS read-only
			STATUS current
			DESCRIPTION
				"Description"
			::= { sheSystemAclEntry 16 }

		
		-- 1.3.6.1.4.1.6296.101.7.5.2
		sheSystemAclControl OBJECT IDENTIFIER ::= { sheSystemAcl 2 }
        
		
		-- 1.3.6.1.4.1.6296.101.7.5.2.1
		sheSystemAclControlReqest OBJECT-TYPE
			SYNTAX INTEGER
				{
				createAclRule(1),
				destroyAclRule(2),
				setAclClassifierProfile(3),
				setAclMatchAction(10),
				setAclNomatchAction(11),
				insertAclRule(12)
				}
			MAX-ACCESS read-write
			STATUS current
			DESCRIPTION
				"DescriptionDescription"
			::= { sheSystemAclControl 1 }

		
		-- 1.3.6.1.4.1.6296.101.7.5.2.2
		sheSystemAclControlStatus OBJECT-TYPE
			SYNTAX SheControlStatusType
			MAX-ACCESS read-only
			STATUS current
			DESCRIPTION
				"Description"
			::= { sheSystemAclControl 2 }

		
		-- 1.3.6.1.4.1.6296.101.7.5.2.3
		sheSystemAclControlTimer OBJECT-TYPE
			SYNTAX Gauge32
			MAX-ACCESS read-write
			STATUS current
			DESCRIPTION
				"Description"
			::= { sheSystemAclControl 3 }

		
		-- 1.3.6.1.4.1.6296.101.7.5.2.4
		sheSystemAclControlTimeStamp OBJECT-TYPE
			SYNTAX TimeTicks
			MAX-ACCESS read-only
			STATUS current
			DESCRIPTION
				"Description"
			::= { sheSystemAclControl 4 }

		
		-- 1.3.6.1.4.1.6296.101.7.5.2.5
		sheSystemAclControlReqResult OBJECT-TYPE
			SYNTAX SheSystemControlRequestResultType
			MAX-ACCESS read-only
			STATUS current
			DESCRIPTION
				"Description"
			::= { sheSystemAclControl 5 }

		
		-- 1.3.6.1.4.1.6296.101.7.5.2.6
		sheSystemAclControlName OBJECT-TYPE
			SYNTAX OCTET STRING (SIZE (0..63))
			MAX-ACCESS read-write
			STATUS current
			DESCRIPTION
				"Description"
			::= { sheSystemAclControl 6 }

		
		-- 1.3.6.1.4.1.6296.101.7.5.2.7
		sheSystemAclControlSrcIpAddr OBJECT-TYPE
			SYNTAX IpAddress
			MAX-ACCESS read-write
			STATUS current
			DESCRIPTION
				"Description"
			::= { sheSystemAclControl 7 }

		
		-- 1.3.6.1.4.1.6296.101.7.5.2.8
		sheSystemAclControlSrcPrefixLength OBJECT-TYPE
			SYNTAX Integer32 (0..31)
			MAX-ACCESS read-write
			STATUS current
			DESCRIPTION
				"Description"
			::= { sheSystemAclControl 8 }

		
		-- 1.3.6.1.4.1.6296.101.7.5.2.9
		sheSystemAclControlDstIpAddr OBJECT-TYPE
			SYNTAX IpAddress
			MAX-ACCESS read-write
			STATUS current
			DESCRIPTION
				"DescriptionDescription"
			::= { sheSystemAclControl 9 }

		
		-- 1.3.6.1.4.1.6296.101.7.5.2.10
		sheSystemAclControlDstPrefixLength OBJECT-TYPE
			SYNTAX Integer32 (0..31)
			MAX-ACCESS read-write
			STATUS current
			DESCRIPTION
				"Description"
			::= { sheSystemAclControl 10 }

		
		-- 1.3.6.1.4.1.6296.101.7.5.2.11
		sheSystemAclControlDscp OBJECT-TYPE
			SYNTAX Integer32
			MAX-ACCESS read-write
			STATUS current
			DESCRIPTION
				"Description"
			DEFVAL { -1 }
			::= { sheSystemAclControl 11 }

		
		-- 1.3.6.1.4.1.6296.101.7.5.2.12
		sheSystemAclControlProtocolType OBJECT-TYPE
			SYNTAX Integer32 (1..255)
			MAX-ACCESS read-write
			STATUS current
			DESCRIPTION
				"Description"
			::= { sheSystemAclControl 12 }

		
		-- 1.3.6.1.4.1.6296.101.7.5.2.13
		sheSystemAclControlTcpFlag OBJECT-TYPE
			SYNTAX BITS
				{
				reserv(0),
				reserv1(1),
				urg(2),
				ack(3),
				psh(4),
				rst(5),
				syn(6),
				fin(7)
				}
			MAX-ACCESS read-write
			STATUS current
			DESCRIPTION
				"Description"
			::= { sheSystemAclControl 13 }

		
		-- 1.3.6.1.4.1.6296.101.7.5.2.14
		sheSystemAclControlSrcL4Port OBJECT-TYPE
			SYNTAX Integer32 (0..65535)
			MAX-ACCESS read-write
			STATUS current
			DESCRIPTION
				"Description"
			::= { sheSystemAclControl 14 }

		
		-- 1.3.6.1.4.1.6296.101.7.5.2.15
		sheSystemAclControlDstL4Port OBJECT-TYPE
			SYNTAX Integer32 (0..65535)
			MAX-ACCESS read-write
			STATUS current
			DESCRIPTION
				"Description"
			::= { sheSystemAclControl 15 }

		
		-- 1.3.6.1.4.1.6296.101.7.5.2.16
		sheSystemAclControlPktLen OBJECT-TYPE
			SYNTAX Integer32 (21..65535)
			MAX-ACCESS read-write
			STATUS current
			DESCRIPTION
				"Description"
			::= { sheSystemAclControl 16 }

		
		-- 1.3.6.1.4.1.6296.101.7.5.2.17
		sheSystemAclControlValidFlags OBJECT-TYPE
			SYNTAX BITS
				{
				aclSrcIpAddress(0),
				aclSrcPrefixLength(1),
				aclDstIpAddress(2),
				aclDstPrefixLength(3),
				aclDscp(4),
				aclProtocolType(5),
				aclTcpFlag(6),
				aclSrcL4Port(7),
				aclDstL4Port(8),
				aclPacketLength(9)
				}
			MAX-ACCESS read-write
			STATUS current
			DESCRIPTION
				"Description"
			::= { sheSystemAclControl 17 }

		
		-- 1.3.6.1.4.1.6296.101.7.5.2.18
		sheSystemAclControlMatchFlags OBJECT-TYPE
			SYNTAX BITS
				{
				aclSrcIpAddress(0),
				aclSrcPrefixLength(1),
				aclDstIpAddress(2),
				aclDstPrefixLength(3),
				aclDscp(4),
				aclProtocolType(5),
				aclTcpFlag(6),
				aclSrcL4Port(7),
				aclDstL4Port(8),
				aclPacketLength(9)
				}
			MAX-ACCESS read-write
			STATUS current
			DESCRIPTION
				"Description"
			::= { sheSystemAclControl 18 }

		
		-- 1.3.6.1.4.1.6296.101.7.5.2.19
		sheSystemAclControlMatchAction OBJECT-TYPE
			SYNTAX INTEGER
				{
				none(0),
				permit(1),
				deny(2)
				}
			MAX-ACCESS read-write
			STATUS current
			DESCRIPTION
				"Description"
			::= { sheSystemAclControl 19 }

		
		-- 1.3.6.1.4.1.6296.101.7.5.2.20
		sheSystemAclControlNomatchAction OBJECT-TYPE
			SYNTAX INTEGER
				{
				none(0),
				permit(1),
				deny(2)
				}
			MAX-ACCESS read-write
			STATUS current
			DESCRIPTION
				"Description"
			::= { sheSystemAclControl 20 }

		
		-- 1.3.6.1.4.1.6296.101.7.5.2.21
		sheSystemAclControlPriority OBJECT-TYPE
			SYNTAX INTEGER
				{
				low(1),
				medium(2),
				high(3),
				highest(4)
				}
			MAX-ACCESS read-write
			STATUS current
			DESCRIPTION
				"Description"
			::= { sheSystemAclControl 21 }


		-- 1.3.6.1.4.1.6296.101.7.5.2.22
		sheSystemAclControlNextName OBJECT-TYPE
			SYNTAX OCTET STRING (SIZE (0..63))
			MAX-ACCESS read-write
			STATUS current
			DESCRIPTION
				"Description"
			::= { sheSystemAclControl 22 }

		
		-- 1.3.6.1.4.1.6296.101.7.5.3
		sheSystemAclNotification OBJECT IDENTIFIER ::= { sheSystemAcl 3 }

		
		-- 1.3.6.1.4.1.6296.101.7.5.3.1
		sheSystemAclCreated NOTIFICATION-TYPE
			OBJECTS { sheSystemAclControlReqest, sheSystemAclControlTimeStamp, sheSystemAclControlReqResult, sheSystemAclControlName,
				sheSystemAclSrcIpAddr, sheSystemAclSrcPrefixLength, sleAclDstIpAddr, sheSystemAclDstPrefixLength, sheSystemAclDscp, 
				sheSystemAclProtocolType, sheSystemAclTcpFlag, sheSystemAclSrcL4Port, sheSystemAclDstL4Port, sheSystemAclPktLen, 
				sheSystemAclValidFlags, sheSystemAclMatchFlags, sheSystemAclMatchAction, sheSystemAclNomatchAction, sheSystemAclPriority }
			STATUS current
			DESCRIPTION 
				"Description"
			::= { sheSystemAclNotification 1 }

		
		-- 1.3.6.1.4.1.6296.101.7.5.3.2
		sheSystemAclDestroyed NOTIFICATION-TYPE
			OBJECTS { sheSystemAclControlReqest, sheSystemAclControlTimeStamp, sheSystemAclControlReqResult, sheSystemAclControlName }
			STATUS current
			DESCRIPTION 
				"Description"
			::= { sheSystemAclNotification 2 }

		
		-- 1.3.6.1.4.1.6296.101.7.5.3.3
		sheSystemAclClassifierProfileChanged NOTIFICATION-TYPE
			OBJECTS { sheSystemAclControlReqest, sheSystemAclControlTimeStamp, sheSystemAclControlReqResult, sheSystemAclControlName, 
				sheSystemAclSrcIpAddr, sheSystemAclSrcPrefixLength, sheSystemAclDstIpAddr, sheSystemAclDstPrefixLength, sheSystemAclDscp, 
				sheSystemAclProtocolType, sheSystemAclTcpFlag, sheSystemAclSrcL4Port, sheSystemAclDstL4Port, sheSystemAclPktLen, sheSystemAclValidFlags, 
				sheSystemAclMatchFlags	 }
			STATUS current
			DESCRIPTION 
				"Description"
			::= { sheSystemAclNotification 3 }

		
		-- 1.3.6.1.4.1.6296.101.7.5.3.4
		sheSystemAclMatchActionChanged NOTIFICATION-TYPE
			OBJECTS { sheSystemAclControlReqest, sheSystemAclControlTimeStamp, sheSystemAclControlReqResult, sheSystemAclControlName, sheSystemAclMatchAction }
			STATUS current
			DESCRIPTION 
				"Description"
			::= { sheSystemAclNotification 4 }

		
		-- 1.3.6.1.4.1.6296.101.7.5.3.5
		sheSystemAclNomatchActionChanged NOTIFICATION-TYPE
			OBJECTS { sheSystemAclControlReqest, sheSystemAclControlTimeStamp, sheSystemAclControlReqResult, sheSystemAclControlName, sheSystemAclNomatchAction }
			STATUS current
			DESCRIPTION 
				"Description"
			::= { sheSystemAclNotification 5 }

 		-- 1.3.6.1.4.1.6296.101.7.5.3.6
		sheSystemAclInserted NOTIFICATION-TYPE
					OBJECTS { sheSystemAclControlReqest, sheSystemAclControlTimeStamp, sheSystemAclControlReqResult, sheSystemAclControlName,
				sheSystemAclSrcIpAddr, sheSystemAclSrcPrefixLength, sleAclDstIpAddr, sheSystemAclDstPrefixLength, sheSystemAclDscp, 
				sheSystemAclProtocolType, sheSystemAclTcpFlag, sheSystemAclSrcL4Port, sheSystemAclDstL4Port, sheSystemAclPktLen, 
				sheSystemAclValidFlags, sheSystemAclMatchFlags, sheSystemAclMatchAction, sheSystemAclNomatchAction, sheSystemAclPriority }
			STATUS current
			DESCRIPTION 
				"Description"
			::= { sheSystemAclNotification 1 }

      
--		RADIUS Mgmt        
        sheSystemRadius	  OBJECT IDENTIFIER ::= { sheSystemSecurity 2 }    
            
            
		sheSystemRadiusRetransmissions OBJECT-TYPE
			SYNTAX Integer32
			MAX-ACCESS read-only
			STATUS current
			DESCRIPTION
				"Description"
			::= { sheSystemRadius 1 }
            
		sheSystemRadiusTimeouts OBJECT-TYPE
			SYNTAX Integer32
			MAX-ACCESS read-only
			STATUS current
			DESCRIPTION
				"Description"
			::= { sheSystemRadius 2 }
            
		sheSystemRadiusInterfaceName OBJECT-TYPE
			SYNTAX OCTET STRING (SIZE (0..255))
			MAX-ACCESS read-only
			STATUS current
			DESCRIPTION
				"Description"
			::= { sheSystemRadius 3 }            
            

		sheSystemRadiusInterfaceAddress OBJECT-TYPE
			SYNTAX IpAddress
			MAX-ACCESS read-only
			STATUS current
			DESCRIPTION
				"Description"
			::= { sheSystemRadius 4 }      
			
		sheSystemRadiusLoginAccountMode OBJECT-TYPE     
			SYNTAX  INTEGER
					{
					 none(0),
					 start(1),
					 stop(2),
					 both(3)
					}
			MAX-ACCESS read-only
			STATUS current
			DESCRIPTION
				" "
			::= { sheSystemRadius 5 }

		sheSystemRadiusServerTable OBJECT-TYPE
			SYNTAX SEQUENCE OF SheSystemRadiusServerEntry
			MAX-ACCESS not-accessible
			STATUS current
			DESCRIPTION
				"Description."
			::= { sheSystemRadius 11 }

		
		sheSystemRadiusServerEntry OBJECT-TYPE
			SYNTAX SheSystemRadiusServerEntry
			MAX-ACCESS not-accessible
			STATUS current
			DESCRIPTION
				"Description."
			INDEX { sheSystemRadiusServerAddress }
			::= { sheSystemRadiusServerTable 1 }

		
		SheSystemRadiusServerEntry ::=
			SEQUENCE { 
				sheSystemRadiusServerAddress
					IpAddress,
				sheSystemRadiusServerClientKey
					OCTET STRING,
				sheSystemRadiusServerAuthPort
					INTEGER,
				sheSystemRadiusServerAccPort
					INTEGER,
				sheSystemRadiusServerMode
					BITS
			 }

		sheSystemRadiusServerAddress OBJECT-TYPE
			SYNTAX IpAddress
			MAX-ACCESS read-only
			STATUS current
			DESCRIPTION
				"The IP address of the RADIUS server referred 
				to in this table entry."
			::= { sheSystemRadiusServerEntry 1 }

		
		sheSystemRadiusServerClientKey OBJECT-TYPE
			SYNTAX OCTET STRING (SIZE (0..255))
			MAX-ACCESS read-only
			STATUS current
			DESCRIPTION
				"The key to be used in communication between the 
				device and the Radius server."
			::= { sheSystemRadiusServerEntry 2 }

		
		sheSystemRadiusServerAuthPort OBJECT-TYPE
			SYNTAX INTEGER (0..65535)
			MAX-ACCESS read-only
			STATUS current
			DESCRIPTION
				"The UDP port the client is using to send requests to this server for authentication."
			::= { sheSystemRadiusServerEntry 3 }

		sheSystemRadiusServerAccPort OBJECT-TYPE
			SYNTAX INTEGER (0..65535)
			MAX-ACCESS read-only
			STATUS current
			DESCRIPTION
				"The UDP port the client is using to send requests to this server for accounting."
			::= { sheSystemRadiusServerEntry 4 }

		
		sheSystemRadiusServerMode OBJECT-TYPE
			SYNTAX BITS
				{
				aaa(0),
				dot1x(1)
				}
			MAX-ACCESS read-only
			STATUS current
			DESCRIPTION
				"Radius Server operation mode: if set bit 0, is used 
				in login, and if set bit 1, is used in 802.1X (dot1x)."
			::= { sheSystemRadiusServerEntry 5 }

		
		sheSystemRadiusControl OBJECT IDENTIFIER ::= { sheSystemRadius 12 }

		
		sheSystemRadiusControlRequest OBJECT-TYPE
			SYNTAX INTEGER
				{                     
				createRadiusServer(1),
				destroyRadiusServer(2),
				setRadiusServerProfile(3)
				setRadiusRetransmission(4),
				setRadiusTimeout(5),
				setRadiusInterface(6),
				setRadiusLoginAccountMode(7)
				}
			MAX-ACCESS read-write
			STATUS current
			DESCRIPTION
				"The MIB object for the user command."
			::= { sheSystemRadiusControl 1 }

		
		sheSystemRadiusControlStatus OBJECT-TYPE
			SYNTAX SheControlStatusType
			MAX-ACCESS read-only
			STATUS current
			DESCRIPTION
				"Describes the status of a user command group, 
				used for block commands while a command execution in process."
			::= { sheSystemRadiusControl 2 }

		
		sheSystemRadiusControlTimer OBJECT-TYPE
			SYNTAX Gauge32
			MAX-ACCESS read-write
			STATUS current
			DESCRIPTION
				"Maximum command duration time in case of long running"
			::= { sheSystemRadiusControl 3 }

		
		-- 1.3.6.1.4.1.6296.101.7.3.2.4
		sheSystemRadiusControlTimeStamp OBJECT-TYPE
			SYNTAX TimeTicks
			MAX-ACCESS read-only
			STATUS current
			DESCRIPTION
				"Time stamp attribute set at end of command."
			::= { sheSystemRadiusControl 4 }

		
		sheSystemRadiusControlReqResult OBJECT-TYPE
			SYNTAX SheSystemControlRequestResultType
			MAX-ACCESS read-only
			STATUS current
			DESCRIPTION
				"Command result attribute."
			::= { sheSystemRadiusControl 5 }

		
		sheSystemRadiusControlServerAddress OBJECT-TYPE
			SYNTAX IpAddress
			MAX-ACCESS read-write
			STATUS current
			DESCRIPTION
				"The IP address of the RADIUS server referred to 
				in this table entry."
			::= { sheSystemRadiusControl 6 }

		
		sheSystemRadiusControlServerClientKey OBJECT-TYPE
			SYNTAX OCTET STRING (SIZE (0..255))
			MAX-ACCESS read-write
			STATUS current
			DESCRIPTION
				"The key to be used in communication between 
				the device and the Radius server."
			::= { sheSystemRadiusControl 7 }

		
		sheSystemRadiusControlServerAuthPort OBJECT-TYPE
			SYNTAX Integer32 (0..65535)
			MAX-ACCESS read-write
			STATUS current
			DESCRIPTION
				"The service port  number for communication with server."
			::= { sheSystemRadiusControl 8 }

		
		sheSystemRadiusControlServerAccPort OBJECT-TYPE
			SYNTAX Integer32 (0..65535)
			MAX-ACCESS read-write
			STATUS current
			DESCRIPTION
				"The service port  number for communication with server."
			::= { sheSystemRadiusServerControl 9 }

		
		sheSystemRadiusControlServerMode OBJECT-TYPE
			SYNTAX BITS
				{
				aaa(0),
				dot1x(1)
				}
			MAX-ACCESS read-write
			STATUS current
			DESCRIPTION
				"Description."
			::= { sheSystemRadiusControl 10 }     
			
		sheSystemRadiusControlRetransmission OBJECT-TYPE
			SYNTAX Integer32
			MAX-ACCESS read-write
			STATUS current
			DESCRIPTION
				"."
			::= { sheSystemRadiusControl 11 }   
			
		sheSystemRadiusControlTimeout OBJECT-TYPE
			SYNTAX Integer32
			MAX-ACCESS read-write
			STATUS current
			DESCRIPTION
				"."
			::= { sheSystemRadiusControl 12 }   
			
		sheSystemRadiusControlInterfaceName OBJECT-TYPE
			SYNTAX OCTET STRING
			MAX-ACCESS read-write
			STATUS current
			DESCRIPTION
				"."
			::= { sheSystemRadiusControl 13 } 
						
		sheSystemRadiusControlInterfaceAddress OBJECT-TYPE
			SYNTAX IpAddress
			MAX-ACCESS read-write
			STATUS current
			DESCRIPTION
				"."
			::= { sheSystemRadiusControl 14 }   
			
		
		sheSystemRadiusControlLoginAccountMode OBJECT-TYPE     
			SYNTAX  INTEGER
					{
					 none(0),
					 start(1),
					 stop(2),
					 both(3)
					}
			MAX-ACCESS read-write
			STATUS current
			DESCRIPTION
				" "
			::= { sheSystemRadiusControl 15 }
 
			

		
		sheSystemRadiusNotification OBJECT IDENTIFIER ::= { sheSystemRadius 13 }
		
		sheSystemRadiusServerCreated NOTIFICATION-TYPE
			OBJECTS { sheSystemRadiusServerControlRequest, sheSystemRadiusServerControlTimeStamp, sheSystemRadiusServerControlReqResult, 
			sheSystemRadiusServerClientKey, sheSystemRadiusServerAccPort, sheSystemRadiusServerAuthPort, sheSystemRadiusServerMode }
			STATUS current
			DESCRIPTION 
				"Description"
			::= { sheSystemRadiusNotification 1 }
		

		sheSystemRadiusServerDestroyed NOTIFICATION-TYPE
			OBJECTS { sheSystemRadiusServerControlRequest, sheSystemRadiusServerControlTimeStamp, 
			sheSystemRadiusServerControlReqResult, sheSystemRadiusServerAddress }
			STATUS current
			DESCRIPTION 
				"Description"
			::= { sheSystemRadiusNotification 2 }

		
		sheSystemRadiusServerProfileChanged NOTIFICATION-TYPE
			OBJECTS { sheSystemRadiusServerControlRequest, sheSystemRadiusServerControlTimeStamp, sheSystemRadiusServerControlReqResult,
			 sheSystemRadiusServerClientKey, sheSystemRadiusServerAuthPort, sheSystemRadiusServerAccPort, sheSystemRadiusServerMode }
			STATUS current
			DESCRIPTION 
				"Description"
			::= { sheSystemRadiusNotification 3 }

 
		sheSystemRadiusRetransmissionChanged NOTIFICATION-TYPE
			OBJECTS { sheSystemRadiusServerControlRequest, sheSystemRadiusServerControlTimeStamp, sheSystemRadiusServerControlReqResult,
			  sheSystemRadiusControlRetransmission }
			STATUS current
			DESCRIPTION 
				"Description"
			::= { sheSystemRadiusNotification 4 }

		sheSystemRadiusTimeoutChanged NOTIFICATION-TYPE
			OBJECTS { sheSystemRadiusServerControlRequest, sheSystemRadiusServerControlTimeStamp, sheSystemRadiusServerControlReqResult,
			  sheSystemRadiusControlTimeout }
			STATUS current
			DESCRIPTION 
				"Description"
			::= { sheSystemRadiusNotification 5 }

		sheSystemRadiusInterfaceChanged NOTIFICATION-TYPE
			OBJECTS { sheSystemRadiusServerControlRequest, sheSystemRadiusServerControlTimeStamp, sheSystemRadiusServerControlReqResult,
			  sheSystemRadiusControlInterfaceName, sheSystemRadiusControlInterfaceAddress }
			STATUS current
			DESCRIPTION 
				"Description"
			::= { sheSystemRadiusNotification 6 } 
			
		sheSystemRadiusLoginAccountModeChanged NOTIFICATION-TYPE
			OBJECTS { sheSystemRadiusServerControlRequest, sheSystemRadiusServerControlTimeStamp, sheSystemRadiusServerControlReqResult,  
			sheSystemRadiusControlLoginAccountMode }
			STATUS current
			DESCRIPTION 
				"."
			::= { sheSystemRadiusNotification 7 }			
		 
                               
                               
--
-- 		ping/traceroute/OAM etc...
--
        sheSystemFaultMgmt OBJECT IDENTIFIER ::= { sheSystem 16 }
        
        
        sheSystemPing OBJECT IDENTIFIER ::= { sheSystemFaultMgmt 1 }
 
 		sheSystemPingControl OBJECT IDENTIFIER ::= { sheSystemPing 1 }
 		
 		sheSystemPingControlRequest OBJECT-TYPE
			SYNTAX INTEGER
				{	createPingRequest(1)}
			MAX-ACCESS read-write
			STATUS current
			DESCRIPTION
				"The MIB object for the user command."
			::= { sheSystemPingControl 1 }

		
		sheSystemPingControlStatus OBJECT-TYPE
			SYNTAX SheControlStatusType
			MAX-ACCESS read-only
			STATUS current
			DESCRIPTION
				"Describes the status of a user command group, 
				used for block commands while a command execution in process."
			::= { sheSystemPingControl 2 }

		
		sheSystemPingControlTimer OBJECT-TYPE
			SYNTAX Gauge32
			MAX-ACCESS read-write
			STATUS current
			DESCRIPTION
				"Maximum command duration time in case of long running"
			::= { sheSystemPingControl 3 }

		
		sheSystemPingControlTimeStamp OBJECT-TYPE
			SYNTAX TimeTicks
			MAX-ACCESS read-only
			STATUS current
			DESCRIPTION
				"Time stamp attribute set at end of command."
			::= { sheSystemPingControl 4 }

		
		sheSystemPingControlReqResult OBJECT-TYPE
			SYNTAX SheSystemControlRequestResultType
			MAX-ACCESS read-only
			STATUS current
			DESCRIPTION
				"Command result attribute."
			::= { sheSystemPingControl 5 }

		
		sheSystemPingControlTargetAddressType OBJECT-TYPE
			SYNTAX InetAddressType
			MAX-ACCESS read-write
			STATUS current
			DESCRIPTION
				"."
			::= { sheSystemPingControl 6 }
		
 		
		sheSystemPingControlTargetAddress OBJECT-TYPE
			SYNTAX InetAddress
			MAX-ACCESS read-write
			STATUS current
			DESCRIPTION
				"."
			::= { sheSystemPingControl 7 }
 		      

		sheSystemPingControlDataSize OBJECT-TYPE
			SYNTAX Unsigned32
			MAX-ACCESS read-write
			STATUS current
			DESCRIPTION
				"."
			::= { sheSystemPingControl 8 }


		sheSystemPingControlTimeOut OBJECT-TYPE
			SYNTAX Unsigned32
			MAX-ACCESS read-write
			STATUS current
			DESCRIPTION
				"."
			::= { sheSystemPingControl 9 }


		sheSystemPingControlProbeCount OBJECT-TYPE
			SYNTAX Unsigned32
			MAX-ACCESS read-write
			STATUS current
			DESCRIPTION
				"."
			::= { sheSystemPingControl 10 }


		sheSystemPingControlFrequency OBJECT-TYPE
			SYNTAX Unsigned32
			MAX-ACCESS read-write
			STATUS current
			DESCRIPTION
				"."
			::= { sheSystemPingControl 11 }

 		sheSystemPingControlSourceAddressType OBJECT-TYPE
			SYNTAX InetAddressType
			MAX-ACCESS read-write
			STATUS current
			DESCRIPTION
				"."
			::= { sheSystemPingControl 12 }


		sheSystemPingControlSourceAddress OBJECT-TYPE
			SYNTAX InetAddress
			MAX-ACCESS read-write
			STATUS current
			DESCRIPTION
				"."
			::= { sheSystemPingControl 13 }


		sheSystemPingResultTable OBJECT-TYPE
			SYNTAX SEQUENCE OF SheSystemPingResultEntry
			MAX-ACCESS not-accessible
			STATUS current
			DESCRIPTION
				"Description."
			::= { sheSystemPing 2 }

		
		sheSystemPingResultEntry OBJECT-TYPE
			SYNTAX SheSystemPingResultEntry
			MAX-ACCESS not-accessible
			STATUS current
			DESCRIPTION
				"Description."
			INDEX { sheSystemPingResultIndex }
			::= { sheSystemPingResultTable 1 }

		
		SheSystemPingResultEntry ::=
			SEQUENCE { 
				sheSystemPingResultIndex
					INTEGER,
				sheSystemPingResultTargetAddressType 
					InetAddressType,
				sheSystemPingResultTargetAddress
					InetAddress,
				sheSystemPingResultMinRtt
					INTEGER,
				sheSystemPingResultMaxRtt
					INTEGER,       
				sheSystemPingResultAvgRtt
					INTEGER,					
				sheSystemPingResultProbeRespond
					INTEGER,
				sheSystemPingResultLastGoodProbe
					DateAndTime
			}

		sheSystemPingResultIndex OBJECT-TYPE
			SYNTAX INTEGER
			MAX-ACCESS read-only
			STATUS current
			DESCRIPTION
				"T."
			::= { sheSystemPingResultEntry 1 }

		sheSystemPingResultTargetAddressType OBJECT-TYPE
			SYNTAX InetAddressType
			MAX-ACCESS read-only
			STATUS current
			DESCRIPTION
				"T."
			::= { sheSystemPingResultEntry 2 } 
					
		sheSystemPingResultTargetAddress OBJECT-TYPE
			SYNTAX InetAddress
			MAX-ACCESS read-only
			STATUS current
			DESCRIPTION
				"T."
			::= { sheSystemPingResultEntry 3 }
					
		sheSystemPingResultMinRtt OBJECT-TYPE
			SYNTAX INTEGER
			MAX-ACCESS read-only
			STATUS current
			DESCRIPTION
				"T."
			::= { sheSystemPingResultEntry 4 }

		sheSystemPingResultMaxRtt OBJECT-TYPE
			SYNTAX INTEGER
			MAX-ACCESS read-only
			STATUS current
			DESCRIPTION
				"T."
			::= { sheSystemPingResultEntry 5 }
				       
		sheSystemPingResultAvgRtt OBJECT-TYPE
			SYNTAX INTEGER
			MAX-ACCESS read-only
			STATUS current
			DESCRIPTION
				"T."
			::= { sheSystemPingResultEntry 6 }
									
		sheSystemPingResultProbeRespond OBJECT-TYPE
			SYNTAX INTEGER
			MAX-ACCESS read-only
			STATUS current
			DESCRIPTION
				"T."
			::= { sheSystemPingResultEntry 7 }

					
		sheSystemPingResultLastGoodProbe OBJECT-TYPE
			SYNTAX DateAndTime
			MAX-ACCESS read-only
			STATUS current
			DESCRIPTION
				"T."
			::= { sheSystemPingResultEntry 8 }
		
   
        sheSystemTraceroute  OBJECT IDENTIFIER ::= { sheSystemFaultMgmt 2 }
        
		sheSystemTracerouteControl OBJECT IDENTIFIER ::= { sheSystemTraceroute 1 }
 		
 		sheSystemTracerouteControlRequest OBJECT-TYPE
			SYNTAX INTEGER
				{	createTracerouteRequest(1)}
			MAX-ACCESS read-write
			STATUS current
			DESCRIPTION
				"The MIB object for the user command."
			::= { sheSystemTracerouteControl 1 }

		
		sheSystemTracerouteControlStatus OBJECT-TYPE
			SYNTAX SheControlStatusType
			MAX-ACCESS read-only
			STATUS current
			DESCRIPTION
				"Describes the status of a user command group, 
				used for block commands while a command execution in process."
			::= { sheSystemTracerouteControl 2 }

		
		sheSystemTracerouteControlTimer OBJECT-TYPE
			SYNTAX Gauge32
			MAX-ACCESS read-write
			STATUS current
			DESCRIPTION
				"Maximum command duration time in case of long running"
			::= { sheSystemTracerouteControl 3 }

		
		sheSystemTracerouteControlTimeStamp OBJECT-TYPE
			SYNTAX TimeTicks
			MAX-ACCESS read-only
			STATUS current
			DESCRIPTION
				"Time stamp attribute set at end of command."
			::= { sheSystemTracerouteControl 4 }

		
		sheSystemTracerouteControlReqResult OBJECT-TYPE
			SYNTAX SheSystemControlRequestResultType
			MAX-ACCESS read-only
			STATUS current
			DESCRIPTION
				"Command result attribute."
			::= { sheSystemTracerouteControl 5 }

		
		sheSystemTracerouteControlTargetAddressType OBJECT-TYPE
			SYNTAX InetAddressType
			MAX-ACCESS read-write
			STATUS current
			DESCRIPTION
				"."
			::= { sheSystemTracerouteControl 6 }
		
 		
		sheSystemTracerouteControlTargetAddress OBJECT-TYPE
			SYNTAX InetAddress
			MAX-ACCESS read-write
			STATUS current
			DESCRIPTION
				"."
			::= { sheSystemTracerouteControl 7 }
 		      

		sheSystemTracerouteControlDataSize OBJECT-TYPE
			SYNTAX Unsigned32
			MAX-ACCESS read-write
			STATUS current
			DESCRIPTION
				"."
			::= { sheSystemTracerouteControl 8 }


		sheSystemTracerouteControlTimeOut OBJECT-TYPE
			SYNTAX Unsigned32
			MAX-ACCESS read-write
			STATUS current
			DESCRIPTION
				"."
			::= { sheSystemTracerouteControl 9 }


		sheSystemTracerouteControlProbePerHop OBJECT-TYPE
			SYNTAX Unsigned32
			MAX-ACCESS read-write
			STATUS current
			DESCRIPTION
				"."
			::= { sheSystemTracerouteControl 10 }


		sheSystemTracerouteControlFrequency OBJECT-TYPE
			SYNTAX Unsigned32
			MAX-ACCESS read-write
			STATUS current
			DESCRIPTION
				"."
			::= { sheSystemTracerouteControl 11 }

 		sheSystemTracerouteControlSourceAddressType OBJECT-TYPE
			SYNTAX InetAddressType
			MAX-ACCESS read-write
			STATUS current
			DESCRIPTION
				"."
			::= { sheSystemTracerouteControl 12 }


		sheSystemTracerouteControlSourceAddress OBJECT-TYPE
			SYNTAX InetAddress
			MAX-ACCESS read-write
			STATUS current
			DESCRIPTION
				"."
			::= { sheSystemTracerouteControl 13 }


		sheSystemTraceroutResultTable OBJECT-TYPE
			SYNTAX SEQUENCE OF SheSystemTraceroutResultEntry
			MAX-ACCESS not-accessible
			STATUS current
			DESCRIPTION
				"Description."
			::= { sheSystemTraceroute 2 }

		
		sheSystemTraceroutResultEntry OBJECT-TYPE
			SYNTAX SheSystemTraceroutResultEntry
			MAX-ACCESS not-accessible
			STATUS current
			DESCRIPTION
				"Description."
			INDEX { sheSystemTraceroutResultIndex }
			::= { sheSystemTraceroutResultTable 1 }

		
		SheSystemTraceroutResultEntry ::=
			SEQUENCE { 
				sheSystemTraceroutResultIndex
					INTEGER,       
				sheSystemTracerouteResultCurHopCount
					INTEGER,      
				sheSystemTracerouteResultCurProbeCount
					INTEGER,
				sheSystemTraceroutResultTargetAddressType 
					InetAddressType,
				sheSystemTraceroutResultTargetAddress
					InetAddress,
				sheSystemTraceroutResultTestAttempts
					INTEGER,
				sheSystemTraceroutResultTestSuccesses
					INTEGER,       
				sheSystemTraceroutResultLastGoodPath
					OCTET STRING
				
			}

		sheSystemTraceroutResultIndex OBJECT-TYPE
			SYNTAX INTEGER
			MAX-ACCESS read-only
			STATUS current
			DESCRIPTION
				"T."
			::= { sheSystemTraceroutResultEntry 1 }  
			
		sheSystemTracerouteResultCurHopCount OBJECT-TYPE
			SYNTAX INTEGER
			MAX-ACCESS read-only
			STATUS current
			DESCRIPTION
				"T."
			::= { sheSystemTraceroutResultEntry 2 }			
        
        sheSystemTracerouteResultCurProbeCount OBJECT-TYPE
			SYNTAX INTEGER
			MAX-ACCESS read-only
			STATUS current
			DESCRIPTION
				"T."
			::= { sheSystemTraceroutResultEntry 3 }
        
        
		sheSystemTraceroutResultTargetAddressType OBJECT-TYPE
			SYNTAX InetAddressType
			MAX-ACCESS read-only
			STATUS current
			DESCRIPTION
				"T."
			::= { sheSystemTraceroutResultEntry 4 } 
					
		sheSystemTraceroutResultTargetAddress OBJECT-TYPE
			SYNTAX InetAddress
			MAX-ACCESS read-only
			STATUS current
			DESCRIPTION
				"T."
			::= { sheSystemTraceroutResultEntry 5 }
					
		sheSystemTraceroutResultTestAttempts OBJECT-TYPE
			SYNTAX INTEGER
			MAX-ACCESS read-only
			STATUS current
			DESCRIPTION
				"T."
			::= { sheSystemTraceroutResultEntry 4 }

		sheSystemTraceroutResultTestSuccesses OBJECT-TYPE
			SYNTAX INTEGER
			MAX-ACCESS read-only
			STATUS current
			DESCRIPTION
				"T."
			::= { sheSystemTraceroutResultEntry 5 }
				       
		sheSystemTraceroutResultLastGoodPath OBJECT-TYPE
			SYNTAX OCTET STRING
			MAX-ACCESS read-only
			STATUS current
			DESCRIPTION
				"T."
			::= { sheSystemTraceroutResultEntry 6 }
									



				           
		           
		sheSystemConformance OBJECT IDENTIFIER ::= { sheSystem 100 }

		
		sheSystemGroups OBJECT IDENTIFIER ::= { sheSystemConformance 1 }

		
		sheSystemGroup OBJECT-GROUP
			OBJECTS { sheSystemFeatureIndex, sheSystemFeatureName, sheSystemFileSwfIndex, sheSystemFileSwfFileName, sheSystemFileSwfTypeOfFile, 
				sheSystemFileSwfVersion, sheSystemFileSwfSize, sheSystemFileSwfTimeStamp, sheSystemDbBackupFileIndex, sheSystemDbBackupFileName, 
				sheSystemManagementSessionIndex, sheSystemManagementSessionType, sheSystemManagementSessionSnmpExpiredTime, sheSystemManagementSessionAddress, sheSystemDnsServerIndex, 
				sheSystemDnsServerAddr, sheSystemNtpClientServerIndex, sheSystemNtpClientServerName, sheSystemDbBackupFileTimeStamp, sheSystemSwmTIndex, 
				sheSystemSwmTCardType, sheSystemSwmTEntPhysicalIndex, sheSystemSwmTTimeStamp, sheSystemSwmTUpgradeState, sheSystemSwmTUpgradeResult, 
				sheSystemSwmTSwVersion, sheSystemSwmTSwVersionNeed }
			STATUS current
			DESCRIPTION 
				" "
			::= { sheSystemGroups 1 }

		
		sheSystemControlGroup OBJECT-GROUP
			OBJECTS { sheSystemVersion, sheSystemExternalTime, sheSystemStartupType, sheSystemTmnConnected, sheSystemLctConnected, 
				sheSystemControlRequest, sheSystemControlStatus, sheSystemControlTimer, sheSystemControlReqResult, sheSystemControlTimeStamp, 
				sheSystemControlExternalTime, sheSystemCliConnected, sheSystemFileControlRequest, sheSystemFileControlStatus, sheSystemFileControlTimer, 
				sheSystemFileControlReqResult, sheSystemFileControlTimeStamp, sheSystemFileControlTypeOfFile, sheSystemFileControlPathName, sheSystemFileControlFileName, 
				sheSystemFileControlCardType, sheSystemFileControlEntPhysicalIndex, sheSystemFileControlLoadStatus, sheSystemFileControlServerAddr, sheSystemFileControlUsrName, 
				sheSystemFileControlPassword, sheSystemNotificationCounter, sheSystemSwmSapsServerAddr, sheSystemSwmSapsPathName, sheSystemSwmSapsFileName, 
				sheSystemSwmAdminState, sheSystemSwmControlSapsServerAddr, sheSystemSwmControlSapsPathName, sheSystemSwmControlSapsFileName, sheSystemSwmControlSapsUsrName, 
				sheSystemSwmControlSapsPassword, sheSystemSwmControlAdminState, sheSystemDbmServerAddr, sheSystemDbmPathName, sheSystemDbmRemoteBackupAdminState, 
				sheSystemDbmBackupPeriod, sheSystemDbmBackupStartTime, sheSystemDbmBackupWaitingPeriod, sheSystemDbmBackupMaxFileNumber, sheSystemDbmLocalBackupAdminState, 
				sheSystemDbmControlRequest, sheSystemDbmControlStatus, sheSystemDbmControlTimer, sheSystemDbmControlReqResultLocal, sheSystemDbmControlReqResultRemote, 
				sheSystemDbmControlTimeStamp, sheSystemDbmControlServerAddr, sheSystemDbmControlPathName, sheSystemDbmControlUsrName, sheSystemDbmControlPassword, 
				sheSystemDbmControlRemoteBackupAdminState, sheSystemDbmControlBackupPeriod, sheSystemDbmControlBackupStartTime, sheSystemDbmControlBackupWaitingPeriod, sheSystemDbmControlBackupMaxFileNumber, 
				sheSystemDbmControlLocalBackupAdminState, sheSystemNtpClientEnabled, sheSystemNtpClientXmitInterval, sheSystemManagementSessionControlRequest, sheSystemManagementSessionControlStatus, 
				sheSystemManagementSessionControlTimer, sheSystemManagementSessionControlReqResult, sheSystemManagementSessionControlTimeStamp, sheSystemManagementSessionControlSnmpAgingTime, sheSystemConfigLogEntryNumber, 
				sheSystemConfigLogFtpUser, sheSystemConfigLogFtpPassword, sheSystemConfigLogFtpInterval, sheSystemConfigLogFtpPathName, sheSystemConfigLogControlRequest, 
				sheSystemConfigLogControlEntryNumber, sheSystemConfigLogControlFtpAddress, sheSystemConfigLogControlFtpUser, sheSystemConfigLogControlFtpPassword, sheSystemConfigLogControlFtpInterval, 
				sheSystemConfigLogControlFtpPathName, sheSystemDnsServerControlRequest, sheSystemDnsServerControlStatus, sheSystemDnsServerControlTimer, sheSystemDnsServerControlReqResult, 
				sheSystemDnsServerControlTimeStamp, sheSystemDnsServerControlAddr, sheSystemDnsServerControlIndex, sheSystemManagementSessionSnmpAgingTime, sheSystemNtpClientControlRequest, 
				sheSystemNtpClientControlStatus, sheSystemNtpClientControlTimer, sheSystemNtpClientControlReqResult, sheSystemNtpClientControlTimeStamp, sheSystemNtpClientControlXmitInterval, 
				sheSystemSwmControlRequest, sheSystemSwmControlStatus, sheSystemSwmControlTimer, sheSystemSwmControlReqResult, sheSystemSwmControlTimeStamp, 
				sheSystemNtpClientControlServerIndex, sheSystemControlTimeZone, sheSystemControlCPUThreshold, sheSystemControlCPUThresholdInterval, sheSystemControlMemoryThreshold, 
				sheSystemControlMemoryThresholdInterval, sheSystemTimeZone, sheSystem5SecCPULoad, sheSystem1MinCPULoad, sheSystem10MinCPULoad, 
				sheSystemCPULoadThreshold, sheSystemCPULoadThresholdInterval, sheSystemTotalMemory, sheSystemUsedMemory, sheSystemFreeMemory, 
				sheSystemMemoryThreshold, sheSystemMemoryThresholdInterval, sheSystemBootloaderVersion, sheSystemStartupResult, sheSystemDbmControlBackupFileIndex, 
				sheSystemConfigLogControlReqResult, sheSystemConfigLogControlStatus, sheSystemConfigLogControlTimeStamp, sheSystemConfigLogFtpServerAddress, sheSystemNtpClientControlServername
				 }
			STATUS current
			DESCRIPTION 
				" "
			::= { sheSystemGroups 2 }

		
		sheSystemNotificationGroup NOTIFICATION-GROUP
			NOTIFICATIONS { sheSystemStartupEnd, sheSystemFtp, sheSystemSwLoadPromoted, sheSystemSwLoadPromotionFailed, sheSystemLctSession, 
				sheSystemWriteDatatoFlashFinished, sheSystemCliSession, sheSystemSwmBaseSet, sheSystemReadSAPSContentFileReady, sheSystemDbmBaseSet, 
				sheSystemDbmBackupFilesTableRefreshed, sheSystemDbmBackupPeriodSet, sheSystemDbmLocalBackupAdminstateSet, sheSystemLocalDbInvalid, sheSystemRemoteDbInvalid, 
				sheSystemDbFtpAccessError, sheSystemSwmFtpExternalAccessError, sheSystemChangedCPULoadThreshold, sheSystemChangedMemoryThreshold, sheSystemCPULoadThresholdExceeded, 
				sheSystemMemoryThresholdExceeded, sheSystemNtpClientEnable, sheSystemNtpClientDisable, sheSystemNtpClientChangeXmitInterval, sheSystemNtpClientAddServerName, 
				sheSystemNtpClientDeleteServerName, sheSystemDnsServerAddAddr, sheSystemDnsServerDeleteAddr, sheSystemManagementSessionConnection, sheSystemManagementSessionDisconnection, 
				sheSystemManagementSessionChangedSnmpAgingTime, sheSystemConfigLogEntryNumberChanged, sheSystemConfigLogFtpLoginInfoChanged, sheSystemConfigLogFtpIntervalChanged, sheSystemDbmRemoteBackupAdminstateSet, 
				sheSystemSwmAdminStateSet, sheSystemSwmReadyForReset, sheSystemSwmFTPError, sheSystemSwmUpgradeStartResult, sheSystemSwmFtpAccessError, 
				sheSystemDbmResult }
			STATUS current
			DESCRIPTION 
				" "
			::= { sheSystemGroups 3 }

		
		sheSystemIpGroup OBJECT-GROUP
			OBJECTS { sheSystemIpHostIndex, sheSystemIpHostName, sheSystemIpHostUseDhcp, sheSystemIpHostIpAddress, sheSystemIpHostSubnetMask, 
				sheSystemIpHostOuterVlanId, sheSystemIpHostInnerVlanId, sheSystemIpHostControlRequest, sheSystemIpHostControlIndex, sheSystemIpHostControlStatus, 
				sheSystemIpHostControlReqResult, sheSystemIpHostControlTimer, sheSystemIpHostControlTimeStamp, sheSystemIpHostControlName, sheSystemIpHostControlUseDhcp, 
				sheSystemIpHostControlIpAddress, sheSystemIpHostControlSubnetMask, sheSystemIpHostControlOuterVlanId, sheSystemIpHostControlInnerVlanId, sheSystemIpRouteIndex, 
				sheSystemIpRouteName, sheSystemIpRouteDestIpAddress, sheSystemIpRouteSubnetMask, sheSystemIpRouteGatewayIpAddress, sheSystemIpRouteControlRequest, 
				sheSystemIpRouteControlIndex, sheSystemIpRouteControlStatus, sheSystemIpRouteControlReqResult, sheSystemIpRouteControlTimer, sheSystemIpRouteControlTimeStamp, 
				sheSystemIpRouteControlName, sheSystemIpRouteControlDestIpAddress, sheSystemIpRouteControlSubnetMask, sheSystemIpRouteMetric, sheSystemIpRouteControlMetric, 
				sheSystemIpRouteControlGatewayIpAddress, sheSystemIpHostDescription, sheSystemIpHostControlDescription }
			STATUS current
			DESCRIPTION 
				"Description."
			::= { sheSystemGroups 4 }

		
		sheSystemIpNotificationGroup NOTIFICATION-GROUP
			NOTIFICATIONS { sheSystemIpHostCreated, sheSystemIpHostDeleted, sheSystemIpHostModified, sheSystemIpRouteCreated, sheSystemIpRouteDeleted, 
				sheSystemIpRouteModified }
			STATUS current
			DESCRIPTION 
				"Description."
			::= { sheSystemGroups 5 }

		
		sheSystemObsoleteGroup OBJECT-GROUP
			OBJECTS { sheSystemAutoConfigBackupEnabled, sheSystemAutoConfigBackupFtpServerAddress, sheSystemAutoConfigBackupFtpUser, sheSystemAutoConfigBackupFtpPassword, sheSystemAutoConfigBackupFtpPathName, 
				sheSystemAutoConfigBackupTime, sheSystemAutoConfigBackupControlRequest, sheSystemAutoConfigBackupControlEnabled, sheSystemAutoConfigBackupControlFtpServerAddress, sheSystemAutoConfigBackupControlFtpUser, 
				sheSystemAutoConfigBackupControlFtpPassword, sheSystemAutoConfigBackupControlFtpPathName, sheSystemAutoConfigBackupControlBackupTime }
			STATUS current
			DESCRIPTION 
				"Description."
			::= { sheSystemGroups 6 }

		
		sheSystemObsoleteNotificationGroup NOTIFICATION-GROUP
			NOTIFICATIONS { sheSystemAutoConfigBackupEnabledChanged, sheSystemAutoConfigBackupFtpLoginInfoChanged, sheSystemAutoConfigBackupTimeChanged }
			STATUS current
			DESCRIPTION 
				"Description."
			::= { sheSystemGroups 7 }

		
		sheSystemCompliances OBJECT IDENTIFIER ::= { sheSystemConformance 2 }

		
		sheSystemCompliance MODULE-COMPLIANCE
			STATUS current
			DESCRIPTION 
				"The compliance statement for SNMP entities which 
				manage VDSL interfaces in SHE."
			MODULE -- this module
				MANDATORY-GROUPS { sheSystemGroup, sheSystemControlGroup, sheSystemNotificationGroup, sheSystemIpGroup, sheSystemIpNotificationGroup
					 }
				GROUP sheSystemObsoleteGroup
					DESCRIPTION 
						"Not used by SHR R2.5.x..."
				GROUP sheSystemObsoleteNotificationGroup
					DESCRIPTION 
						"Not used by SHR R2.5.x..."
			::= { sheSystemCompliances 1 }

		
	
	END

--
-- she-system-mib.mib
--
