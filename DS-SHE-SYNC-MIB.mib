--
-- she-sync-mib.mib
-- MIB generated by MG-SOFT Visual MIB Builder Version 6.0  Build 88
-- Monday, March 10, 2008 at 15:56:01
--

	DS-SHE-SYNC-MIB DEFINITIONS ::= BEGIN
 
		IMPORTS
			she			
				FROM AN-MIB
			dsShe
				FROM DASAN-SMI							
			PhysicalIndex			
				FROM ENTITY-MIB			
			sheAlarmTimeAndDate, sheAlarmReportingSource, sheAlarmReportingSourceType, sheAlarmSeverity, SheAlarmSevProfileIndex			
				FROM DS-SHE-ALARMING-MIB			
			SheControlStatusType			
				FROM DS-SHE-TC-MIB			
			OBJECT-GROUP, MODULE-COMPLIANCE, NOTIFICATION-GROUP			
				FROM SNMPv2-CONF			
			Unsigned32, OBJECT-TYPE, MODULE-IDENTITY, NOTIFICATION-TYPE			
				FROM SNMPv2-SMI			
			TEXTUAL-CONVENTION			
				FROM SNMPv2-TC;
	
	
		sheSync MODULE-IDENTITY 
			LAST-UPDATED "200803101100Z"		-- March 10, 2008 at 11:00 GMT
			ORGANIZATION 
				"Nokia Siemens Networks"
			CONTACT-INFO 
				"Gerd Barchmann
				COO BBA DSLAM RD HW1
				
				gerd.barchmann@nsn.com
				+49 3834 555654"
			DESCRIPTION 
				"The MIB module for managing the clock sources (timing) of the network element."
			REVISION "200704051511Z"		-- April 05, 2007 at 15:11 GMT
			DESCRIPTION 
				"Initial version - merge from GPON project."
			REVISION "200710161100Z"		-- October 16, 2007 at 11:00 GMT
			DESCRIPTION 
				"New release SHE R2.6P support new types of possible sync sources."
			REVISION "200711271137Z"		-- November 27, 2007 at 11:37 GMT
			DESCRIPTION 
				"Expand support to a configurable sync source table according concept paper SHE R3.0."
			REVISION "200712121357Z"		-- December 12, 2007 at 13:57 GMT
			DESCRIPTION 
				"Correct SSM-Level definitions."
			REVISION "200712201309Z"		-- December 20, 2007 at 13:09 GMT
			DESCRIPTION 
				"Redesign synctables after review by systems."
			REVISION "200803101553Z"		-- March 10, 2008 at 15:53 GMT
			DESCRIPTION 
				"Supported startet now with SHE R2.8."
			::= { dsShe 15 }

		
	
--
-- Type definitions
--
	
		SheSyncPriorityType ::= INTEGER (0 | 1..2)

		SheSyncAvailabilityIndexType ::= INTEGER (0 | 1..10)

		SheSyncWaitTimeToRestoreType ::= INTEGER (0..2147483647)

		SheSyncSourceType ::= INTEGER
			{
			sheInternalSyncSource(1),
			sheT3inSyncSource(2),
			sheBitsSyncSource(3),
			sheEthernetSyncSource(4),
			sheE1SyncSource(5),
			sheTimingOverPacketSyncSource(6)
			}

		SheSyncSourceAlarmStateType ::= INTEGER
			{
			sheAlarmCleared(0),
			sheAlarmPresent(1)
			}

		SheSyncControlReqType ::= INTEGER
			{
			noRequest(1),
			sheModifySyncSource(101),
			sheModifySyncWaitTimeToRestore(102),
			sheModifySyncGlobals(103),
			sheModifyUsedSyncSource(104)
			}

	
--
-- Textual conventions
--
	
		SheSyncControlReqResultType ::= TEXTUAL-CONVENTION
			STATUS current
			DESCRIPTION 
				"The result type for synchronization control commands."
			SYNTAX INTEGER
				{
				noRequest(1),
				commExecStarted(5),
				paramFaulty(11),
				requestBusy(12),
				setDataFailed(13),
				aswTimeout(14),
				commandFailed(15),
				commandSucceeded(16),
				wrongAlarmSeverityIndex(23)
				}

		SheSyncModeType ::= TEXTUAL-CONVENTION
			STATUS current
			DESCRIPTION 
				"sheSyncMode values"
			SYNTAX INTEGER
				{
				revertive(1),
				nonrevertive(2)
				}

	
--
-- Node definitions
--
	
		sheSyncObjects OBJECT IDENTIFIER ::= { sheSync 1 }

		
		sheSyncGlobalObjects OBJECT IDENTIFIER ::= { sheSyncObjects 1 }

		
		sheSyncActiveClockSource OBJECT-TYPE
			SYNTAX SheSyncPriorityType
			MAX-ACCESS read-only
			STATUS current
			DESCRIPTION
				"The current chosen (active) clock source. Identifies an entry in the SyncSourceTable.
				0 means that no syncSource is available or configured and the NE uses the internal clock of the used CXU board.
				"
			::= { sheSyncGlobalObjects 1 }

		
		sheSyncWaitTimeToRestore OBJECT-TYPE
			SYNTAX SheSyncWaitTimeToRestoreType
			UNITS "100 ms"
			MAX-ACCESS read-only
			STATUS current
			DESCRIPTION
				"This time has to expire before switch back to a higher
				clock source after error condition.
				Unit is 100 ms."
			::= { sheSyncGlobalObjects 2 }

		
		sheSyncMode OBJECT-TYPE
			SYNTAX SheSyncModeType
			MAX-ACCESS read-only
			STATUS current
			DESCRIPTION
				"The used sync - mode.
				
				revertive - the highest priority sync source with valid reference is always selected.
				nonrevertive - the active sync source will always remain active while it is valid.
				Only if this sync source will be come invalid, a refence switchover to a valid reference
				with highest priority will be initiated."
			DEFVAL { revertive }
			::= { sheSyncGlobalObjects 3 }

		
		sheSyncLocalClockSSMLevel OBJECT-TYPE
			SYNTAX Unsigned32 (0..15)
			MAX-ACCESS read-only
			STATUS current
			DESCRIPTION
				"This parameter defines the configured SSM-Level for the local clock.
				This parameter should be transmitted, if all selected clock sources are failed and the
				NE uses his own internal clock reference (free run).
				The level is defined in 16 steps from 0..15, where 0 is the highest quality level. "
			DEFVAL { 15 }
			::= { sheSyncGlobalObjects 4 }

		
		sheSyncSourceTable OBJECT-TYPE
			SYNTAX SEQUENCE OF SheSyncSourceEntry
			MAX-ACCESS not-accessible
			STATUS current
			DESCRIPTION
				"The synchronization source table is used to manage synchronization sources
				and there priorities in the network element.
				"
			::= { sheSyncObjects 2 }

		
		sheSyncSourceEntry OBJECT-TYPE
			SYNTAX SheSyncSourceEntry
			MAX-ACCESS not-accessible
			STATUS current
			DESCRIPTION
				"An entry in the SyncSourceTable. It defines one possible synchronization source
				of the network element and its priority.
				Maximum two sources could be selected from SyncSourceAvailabilityTable."
			INDEX { sheSyncSourcePriority }
			::= { sheSyncSourceTable 1 }

		
		SheSyncSourceEntry ::=
			SEQUENCE { 
				sheSyncSourcePriority
					SheSyncPriorityType,
				sheSyncSourceType
					SheSyncSourceType,
				sheSyncSourceHwUnitIndex
					INTEGER,
				sheSyncSourceInterfaceNumber
					Unsigned32,
				sheSyncSourceAlarmState
					SheSyncSourceAlarmStateType,
				sheSyncSourceAlarmSeverityIndex
					SheAlarmSevProfileIndex,
				sheSyncSourceSelectedAvailabilityIndex
					SheSyncAvailabilityIndexType,
				sheSyncSourceSSMLevel
					Unsigned32,
				sheSyncSourceSSMLevelRec
					Unsigned32
			 }

		sheSyncSourcePriority OBJECT-TYPE
			SYNTAX SheSyncPriorityType
			MAX-ACCESS read-only
			STATUS current
			DESCRIPTION
				"A unique value to identify the priority of the synchronization source.
				Used as table index. 0 is not an useful index for that table."
			::= { sheSyncSourceEntry 1 }

		
		sheSyncSourceType OBJECT-TYPE
			SYNTAX SheSyncSourceType
			MAX-ACCESS read-only
			STATUS obsolete
			DESCRIPTION
				"The type of the synchronization source of the network element.
				
				NOTE:
				Not longer used with SHE R3.0."
			::= { sheSyncSourceEntry 2 }

		
		sheSyncSourceHwUnitIndex OBJECT-TYPE
			SYNTAX INTEGER (-1 | 1..2147483647)
			MAX-ACCESS read-only
			STATUS obsolete
			DESCRIPTION
				"Identifies the hardware unit that contains the synchronization source.
				If the hardware unit is not equipped, sheSyncSourceHwUnitIndex contains -1. 
				
				NOTE:
				Not longer used with SHE R3.0."
			::= { sheSyncSourceEntry 3 }

		
		sheSyncSourceInterfaceNumber OBJECT-TYPE
			SYNTAX Unsigned32 (1..72)
			MAX-ACCESS read-only
			STATUS obsolete
			DESCRIPTION
				"The number of the physical interface of the hardware unit.
				The interfaces are numbered vendor specific starting with 1
				in ascending order. Synchronization interfaces may not be
				contained in the interface table.
				
				NOTE:
				Not longer used with SHE R3.0."
			::= { sheSyncSourceEntry 4 }

		
		sheSyncSourceAlarmState OBJECT-TYPE
			SYNTAX SheSyncSourceAlarmStateType
			MAX-ACCESS read-only
			STATUS current
			DESCRIPTION
				"An alarm is generated when a clock source can't be used."
			::= { sheSyncSourceEntry 5 }

		
		sheSyncSourceAlarmSeverityIndex OBJECT-TYPE
			SYNTAX SheAlarmSevProfileIndex
			MAX-ACCESS read-only
			STATUS current
			DESCRIPTION
				"This index selects an item in the sheAlarmSeverityProfileTable[]. It is
				used to assign the reported alarm to a severity."
			DEFVAL { 1 }
			::= { sheSyncSourceEntry 6 }

		
		sheSyncSourceSelectedAvailabilityIndex OBJECT-TYPE
			SYNTAX SheSyncAvailabilityIndexType
			MAX-ACCESS read-only
			STATUS current
			DESCRIPTION
				"A unique value to identify a available synchronization source (from sheSyncAvailabilityTable)
				which is used as sync source for the NE.
				An index value 0 means no source is selected. 
				"
			::= { sheSyncSourceEntry 7 }

		
		sheSyncSourceSSMLevel OBJECT-TYPE
			SYNTAX Unsigned32 (0..15)
			MAX-ACCESS read-only
			STATUS current
			DESCRIPTION
				"This parameter defines the configured reference or assigned SSM-Level for this sync source.
				It should work as reference level only for source types, which supports SSM OAM messages for
				clock quality evaluation like ToP or syncEthernet.
				For other sourcetypes it is the assigned SSM-Level which should be used by the input selector
				for sourceclock quality comparation.
				The level is defined in 16 steps from 0..15, where 0 is the highest quality level. 
				
				The sync source will be invalid, if the received SSM level is above the configured
				reference level."
			::= { sheSyncSourceEntry 8 }

		
		sheSyncSourceSSMLevelRec OBJECT-TYPE
			SYNTAX Unsigned32 (0..15)
			MAX-ACCESS read-only
			STATUS current
			DESCRIPTION
				"This parameter shows the received SSM-Level for this sync source.
				It is only valid for source types, which supports SSM OAM messages for
				clock quality evaluation like syncEthernet or ToP. 
				In case of ToP sync sources, the NE will internaly convert the received stratum number (IEEE1588)
				to an SSM level value according G.781.
				
				The level is defined in 16 steps from 0..15, where 0 is the highest quality level. 
				The sync source will be invalid, if the received SSM level is above the configured
				reference level.
				
				"
			::= { sheSyncSourceEntry 9 }

		
		sheSyncControlGroup OBJECT IDENTIFIER ::= { sheSyncObjects 3 }

		
		sheSyncCgControlReq OBJECT-TYPE
			SYNTAX SheSyncControlReqType
			MAX-ACCESS read-write
			STATUS current
			DESCRIPTION
				"sheModifySyncSource
				sheSyncCgSourcePriority
				sheSyncCgSourceAlarmSeverityIndex
				
				sheModifySyncWaitTimeToRestore
				sheSyncCgSourceWaitTimeToRestore 
				
				sheModifySyncGlobals
				sheSyncCgMode
				sheSyncCgSourceWaitTimeToRestore
				sheSyncCgSourceSSMLevel  
				
				sheModifyUsedSyncSource
				sheSyncCgSourcePriority
				sheSyncCgSourceAvailabilityIndex
				sheSyncCgSourceSSMLevel
				"
			::= { sheSyncControlGroup 1 }

		
		sheSyncCgControlStatus OBJECT-TYPE
			SYNTAX SheControlStatusType
			MAX-ACCESS read-only
			STATUS current
			DESCRIPTION
				"Indicates the status of a control request. "
			::= { sheSyncControlGroup 2 }

		
		sheSyncCgControlReqResult OBJECT-TYPE
			SYNTAX SheSyncControlReqResultType
			MAX-ACCESS read-only
			STATUS current
			DESCRIPTION
				"The result of the last user command. "
			::= { sheSyncControlGroup 3 }

		
		sheSyncCgControlTimeStamp OBJECT-TYPE
			SYNTAX Unsigned32
			UNITS "sec"
			MAX-ACCESS read-only
			STATUS current
			DESCRIPTION
				"The time stamp of the last command (end of command). "
			::= { sheSyncControlGroup 4 }

		
		sheSyncCgSourcePriority OBJECT-TYPE
			SYNTAX SheSyncPriorityType
			MAX-ACCESS read-write
			STATUS current
			DESCRIPTION
				"A unique value to identify the synchronization source and its priority.
				Parameter for command sheModifySyncSource and sheModifyUsedSyncSource to select
				the table entry to be modified. 0 is not a useful index value for these commands."
			::= { sheSyncControlGroup 5 }

		
		sheSyncCgSourceAlarmSeverityIndex OBJECT-TYPE
			SYNTAX SheAlarmSevProfileIndex
			MAX-ACCESS read-write
			STATUS current
			DESCRIPTION
				"This index selects an item in the sheAlarmSeverityProfileTable[]. It is
				used to assign the reported alarm (clock source can't be used)
				to a severity."
			::= { sheSyncControlGroup 6 }

		
		sheSyncCgSourceWaitTimeToRestore OBJECT-TYPE
			SYNTAX SheSyncWaitTimeToRestoreType
			UNITS "100 ms"
			MAX-ACCESS read-write
			STATUS current
			DESCRIPTION
				"This time has to expire before switch back to a higher
				clock source after error condition.
				Unit is 100 ms."
			::= { sheSyncControlGroup 7 }

		
		sheSyncCgMode OBJECT-TYPE
			SYNTAX SheSyncModeType
			MAX-ACCESS read-write
			STATUS current
			DESCRIPTION
				"The used sync - mode.
				
				revertive - the highest priority sync source with valid reference is always selected.
				nonrevertive - the active sync source will always remain active while it is valid.
				Only if this sync source will be come invalid, a refence switchover to a valid reference
				with highest priority will be initiated."
			::= { sheSyncControlGroup 8 }

		
		sheSyncCgSourceSSMLevel OBJECT-TYPE
			SYNTAX Unsigned32 (0..15)
			MAX-ACCESS read-write
			STATUS current
			DESCRIPTION
				"This parameter defines the configured reference SSM-Level for this sync source.
				The level is defined in 16 steps from 0..15, where 0 is the highest quality level. "
			::= { sheSyncControlGroup 9 }

		
		sheSyncCgSourceAvailabilityIndex OBJECT-TYPE
			SYNTAX SheSyncAvailabilityIndexType
			MAX-ACCESS read-write
			STATUS current
			DESCRIPTION
				"Select an entry from sheSyncSourceAvailabilityTable to be used as possible sync source for the NE.
				An index parameter 0 will delete the current used syncSource from the selected priority position without an new entry."
			::= { sheSyncControlGroup 10 }

		
		sheSyncNotifications OBJECT IDENTIFIER ::= { sheSyncObjects 4 }

		
		sheSyncEvents OBJECT IDENTIFIER ::= { sheSyncNotifications 1 }

		
		sheSyncControlResult NOTIFICATION-TYPE
			OBJECTS { sheSyncCgControlTimeStamp, sheSyncCgSourcePriority, sheSyncCgControlReq, sheSyncCgControlReqResult }
			STATUS current
			DESCRIPTION 
				"Notification sent at the end of a long running command. "
			::= { sheSyncEvents 1 }

		
		sheSyncClockSourceModified NOTIFICATION-TYPE
			OBJECTS { sheSyncCgControlTimeStamp, sheSyncCgSourcePriority, sheSyncSourceAlarmSeverityIndex }
			STATUS current
			DESCRIPTION 
				"This trap is sent when a clock source (entry in the SyncSourceTable) has been modified."
			::= { sheSyncEvents 2 }

		
		sheSyncWaitTimeToRestoreModified NOTIFICATION-TYPE
			OBJECTS { sheSyncCgControlTimeStamp, sheSyncWaitTimeToRestore }
			STATUS current
			DESCRIPTION 
				"This trap is sent when the WaitTimeToRestore has been modified."
			::= { sheSyncEvents 3 }

		
		sheSyncActiveClockSourceChanged NOTIFICATION-TYPE
			OBJECTS { sheSyncCgControlTimeStamp, sheSyncActiveClockSource }
			STATUS current
			DESCRIPTION 
				"This trap is sent when the active clock source has changed."
			::= { sheSyncEvents 4 }

		
		sheSyncGlobalsModified NOTIFICATION-TYPE
			OBJECTS { sheSyncCgControlTimeStamp, sheSyncWaitTimeToRestore, sheSyncMode, sheSyncLocalClockSSMLevel }
			STATUS current
			DESCRIPTION 
				"This trap is sent when the SyncGlobals has been modified."
			::= { sheSyncEvents 5 }

		
		sheSyncUsedSyncSourcesModified NOTIFICATION-TYPE
			OBJECTS { sheSyncCgControlTimeStamp, sheSyncCgSourcePriority, sheSyncCgSourceAvailabilityIndex, sheSyncCgSourceSSMLevel }
			STATUS current
			DESCRIPTION 
				"This trap is sent when the used sync source table was reconfigured."
			::= { sheSyncEvents 6 }

		
		sheSyncAlarms OBJECT IDENTIFIER ::= { sheSyncNotifications 2 }

		
		sheSyncClockSourceAlarm NOTIFICATION-TYPE
			OBJECTS { sheAlarmTimeAndDate, sheAlarmReportingSource, sheAlarmReportingSourceType, sheAlarmSeverity }
			STATUS current
			DESCRIPTION 
				"An alarm is generated when a clock source can't be used."
			::= { sheSyncAlarms 1 }

		
		sheSyncSourceAvailabilityTable OBJECT-TYPE
			SYNTAX SEQUENCE OF SheSyncSourceAvailabilityEntry
			MAX-ACCESS not-accessible
			STATUS current
			DESCRIPTION
				"The source availability table is used show the management system which synchronization
				sources are available in the NE element depending on the used hardware configuration.
				The table has a fixed number of entries created by the NE. From these table entrys,
				the list of used clocksources inside the sheSyncSourceTable could be configured."
			::= { sheSyncObjects 5 }

		
		sheSyncSourceAvailabilityEntry OBJECT-TYPE
			SYNTAX SheSyncSourceAvailabilityEntry
			MAX-ACCESS not-accessible
			STATUS current
			DESCRIPTION
				"An entry in the SyncSourceAvailabilityTable.
				It defines the possible synchronization sources of the network element, depending on the used HW."
			INDEX { sheSyncSourceAvailabilityIndex }
			::= { sheSyncSourceAvailabilityTable 1 }

		
		SheSyncSourceAvailabilityEntry ::=
			SEQUENCE { 
				sheSyncSourceAvailabilityIndex
					SheSyncAvailabilityIndexType,
				sheSyncSourceAvailabilityType
					SheSyncSourceType,
				sheSyncSourceAvailabilityHwUnitIndex
					PhysicalIndex,
				sheSyncSourceAvailabilityInterfaceNumber
					Unsigned32
			 }

		sheSyncSourceAvailabilityIndex OBJECT-TYPE
			SYNTAX SheSyncAvailabilityIndexType
			MAX-ACCESS read-only
			STATUS current
			DESCRIPTION
				"A unique value to identify a available synchronization source.
				Used as table index. Value 0 is not a valid index value for this table."
			::= { sheSyncSourceAvailabilityEntry 1 }

		
		sheSyncSourceAvailabilityType OBJECT-TYPE
			SYNTAX SheSyncSourceType
			MAX-ACCESS read-only
			STATUS current
			DESCRIPTION
				"The type of the synchronization source of the network element.
				Possible values:
				sheT3inSyncSource(2),
				sheBitsSyncSource(3),
				sheEthernetSyncSource(4),
				sheE1SyncSource(5),
				sheTimingOverPacketSyncSource(6)"
			::= { sheSyncSourceAvailabilityEntry 2 }

		
		sheSyncSourceAvailabilityHwUnitIndex OBJECT-TYPE
			SYNTAX PhysicalIndex
			MAX-ACCESS read-only
			STATUS current
			DESCRIPTION
				"Identifies the hardware unit that contains the synchronization source. "
			::= { sheSyncSourceAvailabilityEntry 3 }

		
		sheSyncSourceAvailabilityInterfaceNumber OBJECT-TYPE
			SYNTAX Unsigned32 (1..72)
			MAX-ACCESS read-only
			STATUS current
			DESCRIPTION
				"The number of the physical interface of the hardware unit.
				The interfaces are numbered vendor specific starting with 1
				in ascending order. Synchronization interfaces may not be
				contained in the interface table."
			::= { sheSyncSourceAvailabilityEntry 4 }

		
		sheSyncConformance OBJECT IDENTIFIER ::= { sheSyncObjects 6 }

		
		sheSyncCompliances OBJECT IDENTIFIER ::= { sheSyncConformance 1 }

		
		sheSyncCompliance MODULE-COMPLIANCE
			STATUS current
			DESCRIPTION 
				"Description."
			MODULE -- this module
				MANDATORY-GROUPS { sheSyncConfigGroup, sheSyncConfigControlGroup, sheSyncNotificationsGroup }
			::= { sheSyncCompliances 1 }

		
		sheSyncGroups OBJECT IDENTIFIER ::= { sheSyncConformance 2 }

		
		sheSyncConfigGroup OBJECT-GROUP
			OBJECTS { sheSyncActiveClockSource, sheSyncWaitTimeToRestore, sheSyncSourcePriority, sheSyncSourceAlarmState, sheSyncSourceAlarmSeverityIndex, 
				sheSyncMode, sheSyncSourceSSMLevel, sheSyncSourceAvailabilityIndex, sheSyncSourceAvailabilityType, sheSyncSourceAvailabilityHwUnitIndex, 
				sheSyncLocalClockSSMLevel, sheSyncSourceAvailabilityInterfaceNumber, sheSyncSourceSelectedAvailabilityIndex, sheSyncSourceSSMLevelRec }
			STATUS current
			DESCRIPTION 
				"Description."
			::= { sheSyncGroups 1 }

		
		sheSyncConfigControlGroup OBJECT-GROUP
			OBJECTS { sheSyncCgControlReq, sheSyncCgControlStatus, sheSyncCgControlReqResult, sheSyncCgControlTimeStamp, sheSyncCgSourcePriority, 
				sheSyncCgSourceAlarmSeverityIndex, sheSyncCgSourceWaitTimeToRestore, sheSyncCgMode, sheSyncCgSourceSSMLevel, sheSyncCgSourceAvailabilityIndex
				 }
			STATUS current
			DESCRIPTION 
				"Description."
			::= { sheSyncGroups 2 }

		
		sheSyncNotificationsGroup NOTIFICATION-GROUP
			NOTIFICATIONS { sheSyncControlResult, sheSyncClockSourceModified, sheSyncWaitTimeToRestoreModified, sheSyncActiveClockSourceChanged, sheSyncClockSourceAlarm, 
				sheSyncUsedSyncSourcesModified, sheSyncGlobalsModified }
			STATUS current
			DESCRIPTION 
				"Description."
			::= { sheSyncGroups 3 }

		
		sheSyncObsoleteGroup OBJECT-GROUP
			OBJECTS { sheSyncSourceType, sheSyncSourceHwUnitIndex, sheSyncSourceInterfaceNumber }
			STATUS obsolete
			DESCRIPTION 
				"This parameters are not longer supported by SHE R3.0."
			::= { sheSyncGroups 4 }

		
	
	END

--
-- she-sync-mib.mib
--
