CSI-BBPROV2-MIB 
-- ******************************************************
--Control Solutions, Inc., SNMP  MIB
--Prefix for private enterprises:  1.3.6.1.4.1	
--Control Solutions, Inc. private enterprize number:  3815
--
-- The following MIB is the definition of the SNMP based 
-- implementation of Babel Buster ProV2 series.
-- This MIB provides access to general purpose data registers
-- per BB Pro core implementation.
--
--
-- ************************************************************

DEFINITIONS ::= BEGIN

IMPORTS  
	MODULE-IDENTITY, OBJECT-TYPE, Integer32, Unsigned32, NOTIFICATION-TYPE 
		FROM SNMPv2-SMI
	MODULE-COMPLIANCE, OBJECT-GROUP, NOTIFICATION-GROUP
		FROM SNMPv2-CONF
 	bbprov2, bbprov2-reg-v1 
		FROM Control-Solutions-MIB-Registrations
	Float32TC, Float64TC
		FROM FLOAT-TC-MIB;

bbproModule MODULE-IDENTITY
	LAST-UPDATED "201509290000Z"
	ORGANIZATION "Control Solutions, Inc."
	CONTACT-INFO
		"Jim Hogenson
		Control Solutions, Inc.
		380 Oak Grove Pkwy, Suite 100
		PO Box 10789
		St. Paul, MN 55110
		jimhogenson@csimn.com
		Voice: 651-426-4410
		Fax: 651-426-4418"
	DESCRIPTION
		"The following MIB is the definition of SNMP access to
		Babel Buster ProV2 SNMP-Modbus gateway."
	REVISION "201602230000Z"
	DESCRIPTION
		"Initial draft, updated with 64-bit in the Uint branch."
	::= { bbprov2-reg-v1 1 }


          -- textual conventions

          DisplayString ::=
              OCTET STRING
          -- This data type is used to model textual information taken
          -- from the NVT ASCII character set.  By convention, objects
          -- with this syntax are declared as having
          --
          --      SIZE (0..255)

-- Major object categories for Babel Buster Pro

dataRegInt32	OBJECT IDENTIFIER ::= { bbprov2 1 }  	-- 3815.1.4.1.1
dataRegUint64	OBJECT IDENTIFIER ::= { bbprov2 2 }  	-- 3815.1.4.1.2
dataRegFloat32	OBJECT IDENTIFIER ::= { bbprov2 3 }  	-- 3815.1.4.1.3
dataRegFloat64	OBJECT IDENTIFIER ::= { bbprov2 4 }  	-- 3815.1.4.1.4
dataRegCharStr	OBJECT IDENTIFIER ::= { bbprov2 5 }  	-- 3815.1.4.1.5

-- ******************************************************
--
-- INTEGER DATA REGISTER TABLE (first Int32 is 1.3.6.1.4.1.3815.1.4.1.1.1.1.2.1)
-- 
-- ******************************************************

dataRegInt32Table OBJECT-TYPE
	SYNTAX	SEQUENCE OF dataRegInt32Entry
	MAX-ACCESS	not-accessible
	STATUS	current
	DESCRIPTION
		"Integer data register table."
	::= { dataRegInt32 1 }

dataRegInt32Entry OBJECT-TYPE
	SYNTAX	dataRegInt32Entry
	MAX-ACCESS	not-accessible
	STATUS	current
	DESCRIPTION
		"Integer data register table entry."
	INDEX	{ dataRegInt32Index }
	::= { dataRegInt32Table 1 }

dataRegInt32Entry ::= SEQUENCE {
	dataRegInt32Index		INTEGER,
	dataRegInt32Register	Integer32,
	dataRegInt32Name		DisplayString,
	dataRegInt32Value		DisplayString,
	dataRegInt32Message	DisplayString,
	}

dataRegInt32Index OBJECT-TYPE
	SYNTAX	INTEGER (1..65536) 
	MAX-ACCESS	not-accessible
	STATUS	current
	DESCRIPTION
		"Register number, index into integer data register table."
	::= { dataRegInt32Entry 1 }

dataRegInt32Register OBJECT-TYPE
	SYNTAX	Integer32
	MAX-ACCESS	read-write
	STATUS	current
	DESCRIPTION
		"Register's data value."
	::= { dataRegInt32Entry 2 }

dataRegInt32Name OBJECT-TYPE
	SYNTAX	DisplayString (SIZE(0..40))
	MAX-ACCESS	read-only
	STATUS	current
	DESCRIPTION
		"Register's name."
	::= { dataRegInt32Entry 3 }

dataRegInt32Value OBJECT-TYPE
	SYNTAX	DisplayString (SIZE(0..40))
	MAX-ACCESS	not-accessible
	STATUS	current
	DESCRIPTION
		"Register's value as ASCII string in trap message."
	::= { dataRegInt32Entry 4 }

dataRegInt32Message OBJECT-TYPE
	SYNTAX	DisplayString (SIZE(0..40))
	MAX-ACCESS	not-accessible
	STATUS	current
	DESCRIPTION
		"Trap message related to this variable."
	::= { dataRegInt32Entry 5 }

-- ******************************************************
--
-- UNSIGNED INTEGER DATA REGISTER TABLE (first Uint64 is 1.3.6.1.4.1.3815.1.4.1.2.1.1.2.1)
-- 
-- ******************************************************

dataRegUint64Table OBJECT-TYPE
	SYNTAX	SEQUENCE OF dataRegUint64Entry
	MAX-ACCESS	not-accessible
	STATUS	current
	DESCRIPTION
		"Unsigned 64-bit integer data register table."
	::= { dataRegUint64 1 }

dataRegUint64Entry OBJECT-TYPE
	SYNTAX	dataRegUint64Entry
	MAX-ACCESS	not-accessible
	STATUS	current
	DESCRIPTION
		"Unsigned 64-bit integer data register table entry."
	INDEX	{ dataRegUint64Index }
	::= { dataRegUint64Table 1 }

dataRegUint64Entry ::= SEQUENCE {
	dataRegUint64Index	INTEGER,
	dataRegUint64Register	Counter64,
	dataRegUint64Name		DisplayString,
	dataRegUint64Value	DisplayString,
	dataRegUint64Message	DisplayString,
	}

dataRegUint64Index OBJECT-TYPE
	SYNTAX	INTEGER (1..65536) 
	MAX-ACCESS	not-accessible
	STATUS	current
	DESCRIPTION
		"Register number, index into unsigned 64-bit integer table."
	::= { dataRegUint64Entry 1 }

dataRegUint64Register OBJECT-TYPE
	SYNTAX	Counter64
	MAX-ACCESS	read-write
	STATUS	current
	DESCRIPTION
		"Register's data value."
	::= { dataRegUint64Entry 2 }

dataRegUint64Name OBJECT-TYPE
	SYNTAX	DisplayString (SIZE(0..40))
	MAX-ACCESS	read-only
	STATUS	current
	DESCRIPTION
		"Register's name."
	::= { dataRegUint64Entry 3 }

dataRegUint64Value OBJECT-TYPE
	SYNTAX	DisplayString (SIZE(0..40))
	MAX-ACCESS	not-accessible
	STATUS	current
	DESCRIPTION
		"Register's value as ASCII string in trap message."
	::= { dataRegUint64Entry 4 }

dataRegUint64Message OBJECT-TYPE
	SYNTAX	DisplayString (SIZE(0..40))
	MAX-ACCESS	not-accessible
	STATUS	current
	DESCRIPTION
		"Trap message related to this variable."
	::= { dataRegUint64Entry 5 }

-- ******************************************************
--
-- 32-BIT FLOATING POINT DATA REGISTER TABLE (first Float32 is 1.3.6.1.4.1.3815.1.4.1.3.1.1.2.1)
-- 
-- ******************************************************

dataRegFloat32Table OBJECT-TYPE
	SYNTAX	SEQUENCE OF dataRegFloat32Entry
	MAX-ACCESS	not-accessible
	STATUS	current
	DESCRIPTION
		"Floating point data register table."
	::= { dataRegFloat32 1 }

dataRegFloat32Entry OBJECT-TYPE
	SYNTAX	dataRegFloat32Entry
	MAX-ACCESS	not-accessible
	STATUS	current
	DESCRIPTION
		"Floating point data register table entry."
	INDEX	{ dataRegFloat32Index }
	::= { dataRegFloat32Table 1 }

dataRegFloat32Entry ::= SEQUENCE {
	dataRegFloat32Index	INTEGER,
	dataRegFloat32Register	Float32TC,
	dataRegFloat32Name	DisplayString,
	dataRegFloat32Value	DisplayString,
	dataRegFloat32Message	DisplayString,
	}

dataRegFloat32Index OBJECT-TYPE
	SYNTAX	INTEGER (1..65536) 
	MAX-ACCESS	not-accessible
	STATUS	current
	DESCRIPTION
		"Register number, index into floating point table."
	::= { dataRegFloat32Entry 1 }

dataRegFloat32Register OBJECT-TYPE
	SYNTAX	Float32TC
	MAX-ACCESS	read-write
	STATUS	current
	DESCRIPTION
		"Register's data value."
	::= { dataRegFloat32Entry 2 }

dataRegFloat32Name OBJECT-TYPE
	SYNTAX	DisplayString (SIZE(0..40))
	MAX-ACCESS	read-only
	STATUS	current
	DESCRIPTION
		"Register's name."
	::= { dataRegFloat32Entry 3 }

dataRegFloat32Value OBJECT-TYPE
	SYNTAX	DisplayString (SIZE(0..40))
	MAX-ACCESS	not-accessible
	STATUS	current
	DESCRIPTION
		"Register's value as ASCII string in trap message."
	::= { dataRegFloat32Entry 4 }

dataRegFloat32Message OBJECT-TYPE
	SYNTAX	DisplayString (SIZE(0..40))
	MAX-ACCESS	not-accessible
	STATUS	current
	DESCRIPTION
		"Trap message related to this variable."
	::= { dataRegFloat32Entry 5 }

-- ******************************************************
--
-- 64-BIT FLOATING POINT DATA REGISTER TABLE (first Float64 is 1.3.6.1.4.1.3815.1.4.1.4.1.1.2.1)
-- 
-- ******************************************************

dataRegFloat64Table OBJECT-TYPE
	SYNTAX	SEQUENCE OF dataRegFloat64Entry
	MAX-ACCESS	not-accessible
	STATUS	current
	DESCRIPTION
		"Double precision floating point data register table."
	::= { dataRegFloat64 1 }

dataRegFloat64Entry OBJECT-TYPE
	SYNTAX	dataRegFloat64Entry
	MAX-ACCESS	not-accessible
	STATUS	current
	DESCRIPTION
		"Double floating point data register table entry."
	INDEX	{ dataRegFloat64Index }
	::= { dataRegFloat64Table 1 }

dataRegFloat64Entry ::= SEQUENCE {
	dataRegFloat64Index	INTEGER,
	dataRegFloat64Register	Float64TC,
	dataRegFloat64Name	DisplayString,
	dataRegFloat64Value	DisplayString,
	dataRegFloat64Message	DisplayString,
	}

dataRegFloat64Index OBJECT-TYPE
	SYNTAX	INTEGER (1..65536) 
	MAX-ACCESS	not-accessible
	STATUS	current
	DESCRIPTION
		"Register number, index into double precision float table."
	::= { dataRegFloat64Entry 1 }

dataRegFloat64Register OBJECT-TYPE
	SYNTAX	Float64TC
	MAX-ACCESS	read-write
	STATUS	current
	DESCRIPTION
		"Register's data value."
	::= { dataRegFloat64Entry 2 }

dataRegFloat64Name OBJECT-TYPE
	SYNTAX	DisplayString (SIZE(0..40))
	MAX-ACCESS	read-only
	STATUS	current
	DESCRIPTION
		"Register's name."
	::= { dataRegFloat64Entry 3 }

dataRegFloat64Value OBJECT-TYPE
	SYNTAX	DisplayString (SIZE(0..40))
	MAX-ACCESS	not-accessible
	STATUS	current
	DESCRIPTION
		"Register's value as ASCII string in trap message."
	::= { dataRegFloat64Entry 4 }

dataRegFloat64Message OBJECT-TYPE
	SYNTAX	DisplayString (SIZE(0..40))
	MAX-ACCESS	not-accessible
	STATUS	current
	DESCRIPTION
		"Trap message related to this variable."
	::= { dataRegFloat64Entry 5 }

-- ******************************************************
--
-- CHARACTER STRING DATA REGISTER TABLE (first CharStr is 1.3.6.1.4.1.3815.1.4.1.5.1.1.2.1)
-- 
-- ******************************************************

dataRegCharStrTable OBJECT-TYPE
	SYNTAX	SEQUENCE OF dataRegCharStrEntry
	MAX-ACCESS	not-accessible
	STATUS	current
	DESCRIPTION
		"Character string data register table."
	::= { dataRegCharStr 1 }

dataRegCharStrEntry OBJECT-TYPE
	SYNTAX	dataRegCharStrEntry
	MAX-ACCESS	not-accessible
	STATUS	current
	DESCRIPTION
		"Character string data register table entry."
	INDEX	{ dataRegCharStrIndex }
	::= { dataRegCharStrTable 1 }

dataRegCharStrEntry ::= SEQUENCE {
	dataRegCharStrIndex	INTEGER,
	dataRegCharStrRegister	DisplayString,
	dataRegCharStrName	DisplayString,
	dataRegCharValue		DisplayString,
	dataRegCharMessage	DisplayString,
	}

dataRegCharStrIndex OBJECT-TYPE
	SYNTAX	INTEGER (1..65536) 
	MAX-ACCESS	not-accessible
	STATUS	current
	DESCRIPTION
		"Register number, index into character string table."
	::= { dataRegCharStrEntry 1 }

dataRegCharStrRegister OBJECT-TYPE
	SYNTAX	DisplayString (SIZE(0..80))
	MAX-ACCESS	read-write
	STATUS	current
	DESCRIPTION
		"Register's data value."
	::= { dataRegCharStrEntry 2 }

dataRegCharStrName OBJECT-TYPE
	SYNTAX	DisplayString (SIZE(0..40))
	MAX-ACCESS	read-only
	STATUS	current
	DESCRIPTION
		"Register's name."
	::= { dataRegCharStrEntry 3 }

dataRegCharValue OBJECT-TYPE
	SYNTAX	DisplayString (SIZE(0..40))
	MAX-ACCESS	not-accessible
	STATUS	current
	DESCRIPTION
		"Register's value as ASCII string in trap message."
	::= { dataRegCharStrEntry 4 }

dataRegCharMessage OBJECT-TYPE
	SYNTAX	DisplayString (SIZE(0..40))
	MAX-ACCESS	not-accessible
	STATUS	current
	DESCRIPTION
		"Trap message related to this variable."
	::= { dataRegCharStrEntry 5 }

-- ******************************************************
--
-- SIMPLE I/O FOR SNMP NOTIFICATIONS
-- 
-- ******************************************************

bbprov2Traps		OBJECT IDENTIFIER ::= { bbprov2 6 }

trapRuleStateChange		NOTIFICATION-TYPE
	OBJECTS {
		changeRegValue,
		changeRegName,
		changeRegValueString,
		changeMessage
	}
	STATUS	 	current
	DESCRIPTION
		"This trap is sent when a register changes value
		if notifications are enabled for the object that changed."
	::= { bbprov2Traps 1 }

-- ******************************************************
--
-- SIMPLE I/O FOR SNMP COMPLIANCE
-- 
-- ******************************************************

bbproConformance	OBJECT IDENTIFIER ::= { bbprov2 7 }

bbproGroups			OBJECT IDENTIFIER ::= { bbproConformance 1 }
bbproCompliances 	OBJECT IDENTIFIER ::= { bbproConformance 2 }

bbproCompliance MODULE-COMPLIANCE
	STATUS 	current
	DESCRIPTION
		"The compliance statement for SNMPv2 entities which
		implement the agent supported by the Babel Buster Pro core."
	MODULE
	MANDATORY-GROUPS
		{ bbproDataRegIntGroup }
	::= { bbproCompliances 1 }

bbproDataRegIntGroup	OBJECT-GROUP
	OBJECTS {
		dataRegInt32Register,
		dataRegInt32Register
	}
	STATUS 	current
	DESCRIPTION
		"Group of objects that define integer data registers."
	::= { bbproGroups 1 }

bbproNotificationGroup	NOTIFICATION-GROUP
	NOTIFICATIONS { 
		trapRuleStateChange 
	}
	STATUS current
	DESCRIPTION
		"Group of objects that define notifications."
	::= { bbproGroups 2 }

END
