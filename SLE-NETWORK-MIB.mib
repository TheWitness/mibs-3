--
-- SLE-NETWORK-MIB.my
-- MIB generated by MG-SOFT Visual MIB Builder Version 6.0  Build 88
-- Wednesday, December 17, 2008 at 13:37:41
--

	SLE-NETWORK-MIB DEFINITIONS ::= BEGIN
 
		IMPORTS
			sleMgmt			
				FROM DASAN-SMI			
			InterfaceIndex			
				FROM IF-MIB			
			SleControlStatusType, SleControlRequestResultType			
				FROM SLE-TC-MIB			
			OBJECT-GROUP, NOTIFICATION-GROUP			
				FROM SNMPv2-CONF			
			TimeTicks, IpAddress, Integer32, Gauge32, BITS, 
			OBJECT-TYPE, MODULE-IDENTITY, NOTIFICATION-TYPE			
				FROM SNMPv2-SMI			
			MacAddress			
				FROM SNMPv2-TC;
	
	
		-- 1.3.6.1.4.1.6296.101.11
		sleNetwork MODULE-IDENTITY 
			LAST-UPDATED "200412291441Z"		-- December 29, 2004 at 14:41 GMT
			ORGANIZATION 
				"HANASOFT"
			CONTACT-INFO 
				" "
			DESCRIPTION 
				"This MIB contains all needed informations about DHCP and
				all supported sle DHCP features."
			REVISION "200412101632Z"		-- December 10, 2004 at 16:32 GMT
			DESCRIPTION 
				"Description"
			::= { sleMgmt 11 }

		
	
	
	
--
-- Node definitions
--
	
		-- 1.3.6.1.4.1.6296.101.11.1
		sleNetInterface OBJECT IDENTIFIER ::= { sleNetwork 1 }

		
		-- 1.3.6.1.4.1.6296.101.11.1.1
		sleNetIfTable OBJECT-TYPE
			SYNTAX SEQUENCE OF SleNetIfEntry
			MAX-ACCESS not-accessible
			STATUS current
			DESCRIPTION
				"Description."
			::= { sleNetInterface 1 }

		
		-- 1.3.6.1.4.1.6296.101.11.1.1.1
		sleNetIfEntry OBJECT-TYPE
			SYNTAX SleNetIfEntry
			MAX-ACCESS not-accessible
			STATUS current
			DESCRIPTION
				"Description."
			INDEX { sleNetIfIndex }
			::= { sleNetIfTable 1 }

		
		SleNetIfEntry ::=
			SEQUENCE { 
				sleNetIfIndex
					Integer32,
				sleNetIfName
					OCTET STRING,
				sleNetIfDescription
					OCTET STRING,
				sleNetIfTableIndex
					InterfaceIndex,
				sleNetIfRegState
					INTEGER,
				sleNetIfAdminState
					INTEGER,
				sleNetIfOperState
					INTEGER,
				sleNetIfMulticast
					INTEGER,
				sleNetIfMtu
					INTEGER,
				sleNetIfIpSetMode
					INTEGER,
				sleNetIfIpMartianFilter
					INTEGER
			 }

		-- 1.3.6.1.4.1.6296.101.11.1.1.1.1
		sleNetIfIndex OBJECT-TYPE
			SYNTAX Integer32 (0..4097)
			MAX-ACCESS read-only
			STATUS current
			DESCRIPTION
				"Network interface index
				0      : any(all)
				1..4094: VLAN
				4095   : management
				4096   : loopback
				4097   : null
				"
			::= { sleNetIfEntry 1 }

		
		-- 1.3.6.1.4.1.6296.101.11.1.1.1.2
		sleNetIfName OBJECT-TYPE
			SYNTAX OCTET STRING (SIZE (0..8))
			MAX-ACCESS read-only
			STATUS current
			DESCRIPTION
				"Device Name of this Interface."
			::= { sleNetIfEntry 2 }

		
		-- 1.3.6.1.4.1.6296.101.11.1.1.1.3
		sleNetIfDescription OBJECT-TYPE
			SYNTAX OCTET STRING (SIZE (0..64))
			MAX-ACCESS read-only
			STATUS current
			DESCRIPTION
				"Description of this interface."
			::= { sleNetIfEntry 3 }

		
		-- 1.3.6.1.4.1.6296.101.11.1.1.1.4
		sleNetIfTableIndex OBJECT-TYPE
			SYNTAX InterfaceIndex
			MAX-ACCESS read-only
			STATUS current
			DESCRIPTION
				"Same as ifIndex (for appropriated ifTable entries)."
			::= { sleNetIfEntry 4 }

		
		-- 1.3.6.1.4.1.6296.101.11.1.1.1.5
		sleNetIfRegState OBJECT-TYPE
			SYNTAX INTEGER
				{
				unregistered(0),
				registered(1)
				}
			MAX-ACCESS read-only
			STATUS current
			DESCRIPTION
				"Registered state of Network device."
			::= { sleNetIfEntry 5 }

		
		-- 1.3.6.1.4.1.6296.101.11.1.1.1.6
		sleNetIfAdminState OBJECT-TYPE
			SYNTAX INTEGER
				{
				down(0),
				up(1)
				}
			MAX-ACCESS read-only
			STATUS current
			DESCRIPTION
				"Administrative state.
				down - shutdown
				up - noshutdown"
			::= { sleNetIfEntry 6 }

		
		-- 1.3.6.1.4.1.6296.101.11.1.1.1.7
		sleNetIfOperState OBJECT-TYPE
			SYNTAX INTEGER
				{
				down(0),
				up(1)
				}
			MAX-ACCESS read-only
			STATUS current
			DESCRIPTION
				"Operational state.
				down - shutdown or not running
				up - running"
			::= { sleNetIfEntry 7 }

		
		-- 1.3.6.1.4.1.6296.101.11.1.1.1.8
		sleNetIfMulticast OBJECT-TYPE
			SYNTAX INTEGER
				{
				disable(0),
				enable(1)
				}
			MAX-ACCESS read-only
			STATUS current
			DESCRIPTION
				"Multicast enable/disable state."
			::= { sleNetIfEntry 8 }

		
		-- 1.3.6.1.4.1.6296.101.11.1.1.1.9
		sleNetIfMtu OBJECT-TYPE
			SYNTAX INTEGER (64..17940)
			MAX-ACCESS read-only
			STATUS current
			DESCRIPTION
				"Maximum Transmission Unit."
			::= { sleNetIfEntry 9 }

		
		-- 1.3.6.1.4.1.6296.101.11.1.1.1.10
		sleNetIfIpSetMode OBJECT-TYPE
			SYNTAX INTEGER
				{
				static(0),
				dynamic(1)
				}
			MAX-ACCESS read-only
			STATUS current
			DESCRIPTION
				"IP address setting mode.
				0 : static
				1 : dynamic (by DHCP client)
				"
			::= { sleNetIfEntry 10 }

		
		-- 1.3.6.1.4.1.6296.101.11.1.1.1.11
		sleNetIfIpMartianFilter OBJECT-TYPE
			SYNTAX INTEGER
				{
				disable(0),
				enable(1)
				}
			MAX-ACCESS read-only
			STATUS current
			DESCRIPTION
				"Description."
			::= { sleNetIfEntry 11 }

		
		-- 1.3.6.1.4.1.6296.101.11.1.2
		sleNetIfControl OBJECT IDENTIFIER ::= { sleNetInterface 2 }

		
		-- 1.3.6.1.4.1.6296.101.11.1.2.1
		sleNetIfControlRequest OBJECT-TYPE
			SYNTAX INTEGER
				{
				setNetIfRegState(1),
				setNetIfProfile(2),
				setNetIfIpMartianFilter(3)
				}
			MAX-ACCESS read-write
			STATUS current
			DESCRIPTION
				"The request of a user command."
			DEFVAL { setNetIfProfile }
			::= { sleNetIfControl 1 }

		
		-- 1.3.6.1.4.1.6296.101.11.1.2.2
		sleNetIfControlStatus OBJECT-TYPE
			SYNTAX SleControlStatusType
			MAX-ACCESS read-only
			STATUS current
			DESCRIPTION
				"The status of a user command."
			::= { sleNetIfControl 2 }

		
		-- 1.3.6.1.4.1.6296.101.11.1.2.3
		sleNetIfControlTimer OBJECT-TYPE
			SYNTAX Gauge32
			MAX-ACCESS read-write
			STATUS current
			DESCRIPTION
				"The maximum wait time for the manager for a long running user command."
			DEFVAL { 0 }
			::= { sleNetIfControl 3 }

		
		-- 1.3.6.1.4.1.6296.101.11.1.2.4
		sleNetIfControlTimeStamp OBJECT-TYPE
			SYNTAX SleControlRequestResultType
			MAX-ACCESS read-only
			STATUS current
			DESCRIPTION
				"The time stamp of the last command (end of command)."
			::= { sleNetIfControl 4 }

		
		-- 1.3.6.1.4.1.6296.101.11.1.2.5
		sleNetIfControlReqResult OBJECT-TYPE
			SYNTAX TimeTicks
			MAX-ACCESS read-only
			STATUS current
			DESCRIPTION
				"The result of the last user command."
			::= { sleNetIfControl 5 }

		
		-- 1.3.6.1.4.1.6296.101.11.1.2.6
		sleNetIfControlIndex OBJECT-TYPE
			SYNTAX INTEGER (0..4095)
			MAX-ACCESS read-write
			STATUS current
			DESCRIPTION
				"Network interface index."
			DEFVAL { 1 }
			::= { sleNetIfControl 6 }

		
		-- 1.3.6.1.4.1.6296.101.11.1.2.7
		sleNetIfControlDescription OBJECT-TYPE
			SYNTAX OCTET STRING (SIZE (0..64))
			MAX-ACCESS read-write
			STATUS current
			DESCRIPTION
				"Description of this interface."
			DEFVAL { "" }
			::= { sleNetIfControl 7 }

		
		-- 1.3.6.1.4.1.6296.101.11.1.2.8
		sleNetIfControlRegState OBJECT-TYPE
			SYNTAX INTEGER
				{
				unregister(0),
				register(1)
				}
			MAX-ACCESS read-write
			STATUS current
			DESCRIPTION
				"Description."
			::= { sleNetIfControl 8 }

		
		-- 1.3.6.1.4.1.6296.101.11.1.2.9
		sleNetIfControlAdminState OBJECT-TYPE
			SYNTAX INTEGER
				{
				down(0),
				up(1)
				}
			MAX-ACCESS read-write
			STATUS current
			DESCRIPTION
				"Administrative state."
			DEFVAL { up }
			::= { sleNetIfControl 9 }

		
		-- 1.3.6.1.4.1.6296.101.11.1.2.10
		sleNetIfControlMulticast OBJECT-TYPE
			SYNTAX INTEGER
				{
				disable(0),
				enable(1)
				}
			MAX-ACCESS read-write
			STATUS current
			DESCRIPTION
				"Multicast enable/disable state."
			DEFVAL { enable }
			::= { sleNetIfControl 10 }

		
		-- 1.3.6.1.4.1.6296.101.11.1.2.11
		sleNetIfControlMtu OBJECT-TYPE
			SYNTAX INTEGER (64..17940)
			MAX-ACCESS read-write
			STATUS current
			DESCRIPTION
				"Maximum Transmission Unit."
			DEFVAL { 1500 }
			::= { sleNetIfControl 11 }

		
		-- 1.3.6.1.4.1.6296.101.11.1.2.12
		sleNetIfControlIpMartianFilter OBJECT-TYPE
			SYNTAX INTEGER
				{
				disable(0),
				enable(1)
				}
			MAX-ACCESS read-write
			STATUS current
			DESCRIPTION
				"Description."
			::= { sleNetIfControl 12 }

		
		-- 1.3.6.1.4.1.6296.101.11.1.3
		sleNetIfNotification OBJECT IDENTIFIER ::= { sleNetInterface 3 }

		
		-- 1.3.6.1.4.1.6296.101.11.1.3.1
		sleNetIfRegStateChanged NOTIFICATION-TYPE
			OBJECTS { sleNetIfControlRequest, sleNetIfControlTimeStamp, sleNetIfControlReqResult, sleNetIfRegState }
			STATUS current
			DESCRIPTION 
				"Description."
			::= { sleNetIfNotification 1 }

		
		-- 1.3.6.1.4.1.6296.101.11.1.3.2
		sleNetIfProfileChanged NOTIFICATION-TYPE
			OBJECTS { sleNetIfControlRequest, sleNetIfControlTimeStamp, sleNetIfControlReqResult, sleNetIfDescription, sleNetIfAdminState, 
				sleNetIfMulticast, sleNetIfMtu }
			STATUS current
			DESCRIPTION 
				"setNetIfProfile."
			::= { sleNetIfNotification 2 }

		
		-- 1.3.6.1.4.1.6296.101.11.1.3.3
		sleNetIfIpMartianFilterChanged NOTIFICATION-TYPE
			OBJECTS { sleNetIfControlRequest, sleNetIfControlIndex, sleNetIfControlTimeStamp, sleNetIfControlReqResult, sleNetIfControlIpMartianFilter
				 }
			STATUS current
			DESCRIPTION 
				"Description."
			::= { sleNetIfNotification 3 }

		
		-- 1.3.6.1.4.1.6296.101.11.2
		sleIpAddress OBJECT IDENTIFIER ::= { sleNetwork 2 }

		
		-- 1.3.6.1.4.1.6296.101.11.2.1
		sleIpAddrTable OBJECT-TYPE
			SYNTAX SEQUENCE OF SleIpAddrEntry
			MAX-ACCESS not-accessible
			STATUS current
			DESCRIPTION
				"Description."
			::= { sleIpAddress 1 }

		
		-- 1.3.6.1.4.1.6296.101.11.2.1.1
		sleIpAddrEntry OBJECT-TYPE
			SYNTAX SleIpAddrEntry
			MAX-ACCESS not-accessible
			STATUS current
			DESCRIPTION
				"Description."
			INDEX { sleNetIfIndex, sleIpAddrValue }
			::= { sleIpAddrTable 1 }

		
		SleIpAddrEntry ::=
			SEQUENCE { 
				sleIpAddrValue
					IpAddress,
				sleIpAddrMask
					Integer32,
				sleIpAddrBcast
					IpAddress,
				sleIpAddrFlag
					BITS,
				sleIpAddrScope
					INTEGER
			 }

		-- 1.3.6.1.4.1.6296.101.11.2.1.1.1
		sleIpAddrValue OBJECT-TYPE
			SYNTAX IpAddress
			MAX-ACCESS read-only
			STATUS current
			DESCRIPTION
				"The IP address to which this entry's addressing information pertains."
			::= { sleIpAddrEntry 1 }

		
		-- 1.3.6.1.4.1.6296.101.11.2.1.1.2
		sleIpAddrMask OBJECT-TYPE
			SYNTAX Integer32 (1..32)
			MAX-ACCESS read-only
			STATUS current
			DESCRIPTION
				"The subnet mask associated with the IP address of this entry.  
				The value of the mask is an IP address with all the network 
				bits set to 1 and all the hosts bits set to 0."
			::= { sleIpAddrEntry 2 }

		
		-- 1.3.6.1.4.1.6296.101.11.2.1.1.3
		sleIpAddrBcast OBJECT-TYPE
			SYNTAX IpAddress
			MAX-ACCESS read-only
			STATUS current
			DESCRIPTION
				"The value of the least-significant bit in the IP broadcast 
				address used for sending datagrams on the (logical) 
				interface associated with the IP address of this entry.
				For example, when the Internet standard all-ones broadcast 
				address is used, the value will be 1.  This value applies 
				to both the subnet and network broadcasts addresses used 
				by the entity on this (logical) interface."
			::= { sleIpAddrEntry 3 }

		
		-- 1.3.6.1.4.1.6296.101.11.2.1.1.4
		sleIpAddrFlag OBJECT-TYPE
			SYNTAX BITS
				{
				permanent(0),
				tentative(1),
				deprecated(2),
				reserved3(3),
				reserved4(4),
				reserved5(5),
				reserved6(6),
				secondary(7)
				}
			MAX-ACCESS read-only
			STATUS current
			DESCRIPTION
				"Description."
			::= { sleIpAddrEntry 4 }

		
		-- 1.3.6.1.4.1.6296.101.11.2.1.1.5
		sleIpAddrScope OBJECT-TYPE
			SYNTAX INTEGER
				{
				global(0),
				site(200),
				link(253),
				host(254),
				nowhere(255)
				}
			MAX-ACCESS read-only
			STATUS current
			DESCRIPTION
				"Description."
			::= { sleIpAddrEntry 5 }

		
		-- 1.3.6.1.4.1.6296.101.11.2.2
		sleIpAddrControl OBJECT IDENTIFIER ::= { sleIpAddress 2 }

		
		-- 1.3.6.1.4.1.6296.101.11.2.2.1
		sleIpAddrControlRequest OBJECT-TYPE
			SYNTAX INTEGER
				{
				createIpAddress(1),
				destroyIpAddress(2)
				}
			MAX-ACCESS read-write
			STATUS current
			DESCRIPTION
				"The request of a user command."
			::= { sleIpAddrControl 1 }

		
		-- 1.3.6.1.4.1.6296.101.11.2.2.2
		sleIpAddrControlStatus OBJECT-TYPE
			SYNTAX SleControlStatusType
			MAX-ACCESS read-only
			STATUS current
			DESCRIPTION
				"The status of a user command."
			::= { sleIpAddrControl 2 }

		
		-- 1.3.6.1.4.1.6296.101.11.2.2.3
		sleIpAddrControlTimer OBJECT-TYPE
			SYNTAX Gauge32
			MAX-ACCESS read-write
			STATUS current
			DESCRIPTION
				"The maximum wait time for the manager for a long running user command."
			DEFVAL { 0 }
			::= { sleIpAddrControl 3 }

		
		-- 1.3.6.1.4.1.6296.101.11.2.2.4
		sleIpAddrControlTimeStamp OBJECT-TYPE
			SYNTAX SleControlRequestResultType
			MAX-ACCESS read-only
			STATUS current
			DESCRIPTION
				"The time stamp of the last command (end of command)."
			::= { sleIpAddrControl 4 }

		
		-- 1.3.6.1.4.1.6296.101.11.2.2.5
		sleIpAddrControlReqResult OBJECT-TYPE
			SYNTAX TimeTicks
			MAX-ACCESS read-only
			STATUS current
			DESCRIPTION
				"The result of the last user command."
			::= { sleIpAddrControl 5 }

		
		-- 1.3.6.1.4.1.6296.101.11.2.2.6
		sleIpAddrControlNetIfIndex OBJECT-TYPE
			SYNTAX Integer32 (1..4094)
			MAX-ACCESS read-write
			STATUS current
			DESCRIPTION
				"Vlan Index."
			DEFVAL { 1 }
			::= { sleIpAddrControl 6 }

		
		-- 1.3.6.1.4.1.6296.101.11.2.2.7
		sleIpAddrControlValue OBJECT-TYPE
			SYNTAX IpAddress
			MAX-ACCESS read-write
			STATUS current
			DESCRIPTION
				"The IP address to which this entry's addressing information pertains."
			DEFVAL { 'ac106464'h }
			::= { sleIpAddrControl 7 }

		
		-- 1.3.6.1.4.1.6296.101.11.2.2.8
		sleIpAddrControlMask OBJECT-TYPE
			SYNTAX Integer32 (1..32)
			MAX-ACCESS read-write
			STATUS current
			DESCRIPTION
				"The subnet mask associated with the IP address of this entry.  "
			DEFVAL { 24 }
			::= { sleIpAddrControl 8 }

		
		-- 1.3.6.1.4.1.6296.101.11.2.2.9
		sleIpAddrControlFlag OBJECT-TYPE
			SYNTAX INTEGER
				{
				primary(0),
				secondary(1)
				}
			MAX-ACCESS read-write
			STATUS current
			DESCRIPTION
				"Description."
			DEFVAL { primary }
			::= { sleIpAddrControl 9 }

		
		-- 1.3.6.1.4.1.6296.101.11.2.2.10
		sleIpAddrControlScope OBJECT-TYPE
			SYNTAX INTEGER
				{
				global(0),
				link(253),
				host(254)
				}
			MAX-ACCESS read-write
			STATUS current
			DESCRIPTION
				"Description."
			DEFVAL { global }
			::= { sleIpAddrControl 10 }

		
		-- 1.3.6.1.4.1.6296.101.11.2.3
		sleIpAddrNotification OBJECT IDENTIFIER ::= { sleIpAddress 3 }

		
		-- 1.3.6.1.4.1.6296.101.11.2.3.1
		sleIpAddressCreated NOTIFICATION-TYPE
			OBJECTS { sleIpAddrControlRequest, sleIpAddrControlTimeStamp, sleIpAddrControlReqResult, sleIpAddrMask, sleIpAddrFlag, 
				sleIpAddrScope }
			STATUS current
			DESCRIPTION 
				"createIpAddress."
			::= { sleIpAddrNotification 1 }

		
		-- 1.3.6.1.4.1.6296.101.11.2.3.2
		sleIpAddressDestroyed NOTIFICATION-TYPE
			OBJECTS { sleIpAddrControlRequest, sleIpAddrControlTimeStamp, sleIpAddrControlReqResult, sleIpAddrMask }
			STATUS current
			DESCRIPTION 
				"destroyIpAddress."
			::= { sleIpAddrNotification 2 }

		
		-- 1.3.6.1.4.1.6296.101.11.3
		sleArp OBJECT IDENTIFIER ::= { sleNetwork 3 }

		
		-- 1.3.6.1.4.1.6296.101.11.3.1
		sleArpTable OBJECT-TYPE
			SYNTAX SEQUENCE OF SleArpEntry
			MAX-ACCESS not-accessible
			STATUS current
			DESCRIPTION
				"Description."
			::= { sleArp 1 }

		
		-- 1.3.6.1.4.1.6296.101.11.3.1.1
		sleArpEntry OBJECT-TYPE
			SYNTAX SleArpEntry
			MAX-ACCESS not-accessible
			STATUS current
			DESCRIPTION
				"Description."
			INDEX { sleNetIfIndex, sleArpIpAddress }
			::= { sleArpTable 1 }

		
		SleArpEntry ::=
			SEQUENCE { 
				sleArpIpAddress
					IpAddress,
				sleArpPhyAddress
					MacAddress,
				sleArpPortIndex
					Integer32,
				sleArpState
					INTEGER,
				sleArpHwType
					INTEGER,
				sleArpHwUsed
					INTEGER,
				sleArpUsedTime
					INTEGER
			 }

		-- 1.3.6.1.4.1.6296.101.11.3.1.1.1
		sleArpIpAddress OBJECT-TYPE
			SYNTAX IpAddress
			MAX-ACCESS read-only
			STATUS current
			DESCRIPTION
				"The NetworkAddress (e.g., the IP address) corresponding 
				to the media-dependent `physical' address."
			::= { sleArpEntry 1 }

		
		-- 1.3.6.1.4.1.6296.101.11.3.1.1.2
		sleArpPhyAddress OBJECT-TYPE
			SYNTAX MacAddress
			MAX-ACCESS read-only
			STATUS current
			DESCRIPTION
				"The media-dependent `physical' address."
			::= { sleArpEntry 2 }

		
		-- 1.3.6.1.4.1.6296.101.11.3.1.1.3
		sleArpPortIndex OBJECT-TYPE
			SYNTAX Integer32 (0..255)
			MAX-ACCESS read-only
			STATUS current
			DESCRIPTION
				"The interface on which this entry's equivalence is effective.
				0: for any ports."
			::= { sleArpEntry 3 }

		
		-- 1.3.6.1.4.1.6296.101.11.3.1.1.4
		sleArpState OBJECT-TYPE
			SYNTAX INTEGER
				{
				static(0),
				dynamic(1)
				}
			MAX-ACCESS read-only
			STATUS current
			DESCRIPTION
				"Arp entry's currently status."
			::= { sleArpEntry 4 }

		
		-- 1.3.6.1.4.1.6296.101.11.3.1.1.5
		sleArpHwType OBJECT-TYPE
			SYNTAX INTEGER { ethernet(1) }
			MAX-ACCESS read-only
			STATUS current
			DESCRIPTION
				"Hardware Type of media."
			::= { sleArpEntry 5 }

		
		-- 1.3.6.1.4.1.6296.101.11.3.1.1.6
		sleArpHwUsed OBJECT-TYPE
			SYNTAX INTEGER
				{
				nonused(0),
				used(1)
				}
			MAX-ACCESS read-only
			STATUS current
			DESCRIPTION
				"Arp entry's currently chip usage state."
			::= { sleArpEntry 6 }

		
		-- 1.3.6.1.4.1.6296.101.11.3.1.1.7
		sleArpUsedTime OBJECT-TYPE
			SYNTAX INTEGER (1..10000000)
			MAX-ACCESS read-only
			STATUS current
			DESCRIPTION
				"Arp entry's chip used time.(if sleArpState is 0, always 0 and if sleArpHwUsed is 0, always 0.)"
			::= { sleArpEntry 7 }

		
		-- 1.3.6.1.4.1.6296.101.11.3.2
		sleArpControl OBJECT IDENTIFIER ::= { sleArp 2 }

		
		-- 1.3.6.1.4.1.6296.101.11.3.2.1
		sleArpControlRequest OBJECT-TYPE
			SYNTAX INTEGER
				{
				createArpEntry(1),
				destroyArpEntry(2),
				clearArpTable(3),
				clearArpTableByAddr(4)
				}
			MAX-ACCESS read-write
			STATUS current
			DESCRIPTION
				"The request of a user command."
			::= { sleArpControl 1 }

		
		-- 1.3.6.1.4.1.6296.101.11.3.2.2
		sleArpControlStatus OBJECT-TYPE
			SYNTAX SleControlStatusType
			MAX-ACCESS read-only
			STATUS current
			DESCRIPTION
				"The status of a user command."
			::= { sleArpControl 2 }

		
		-- 1.3.6.1.4.1.6296.101.11.3.2.3
		sleArpControlTimer OBJECT-TYPE
			SYNTAX Gauge32
			MAX-ACCESS read-write
			STATUS current
			DESCRIPTION
				"The maximum wait time for the manager for a long running user command."
			::= { sleArpControl 3 }

		
		-- 1.3.6.1.4.1.6296.101.11.3.2.4
		sleArpControlTimeStamp OBJECT-TYPE
			SYNTAX SleControlRequestResultType
			MAX-ACCESS read-only
			STATUS current
			DESCRIPTION
				"The time stamp of the last command (end of command)."
			::= { sleArpControl 4 }

		
		-- 1.3.6.1.4.1.6296.101.11.3.2.5
		sleArpControlReqResult OBJECT-TYPE
			SYNTAX TimeTicks
			MAX-ACCESS read-only
			STATUS current
			DESCRIPTION
				"The result of the last user command."
			::= { sleArpControl 5 }

		
		-- 1.3.6.1.4.1.6296.101.11.3.2.6
		sleArpControlNetIfIndex OBJECT-TYPE
			SYNTAX Integer32 (0..4096)
			MAX-ACCESS read-write
			STATUS current
			DESCRIPTION
				"Network interface index."
			::= { sleArpControl 6 }

		
		-- 1.3.6.1.4.1.6296.101.11.3.2.7
		sleArpControlIpAddress OBJECT-TYPE
			SYNTAX IpAddress
			MAX-ACCESS read-write
			STATUS current
			DESCRIPTION
				"The NetworkAddress (e.g., the IP address) corresponding 
				to the media-dependent `physical' address."
			::= { sleArpControl 7 }

		
		-- 1.3.6.1.4.1.6296.101.11.3.2.8
		sleArpControlPhyAddress OBJECT-TYPE
			SYNTAX MacAddress
			MAX-ACCESS read-write
			STATUS current
			DESCRIPTION
				"The media-dependent `physical' address."
			::= { sleArpControl 8 }

		
		-- 1.3.6.1.4.1.6296.101.11.3.2.9
		sleArpControlState OBJECT-TYPE
			SYNTAX INTEGER
				{
				static(0),
				dynamic(1)
				}
			MAX-ACCESS read-write
			STATUS current
			DESCRIPTION
				"Arp entry's currently status."
			::= { sleArpControl 9 }

		
		-- 1.3.6.1.4.1.6296.101.11.3.2.10
		sleArpControlMask OBJECT-TYPE
			SYNTAX INTEGER (0..32)
			MAX-ACCESS read-write
			STATUS current
			DESCRIPTION
				"Description."
			::= { sleArpControl 10 }

		
		-- 1.3.6.1.4.1.6296.101.11.3.3
		sleArpNotification OBJECT IDENTIFIER ::= { sleArp 3 }

		
		-- 1.3.6.1.4.1.6296.101.11.3.3.1
		sleArpEntryCreated NOTIFICATION-TYPE
			OBJECTS { sleArpControlRequest, sleArpControlTimeStamp, sleArpControlReqResult, sleArpPhyAddress }
			STATUS current
			DESCRIPTION 
				"createArpEntry."
			::= { sleArpNotification 1 }

		
		-- 1.3.6.1.4.1.6296.101.11.3.3.2
		sleArpEntryDestroyed NOTIFICATION-TYPE
			OBJECTS { sleArpControlRequest, sleArpControlTimeStamp, sleArpControlReqResult, sleArpPhyAddress }
			STATUS current
			DESCRIPTION 
				"destroyArpEntry."
			::= { sleArpNotification 2 }

		
		-- 1.3.6.1.4.1.6296.101.11.3.3.3
		sleArpTableCleared NOTIFICATION-TYPE
			OBJECTS { sleArpControlRequest, sleArpControlTimeStamp, sleArpControlReqResult, sleArpState }
			STATUS current
			DESCRIPTION 
				"clearArpTable.
				 In this notification PDU, key of sleArpState 
				 is ifindex.0.0.0.0."
			::= { sleArpNotification 3 }

		
		-- 1.3.6.1.4.1.6296.101.11.3.3.4
		sleArpTableClearedByAddr NOTIFICATION-TYPE
			OBJECTS { sleArpControlRequest, sleArpControlTimeStamp, sleArpControlReqResult, sleArpControlIpAddress, sleArpControlMask, 
				sleArpControlState }
			STATUS current
			DESCRIPTION 
				"clearArpTableByAddr"
			::= { sleArpNotification 4 }

		
		-- 1.3.6.1.4.1.6296.101.11.4
		sleRoute OBJECT IDENTIFIER ::= { sleNetwork 4 }

		
		-- 1.3.6.1.4.1.6296.101.11.4.1
		sleRouteTable OBJECT-TYPE
			SYNTAX SEQUENCE OF SleRouteEntry
			MAX-ACCESS not-accessible
			STATUS current
			DESCRIPTION
				"Description."
			::= { sleRoute 1 }

		
		-- 1.3.6.1.4.1.6296.101.11.4.1.1
		sleRouteEntry OBJECT-TYPE
			SYNTAX SleRouteEntry
			MAX-ACCESS not-accessible
			STATUS current
			DESCRIPTION
				"Description."
			INDEX { sleRouteDstAddress, sleRouteDstMask, sleRouteGateway, sleRouteInterface }
			::= { sleRouteTable 1 }

		
		SleRouteEntry ::=
			SEQUENCE { 
				sleRouteDstAddress
					IpAddress,
				sleRouteDstMask
					INTEGER,
				sleRouteGateway
					IpAddress,
				sleRouteInterface
					INTEGER,
				sleRouteType
					INTEGER,
				sleRouteProto
					INTEGER,
				sleRouteMetric
					INTEGER,
				sleRouteActive
					INTEGER,
				sleRouteBindingSrcAddr
					IpAddress,
				sleRouteDistance
					INTEGER,
				sleRouteSubtype
					INTEGER,
				sleRouteNexthopStatus
					BITS,
				sleRouteRibStatus
					BITS
			 }

		-- 1.3.6.1.4.1.6296.101.11.4.1.1.1
		sleRouteDstAddress OBJECT-TYPE
			SYNTAX IpAddress
			MAX-ACCESS read-only
			STATUS current
			DESCRIPTION
				"The destination IP address of this route. An entry with a value of 0.0.0.0 is considered a default route. Multiple routes to a single destination can appear in the table, but access to such multiple entries is dependent on the table-access mechanisms defined by the network management protocol in use."
			::= { sleRouteEntry 1 }

		
		-- 1.3.6.1.4.1.6296.101.11.4.1.1.2
		sleRouteDstMask OBJECT-TYPE
			SYNTAX INTEGER (0..32)
			MAX-ACCESS read-only
			STATUS current
			DESCRIPTION
				"Indicate the mask to be logical-ANDed with the destination address before being compared to the value in the sleRouteDstAddress field. For those systems that do not support arbitrary subnet masks, an agent constructs the value of the sleRouteDstMask by determining whether the value of the correspondent sleRouteDstAddress field belong to a class-A, B, or C network. If the value of the sleRouteDstAddress is 0.0.0.0 (a default route), then the mask value is also 0.0.0.0. It should be noted that all IP routing subsystems implicitly use this mechanism."
			::= { sleRouteEntry 2 }

		
		-- 1.3.6.1.4.1.6296.101.11.4.1.1.3
		sleRouteGateway OBJECT-TYPE
			SYNTAX IpAddress
			MAX-ACCESS read-only
			STATUS current
			DESCRIPTION
				"The Gateway IP Address.
				0.0.0.0/0 : indicate default gateway or invalid"
			::= { sleRouteEntry 3 }

		
		-- 1.3.6.1.4.1.6296.101.11.4.1.1.4
		sleRouteInterface OBJECT-TYPE
			SYNTAX INTEGER (0..4097)
			MAX-ACCESS read-only
			STATUS current
			DESCRIPTION
				"The index value which uniquely identifies 
				the local interface through 
				which the next hop of this route 
				should be reached. 
				The interface identified by a particular 
				value of this index is the same interface 
				as identified by the same value of 
				sleNetIfIndex.
				
				Network interface index
				0: invalid
				1..4094: VLAN
				4095: management
				4096: loopback
				4097: NULL device
				"
			::= { sleRouteEntry 4 }

		
		-- 1.3.6.1.4.1.6296.101.11.4.1.1.5
		sleRouteType OBJECT-TYPE
			SYNTAX INTEGER
				{
				other(1),
				invalid(2),
				direct(3),
				indirect(4)
				}
			MAX-ACCESS read-write
			STATUS current
			DESCRIPTION
				"The type of route. Note that the values direct and indirect refer to the notion of direct and indirect routing in the IP architecture.
				Setting this object to the value invalid has the effect of invalidating the corresponding entry in the sleRouteTable object. That is, it effectively dissasociates the destination identified with said entry from the route identified with said entry. It is an implementation-specific matter as to whether the agent removes an invalidated entry from the table. Accordingly, management stations must be prepared to receive tabular information from agents that corresponds to entries not currently in use. Proper interpretation of such entries requires examination of the relevant sleRouteType object."
			::= { sleRouteEntry 5 }

		
		-- 1.3.6.1.4.1.6296.101.11.4.1.1.6
		sleRouteProto OBJECT-TYPE
			SYNTAX INTEGER
				{
				other(1),
				localDirect(2),
				netmgmtStatic(3),
				icmp(4),
				egp(5),
				ggp(6),
				hello(7),
				rip(8),
				isIs(9),
				esIs(10),
				ciscoIgrp(11),
				bbnSpfIgp(12),
				ospf(13),
				bgp(14),
				idpr(15),
				ciscoEigrp(16),
				dhcp(17)
				}
			MAX-ACCESS read-only
			STATUS current
			DESCRIPTION
				"The routing mechanism via which this route was learned. Inclusion of values for gateway routing protocols is not intended to imply that hosts should support those protocols."
			::= { sleRouteEntry 6 }

		
		-- 1.3.6.1.4.1.6296.101.11.4.1.1.7
		sleRouteMetric OBJECT-TYPE
			SYNTAX INTEGER (-1..255)
			MAX-ACCESS read-write
			STATUS current
			DESCRIPTION
				"The primary routing metric for this route.
				The semantics of this metric are determined 
				by the routing-protocol specified 
				in the route's sleRouteProto value. 
				If this metric is not used, 
				its value should be set to -1."
			::= { sleRouteEntry 7 }

		
		-- 1.3.6.1.4.1.6296.101.11.4.1.1.8
		sleRouteActive OBJECT-TYPE
			SYNTAX INTEGER
				{
				inactive(0),
				active(1)
				}
			MAX-ACCESS read-write
			STATUS current
			DESCRIPTION
				"The active status for this routing entry."
			::= { sleRouteEntry 8 }

		
		-- 1.3.6.1.4.1.6296.101.11.4.1.1.9
		sleRouteBindingSrcAddr OBJECT-TYPE
			SYNTAX IpAddress
			MAX-ACCESS read-only
			STATUS current
			DESCRIPTION
				"The binding source IP Address for this route."
			::= { sleRouteEntry 9 }

		
		-- 1.3.6.1.4.1.6296.101.11.4.1.1.10
		sleRouteDistance OBJECT-TYPE
			SYNTAX INTEGER (1..255)
			MAX-ACCESS read-write
			STATUS current
			DESCRIPTION
				"The Distance value for this route."
			::= { sleRouteEntry 10 }

		
		-- 1.3.6.1.4.1.6296.101.11.4.1.1.11
		sleRouteSubtype OBJECT-TYPE
			SYNTAX INTEGER
				{
				unknown(0),
				ospf_ia(1),
				ospf_nssa_1(2),
				ospf_nssa_2(3),
				ospf_external_1(4),
				ospf_external_2(5),
				isis_l1(8),
				isis_l2(9),
				isis_ia(10),
				bgp_mpls(11)
				}
			MAX-ACCESS read-only
			STATUS current
			DESCRIPTION
				"The subtype of this route."
			::= { sleRouteEntry 11 }

		
		-- 1.3.6.1.4.1.6296.101.11.4.1.1.12
		sleRouteNexthopStatus OBJECT-TYPE
			SYNTAX BITS
				{
				active(0),
				fib(1),
				recursive(2)
				}
			MAX-ACCESS read-only
			STATUS current
			DESCRIPTION
				"The nexthop status of this route."
			::= { sleRouteEntry 12 }

		
		-- 1.3.6.1.4.1.6296.101.11.4.1.1.13
		sleRouteRibStatus OBJECT-TYPE
			SYNTAX BITS
				{
				internal(0),
				selfroute(1),
				blackhole(2),
				nonfib(3),
				selected(4),
				changed(5),
				static(6),
				stale(7)
				}
			MAX-ACCESS read-only
			STATUS current
			DESCRIPTION
				"The rib status for this route."
			::= { sleRouteEntry 13 }

		
		-- 1.3.6.1.4.1.6296.101.11.4.2
		sleRouteControl OBJECT IDENTIFIER ::= { sleRoute 2 }

		
		-- 1.3.6.1.4.1.6296.101.11.4.2.1
		sleRouteControlRequest OBJECT-TYPE
			SYNTAX INTEGER
				{
				createStaticRoute(1),
				destroyStaticRoute(2),
				setStaticRouteProfile(3)
				}
			MAX-ACCESS read-write
			STATUS current
			DESCRIPTION
				"The request of a user command."
			::= { sleRouteControl 1 }

		
		-- 1.3.6.1.4.1.6296.101.11.4.2.2
		sleRouteControlStatus OBJECT-TYPE
			SYNTAX SleControlStatusType
			MAX-ACCESS read-only
			STATUS current
			DESCRIPTION
				"The status of a user command."
			::= { sleRouteControl 2 }

		
		-- 1.3.6.1.4.1.6296.101.11.4.2.3
		sleRouteControlTimer OBJECT-TYPE
			SYNTAX Gauge32
			MAX-ACCESS read-write
			STATUS current
			DESCRIPTION
				"The maximum wait time for the manager for a long running user command."
			::= { sleRouteControl 3 }

		
		-- 1.3.6.1.4.1.6296.101.11.4.2.4
		sleRouteControlTimeStamp OBJECT-TYPE
			SYNTAX SleControlRequestResultType
			MAX-ACCESS read-only
			STATUS current
			DESCRIPTION
				"The result of the last user command."
			::= { sleRouteControl 4 }

		
		-- 1.3.6.1.4.1.6296.101.11.4.2.5
		sleRouteControlReqResult OBJECT-TYPE
			SYNTAX TimeTicks
			MAX-ACCESS read-only
			STATUS current
			DESCRIPTION
				"The time stamp of the last command (end of command)."
			::= { sleRouteControl 5 }

		
		-- 1.3.6.1.4.1.6296.101.11.4.2.6
		sleRouteControlDstAddress OBJECT-TYPE
			SYNTAX IpAddress
			MAX-ACCESS read-write
			STATUS current
			DESCRIPTION
				"Description."
			::= { sleRouteControl 6 }

		
		-- 1.3.6.1.4.1.6296.101.11.4.2.7
		sleRouteControlDstMask OBJECT-TYPE
			SYNTAX INTEGER (0..32)
			MAX-ACCESS read-write
			STATUS current
			DESCRIPTION
				"Description."
			::= { sleRouteControl 7 }

		
		-- 1.3.6.1.4.1.6296.101.11.4.2.8
		sleRouteControlGateway OBJECT-TYPE
			SYNTAX IpAddress
			MAX-ACCESS read-write
			STATUS current
			DESCRIPTION
				"Description."
			::= { sleRouteControl 8 }

		
		-- 1.3.6.1.4.1.6296.101.11.4.2.9
		sleRouteControlInterface OBJECT-TYPE
			SYNTAX INTEGER (0..4097)
			MAX-ACCESS read-write
			STATUS current
			DESCRIPTION
				"Network interface index
				0: invalid
				1..4094: VLAN
				4095: management
				4096: loopback
				4097: NULL device"
			::= { sleRouteControl 9 }

		
		-- 1.3.6.1.4.1.6296.101.11.4.2.10
		sleRouteControlBindingSrcAddr OBJECT-TYPE
			SYNTAX IpAddress
			MAX-ACCESS read-write
			STATUS current
			DESCRIPTION
				"Description."
			::= { sleRouteControl 10 }

		
		-- 1.3.6.1.4.1.6296.101.11.4.2.11
		sleRouteControlDistance OBJECT-TYPE
			SYNTAX INTEGER (1..255)
			MAX-ACCESS read-write
			STATUS current
			DESCRIPTION
				"Description."
			DEFVAL { 1 }
			::= { sleRouteControl 11 }

		
		-- 1.3.6.1.4.1.6296.101.11.4.3
		sleRouteNotification OBJECT IDENTIFIER ::= { sleRoute 3 }

		
		-- 1.3.6.1.4.1.6296.101.11.4.3.1
		sleRouteStaticCreated NOTIFICATION-TYPE
			OBJECTS { sleRouteBindingSrcAddr, sleRouteDistance, sleRouteControlRequest, sleRouteControlTimeStamp, sleRouteControlReqResult
				 }
			STATUS current
			DESCRIPTION 
				"Description."
			::= { sleRouteNotification 1 }

		
		-- 1.3.6.1.4.1.6296.101.11.4.3.2
		sleRouteStaticDestroyed NOTIFICATION-TYPE
			OBJECTS { sleRouteInterface, sleRouteControlRequest, sleRouteControlTimeStamp, sleRouteControlReqResult }
			STATUS current
			DESCRIPTION 
				"Description."
			::= { sleRouteNotification 2 }

		
		-- 1.3.6.1.4.1.6296.101.11.4.3.3
		sleRouteStaticProfileChanged NOTIFICATION-TYPE
			OBJECTS { sleRouteBindingSrcAddr, sleRouteDistance, sleRouteControlRequest, sleRouteControlTimeStamp, sleRouteControlReqResult
				 }
			STATUS current
			DESCRIPTION 
				"Description."
			::= { sleRouteNotification 3 }

		
		-- 1.3.6.1.4.1.6296.101.11.5
		sleDhcpClient OBJECT IDENTIFIER ::= { sleNetwork 5 }

		
		-- 1.3.6.1.4.1.6296.101.11.5.1
		sleDhcpClTable OBJECT-TYPE
			SYNTAX SEQUENCE OF SleDhcpClEntry
			MAX-ACCESS not-accessible
			STATUS current
			DESCRIPTION
				"Description."
			::= { sleDhcpClient 1 }

		
		-- 1.3.6.1.4.1.6296.101.11.5.1.1
		sleDhcpClEntry OBJECT-TYPE
			SYNTAX SleDhcpClEntry
			MAX-ACCESS not-accessible
			STATUS current
			DESCRIPTION
				"Description."
			INDEX { sleNetIfIndex }
			::= { sleDhcpClTable 1 }

		
		SleDhcpClEntry ::=
			SEQUENCE { 
				sleDhcpClMode
					INTEGER,
				sleDhcpClIpAddr
					IpAddress,
				sleDhcpClNetmask
					IpAddress,
				sleDhcpClGateway
					IpAddress,
				sleDhcpClDnsServer
					IpAddress,
				sleDhcpClServer
					IpAddress,
				sleDhcpClClientId
					OCTET STRING,
				sleDhcpClClientIdStyle
					INTEGER,
				sleDhcpClClassId
					OCTET STRING,
				sleDhcpClClassIdStyle
					INTEGER,
				sleDhcpClLeasetime
					Integer32,
				sleDhcpClState
					INTEGER
			 }

		-- 1.3.6.1.4.1.6296.101.11.5.1.1.1
		sleDhcpClMode OBJECT-TYPE
			SYNTAX INTEGER
				{
				disable(0),
				enable(1)
				}
			MAX-ACCESS read-only
			STATUS current
			DESCRIPTION
				"DHCP Client activity state in this interface."
			DEFVAL { disable }
			::= { sleDhcpClEntry 1 }

		
		-- 1.3.6.1.4.1.6296.101.11.5.1.1.2
		sleDhcpClIpAddr OBJECT-TYPE
			SYNTAX IpAddress
			MAX-ACCESS read-only
			STATUS current
			DESCRIPTION
				"The IP address acquired by DHCP Client active in this interface."
			::= { sleDhcpClEntry 2 }

		
		-- 1.3.6.1.4.1.6296.101.11.5.1.1.3
		sleDhcpClNetmask OBJECT-TYPE
			SYNTAX IpAddress
			MAX-ACCESS read-only
			STATUS current
			DESCRIPTION
				"The subnet mask associated with the IP address acquired by DHCP Client.  
				The value of the mask is an IP address with all the network 
				bits set to 1 and all the hosts bits set to 0."
			::= { sleDhcpClEntry 3 }

		
		-- 1.3.6.1.4.1.6296.101.11.5.1.1.4
		sleDhcpClGateway OBJECT-TYPE
			SYNTAX IpAddress
			MAX-ACCESS read-only
			STATUS current
			DESCRIPTION
				"The Gateway's IP address acquired by DHCP Client active in this interface."
			::= { sleDhcpClEntry 4 }

		
		-- 1.3.6.1.4.1.6296.101.11.5.1.1.5
		sleDhcpClDnsServer OBJECT-TYPE
			SYNTAX IpAddress
			MAX-ACCESS read-only
			STATUS current
			DESCRIPTION
				"The DNS server's IP address acquired by DHCP Client active in this interface."
			::= { sleDhcpClEntry 5 }

		
		-- 1.3.6.1.4.1.6296.101.11.5.1.1.6
		sleDhcpClServer OBJECT-TYPE
			SYNTAX IpAddress
			MAX-ACCESS read-only
			STATUS current
			DESCRIPTION
				"DHCP Server's IP address."
			::= { sleDhcpClEntry 6 }

		
		-- 1.3.6.1.4.1.6296.101.11.5.1.1.7
		sleDhcpClClientId OBJECT-TYPE
			SYNTAX OCTET STRING (SIZE (0..255))
			MAX-ACCESS read-only
			STATUS current
			DESCRIPTION
				"DHCP Client-identifier value.
				This is used by DHCP clients to specify their unique identifier.
				DHCP servers use this value to index their database of address bindings.
				This value is expected to be unique for all clients in an administrative domain."
			::= { sleDhcpClEntry 7 }

		
		-- 1.3.6.1.4.1.6296.101.11.5.1.1.8
		sleDhcpClClientIdStyle OBJECT-TYPE
			SYNTAX INTEGER
				{
				ascii(0),
				hex(1)
				}
			MAX-ACCESS read-only
			STATUS current
			DESCRIPTION
				"DHCP Client-identifier input style.
				0 : ascii string format
				1 : hexadecimal format"
			DEFVAL { ascii }
			::= { sleDhcpClEntry 8 }

		
		-- 1.3.6.1.4.1.6296.101.11.5.1.1.9
		sleDhcpClClassId OBJECT-TYPE
			SYNTAX OCTET STRING (SIZE (0..256))
			MAX-ACCESS read-only
			STATUS current
			DESCRIPTION
				"DHCP Class identifier value.
				This is used by DHCP clients to optionally identify the vendor 
				type and configuration of a DHCP client.
				The information is a string of n octets, interpreted by servers.
				Vendors may choose to define specific vendor class identifiers 
				to convey particular configuration or other identification 
				information about a client.
				For example, the identifier may encode the client's hardware configuration."
			::= { sleDhcpClEntry 9 }

		
		-- 1.3.6.1.4.1.6296.101.11.5.1.1.10
		sleDhcpClClassIdStyle OBJECT-TYPE
			SYNTAX INTEGER
				{
				ascii(0),
				hex(1)
				}
			MAX-ACCESS read-only
			STATUS current
			DESCRIPTION
				"DHCP Class identifier input style.
				0 : ascii string format
				1 : hexadecimal format"
			DEFVAL { ascii }
			::= { sleDhcpClEntry 10 }

		
		-- 1.3.6.1.4.1.6296.101.11.5.1.1.11
		sleDhcpClLeasetime OBJECT-TYPE
			SYNTAX Integer32 (120..2147483637)
			MAX-ACCESS read-only
			STATUS current
			DESCRIPTION
				"The leased time for IP address acquired by DHCP Client.
				 Default lease-time: 3600s"
			DEFVAL { 3600 }
			::= { sleDhcpClEntry 11 }

		
		-- 1.3.6.1.4.1.6296.101.11.5.1.1.12
		sleDhcpClState OBJECT-TYPE
			SYNTAX INTEGER
				{
				halt(0),
				init(1),
				request(3),
				bound(4),
				renew(5),
				rebind(6),
				nonactive(255)
				}
			MAX-ACCESS read-only
			STATUS current
			DESCRIPTION
				"The operating status of DHCP Client."
			DEFVAL { non-active }
			::= { sleDhcpClEntry 12 }

		
		-- 1.3.6.1.4.1.6296.101.11.5.2
		sleDhcpClControl OBJECT IDENTIFIER ::= { sleDhcpClient 2 }

		
		-- 1.3.6.1.4.1.6296.101.11.5.2.1
		sleDhcpClControlRequest OBJECT-TYPE
			SYNTAX INTEGER
				{
				setDhcpClMode(1),
				setDhcpClProfile(2),
				changeDhcpClState(3)
				}
			MAX-ACCESS read-write
			STATUS current
			DESCRIPTION
				"The request of a user command."
			::= { sleDhcpClControl 1 }

		
		-- 1.3.6.1.4.1.6296.101.11.5.2.2
		sleDhcpClControlStatus OBJECT-TYPE
			SYNTAX SleControlStatusType
			MAX-ACCESS read-only
			STATUS current
			DESCRIPTION
				"The status of a user command."
			::= { sleDhcpClControl 2 }

		
		-- 1.3.6.1.4.1.6296.101.11.5.2.3
		sleDhcpClControlTimer OBJECT-TYPE
			SYNTAX Gauge32
			MAX-ACCESS read-write
			STATUS current
			DESCRIPTION
				"The maximum wait time for the manager for a long running user command."
			::= { sleDhcpClControl 3 }

		
		-- 1.3.6.1.4.1.6296.101.11.5.2.4
		sleDhcpClControlTimeStamp OBJECT-TYPE
			SYNTAX SleControlRequestResultType
			MAX-ACCESS read-only
			STATUS current
			DESCRIPTION
				"The time stamp of the last command (end of command)."
			::= { sleDhcpClControl 4 }

		
		-- 1.3.6.1.4.1.6296.101.11.5.2.5
		sleDhcpClControlReqResult OBJECT-TYPE
			SYNTAX TimeTicks
			MAX-ACCESS read-only
			STATUS current
			DESCRIPTION
				"The result of the last user command."
			::= { sleDhcpClControl 5 }

		
		-- 1.3.6.1.4.1.6296.101.11.5.2.6
		sleDhcpClControlNetIfIndex OBJECT-TYPE
			SYNTAX Integer32 (1..4094)
			MAX-ACCESS read-write
			STATUS current
			DESCRIPTION
				"Network Interface Index."
			DEFVAL { 1 }
			::= { sleDhcpClControl 6 }

		
		-- 1.3.6.1.4.1.6296.101.11.5.2.7
		sleDhcpClControlMode OBJECT-TYPE
			SYNTAX INTEGER
				{
				disable(0),
				enable(1)
				}
			MAX-ACCESS read-write
			STATUS current
			DESCRIPTION
				"DHCP Client activity state in this interface."
			DEFVAL { disable }
			::= { sleDhcpClControl 7 }

		
		-- 1.3.6.1.4.1.6296.101.11.5.2.8
		sleDhcpClControlClientId OBJECT-TYPE
			SYNTAX OCTET STRING (SIZE (0..255))
			MAX-ACCESS read-write
			STATUS current
			DESCRIPTION
				"DHCP Client-identifier value.
				This is used by DHCP clients to specify their unique identifier.
				DHCP servers use this value to index their database of address bindings.
				This value is expected to be unique for all clients in an administrative domain."
			::= { sleDhcpClControl 8 }

		
		-- 1.3.6.1.4.1.6296.101.11.5.2.9
		sleDhcpClControlClientIdStyle OBJECT-TYPE
			SYNTAX INTEGER
				{
				ascii(0),
				hex(1)
				}
			MAX-ACCESS read-write
			STATUS current
			DESCRIPTION
				"DHCP Client-identifier input style.
				0 : ascii string format
				1 : hexadecimal format"
			DEFVAL { ascii }
			::= { sleDhcpClControl 9 }

		
		-- 1.3.6.1.4.1.6296.101.11.5.2.10
		sleDhcpClControlClassId OBJECT-TYPE
			SYNTAX OCTET STRING (SIZE (0..255))
			MAX-ACCESS read-write
			STATUS current
			DESCRIPTION
				"DHCP Class identifier value.
				This is used by DHCP clients to optionally identify the vendor 
				type and configuration of a DHCP client.
				The information is a string of n octets, interpreted by servers.
				Vendors may choose to define specific vendor class identifiers 
				to convey particular configuration or other identification 
				information about a client.
				For example, the identifier may encode the client's hardware configuration."
			::= { sleDhcpClControl 10 }

		
		-- 1.3.6.1.4.1.6296.101.11.5.2.11
		sleDhcpClControlClassIdStyle OBJECT-TYPE
			SYNTAX INTEGER
				{
				ascii(0),
				hex(1)
				}
			MAX-ACCESS read-write
			STATUS current
			DESCRIPTION
				"DHCP Class identifier input style.
				0 : ascii string format
				1 : hexadecimal format"
			DEFVAL { ascii }
			::= { sleDhcpClControl 11 }

		
		-- 1.3.6.1.4.1.6296.101.11.5.2.12
		sleDhcpClControlLeasetime OBJECT-TYPE
			SYNTAX Integer32 (120..2147483637)
			MAX-ACCESS read-write
			STATUS current
			DESCRIPTION
				"The leased time for IP address acquired by DHCP Client.
				 Default lease-time: 3600s"
			DEFVAL { 3600 }
			::= { sleDhcpClControl 12 }

		
		-- 1.3.6.1.4.1.6296.101.11.5.2.13
		sleDhcpClControlUpdateIP OBJECT-TYPE
			SYNTAX INTEGER
				{
				remain(0),
				renew(1),
				release(2)
				}
			MAX-ACCESS read-write
			STATUS current
			DESCRIPTION
				"Update DHCP client operating status.
				0 : default
				1 : renew
				2 : release
				"
			DEFVAL { remain }
			::= { sleDhcpClControl 13 }

		
		-- 1.3.6.1.4.1.6296.101.11.5.4
		sleDhcpClNotification OBJECT IDENTIFIER ::= { sleDhcpClient 4 }

		
		-- 1.3.6.1.4.1.6296.101.11.5.4.1
		sleDhcpClModeChanged NOTIFICATION-TYPE
			OBJECTS { sleDhcpClControlRequest, sleDhcpClControlTimeStamp, sleDhcpClControlReqResult, sleDhcpClMode }
			STATUS current
			DESCRIPTION 
				"setDhcpClMode."
			::= { sleDhcpClNotification 1 }

		
		-- 1.3.6.1.4.1.6296.101.11.5.4.2
		sleDhcpClProfileChanged NOTIFICATION-TYPE
			OBJECTS { sleDhcpClControlRequest, sleDhcpClControlTimeStamp, sleDhcpClControlReqResult, sleDhcpClClientId, sleDhcpClClientIdStyle, 
				sleDhcpClClassId, sleDhcpClClassIdStyle, sleDhcpClLeasetime }
			STATUS current
			DESCRIPTION 
				"setDhcpClProfile."
			::= { sleDhcpClNotification 2 }

		
		-- 1.3.6.1.4.1.6296.101.11.5.4.3
		sleDhcpClStateChanged NOTIFICATION-TYPE
			OBJECTS { sleDhcpClControlRequest, sleDhcpClControlTimeStamp, sleDhcpClControlReqResult, sleDhcpClState }
			STATUS current
			DESCRIPTION 
				"ChangeDhcpClState."
			::= { sleDhcpClNotification 3 }

		
		-- 1.3.6.1.4.1.6296.101.11.6
		sleV2DhcpClient OBJECT IDENTIFIER ::= { sleNetwork 6 }

		
		-- 1.3.6.1.4.1.6296.101.11.7
		sleNetworkBase OBJECT IDENTIFIER ::= { sleNetwork 7 }

		
		-- 1.3.6.1.4.1.6296.101.11.7.1
		sleNetworkBaseInfo OBJECT IDENTIFIER ::= { sleNetworkBase 1 }

		
		-- 1.3.6.1.4.1.6296.101.11.7.1.1
		sleNetworkArpAgingTime OBJECT-TYPE
			SYNTAX INTEGER (10..2147483637)
			MAX-ACCESS read-only
			STATUS current
			DESCRIPTION
				"System Arp Aging Time"
			::= { sleNetworkBaseInfo 1 }

		
		-- 1.3.6.1.4.1.6296.101.11.7.2
		sleNetworkBaseControl OBJECT IDENTIFIER ::= { sleNetworkBase 2 }

		
		-- 1.3.6.1.4.1.6296.101.11.7.2.1
		sleNetworkControlRequest OBJECT-TYPE
			SYNTAX INTEGER { setArpProfile(1) }
			MAX-ACCESS read-write
			STATUS current
			DESCRIPTION
				"Description."
			::= { sleNetworkBaseControl 1 }

		
		-- 1.3.6.1.4.1.6296.101.11.7.2.2
		sleNetworkControlStatus OBJECT-TYPE
			SYNTAX SleControlStatusType
			MAX-ACCESS read-only
			STATUS current
			DESCRIPTION
				"Description."
			::= { sleNetworkBaseControl 2 }

		
		-- 1.3.6.1.4.1.6296.101.11.7.2.3
		sleNetworkControlTimer OBJECT-TYPE
			SYNTAX Gauge32
			MAX-ACCESS read-write
			STATUS current
			DESCRIPTION
				"Description."
			::= { sleNetworkBaseControl 3 }

		
		-- 1.3.6.1.4.1.6296.101.11.7.2.4
		sleNetworkControlTimeStamp OBJECT-TYPE
			SYNTAX TimeTicks
			MAX-ACCESS read-only
			STATUS current
			DESCRIPTION
				"Description."
			::= { sleNetworkBaseControl 4 }

		
		-- 1.3.6.1.4.1.6296.101.11.7.2.5
		sleNetworkControlReqResult OBJECT-TYPE
			SYNTAX SleControlRequestResultType
			MAX-ACCESS read-only
			STATUS current
			DESCRIPTION
				"Description."
			::= { sleNetworkBaseControl 5 }

		
		-- 1.3.6.1.4.1.6296.101.11.7.2.6
		sleNetworkControlArpAgingTime OBJECT-TYPE
			SYNTAX INTEGER (10..2147483637)
			MAX-ACCESS read-write
			STATUS current
			DESCRIPTION
				"Description."
			::= { sleNetworkBaseControl 6 }

		
		-- 1.3.6.1.4.1.6296.101.11.7.3
		sleNetworkBaseNotification OBJECT IDENTIFIER ::= { sleNetworkBase 3 }

		
		-- 1.3.6.1.4.1.6296.101.11.7.3.1
		sleNetworkArpProfileChanged NOTIFICATION-TYPE
			OBJECTS { sleNetworkControlRequest, sleNetworkControlReqResult, sleNetworkControlTimeStamp, sleNetworkArpAgingTime }
			STATUS current
			DESCRIPTION 
				"Description."
			::= { sleNetworkBaseNotification 1 }

		
		-- 1.3.6.1.4.1.6296.101.11.8
		sleNetworkGroup OBJECT-GROUP
			OBJECTS { sleNetIfIndex, sleNetIfName, sleNetIfDescription, sleNetIfTableIndex, sleNetIfAdminState, 
				sleNetIfOperState, sleNetIfMulticast, sleNetIfControlRequest, sleNetIfControlStatus, sleNetIfControlTimer, 
				sleNetIfControlTimeStamp, sleNetIfControlReqResult, sleNetIfControlIndex, sleNetIfControlDescription, sleNetIfControlAdminState, 
				sleNetIfControlMulticast, sleIpAddrValue, sleIpAddrMask, sleIpAddrBcast, sleIpAddrControlRequest, 
				sleIpAddrControlStatus, sleIpAddrControlTimer, sleIpAddrControlTimeStamp, sleIpAddrControlReqResult, sleIpAddrControlNetIfIndex, 
				sleIpAddrControlValue, sleIpAddrControlMask, sleArpIpAddress, sleArpPhyAddress, sleArpPortIndex, 
				sleArpHwType, sleArpControlRequest, sleArpControlStatus, sleArpControlTimer, sleArpControlTimeStamp, 
				sleArpControlReqResult, sleArpControlIpAddress, sleArpControlPhyAddress, sleRouteDstAddress, sleRouteDstMask, 
				sleRouteGateway, sleRouteInterface, sleRouteType, sleRouteProto, sleRouteMetric, 
				sleRouteActive, sleRouteBindingSrcAddr, sleRouteDistance, sleRouteControlRequest, sleRouteControlStatus, 
				sleRouteControlTimer, sleRouteControlTimeStamp, sleRouteControlReqResult, sleRouteControlDstAddress, sleRouteControlDstMask, 
				sleRouteControlGateway, sleRouteControlInterface, sleRouteControlBindingSrcAddr, sleRouteControlDistance, sleDhcpClIpAddr, 
				sleDhcpClState, sleDhcpClControlRequest, sleDhcpClControlStatus, sleDhcpClControlTimer, sleDhcpClControlTimeStamp, 
				sleDhcpClControlReqResult, sleDhcpClControlUpdateIP, sleNetIfRegState, sleNetIfMtu, sleNetIfIpSetMode, 
				sleNetIfIpMartianFilter, sleNetIfControlRegState, sleNetIfControlMtu, sleNetIfControlIpMartianFilter, sleIpAddrFlag, 
				sleIpAddrScope, sleIpAddrControlFlag, sleIpAddrControlScope, sleArpState, sleArpHwUsed, 
				sleArpUsedTime, sleArpControlNetIfIndex, sleArpControlState, sleArpControlMask, sleRouteSubtype, 
				sleRouteNexthopStatus, sleRouteRibStatus, sleNetworkArpAgingTime, sleNetworkControlRequest, sleNetworkControlStatus, 
				sleNetworkControlTimer, sleNetworkControlReqResult, sleNetworkControlTimeStamp, sleNetworkControlArpAgingTime, sleDhcpClControlNetIfIndex, 
				sleDhcpClMode, sleDhcpClNetmask, sleDhcpClGateway, sleDhcpClDnsServer, sleDhcpClServer, 
				sleDhcpClClientId, sleDhcpClClientIdStyle, sleDhcpClClassId, sleDhcpClClassIdStyle, sleDhcpClLeasetime, 
				sleDhcpClControlMode, sleDhcpClControlClientId, sleDhcpClControlClientIdStyle, sleDhcpClControlClassId, sleDhcpClControlClassIdStyle, 
				sleDhcpClControlLeasetime }
			STATUS current
			DESCRIPTION 
				"Description."
			::= { sleNetwork 8 }

		
		-- 1.3.6.1.4.1.6296.101.11.9
		sleNetworkNotificationGroup NOTIFICATION-GROUP
			NOTIFICATIONS { sleNetIfProfileChanged, sleIpAddressCreated, sleIpAddressDestroyed, sleArpEntryCreated, sleArpEntryDestroyed, 
				sleArpTableCleared, sleRouteStaticCreated, sleRouteStaticDestroyed, sleRouteStaticProfileChanged, sleDhcpClModeChanged, 
				sleDhcpClProfileChanged, sleDhcpClStateChanged, sleNetIfRegStateChanged, sleNetIfIpMartianFilterChanged, sleArpTableClearedByAddr, 
				sleNetworkArpProfileChanged }
			STATUS current
			DESCRIPTION 
				"Description."
			::= { sleNetwork 9 }

		
	
	END

--
-- SLE-NETWORK-MIB.my
--
