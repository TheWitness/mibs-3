--
-- she-topology-mib.mib
-- MIB generated by MG-SOFT Visual MIB Builder Version 5.0  Build 250
-- Monday, October 16, 2006 at 10:26:48
--

	DS-SHE-TOPOLOGY-MIB DEFINITIONS ::= BEGIN
 
		IMPORTS
			she			
				FROM AN-MIB
			dsShe
				FROM DASAN-SMI							
			PhysicalIndex			
				FROM ENTITY-MIB			
			AddressFamilyNumbers			
				FROM IANA-ADDRESS-FAMILY-NUMBERS-MIB			
			lldpLocPortNum, lldpRemIndex			
				FROM LLDP-MIB			
			PtopoChassisIdType, PtopoChassisId, PtopoPortIdType, PtopoPortId, PtopoGenAddr			
				FROM PTOPO-MIB			
			TimeFilter			
				FROM RMON2-MIB			
			SheControlStatusType			
				FROM DS-SHE-TC-MIB			
			OBJECT-GROUP, MODULE-COMPLIANCE, NOTIFICATION-GROUP			
				FROM SNMPv2-CONF			
			IpAddress, Integer32, Unsigned32, OBJECT-TYPE, MODULE-IDENTITY, 
			NOTIFICATION-TYPE			
				FROM SNMPv2-SMI			
			TruthValue, TEXTUAL-CONVENTION			
				FROM SNMPv2-TC;
	
	
--  1.3.6.1.4.1.231.7.1.2.2.1.17
		sheTopology MODULE-IDENTITY 
			LAST-UPDATED "200610161100Z"		-- October 16, 2006 at 11:00 GMT
			ORGANIZATION 
				"Siemens AG"
			CONTACT-INFO 
				"jmkim@dasannetworks.com"
			DESCRIPTION 
				" The MIB module is the proprietary extension of PTOPO-MIB and LLDP-MIB 
				defining a control group. "
			REVISION "200608111054Z"		-- August 11, 2006 at 10:54 GMT
			DESCRIPTION 
				"Take over by Gerd Barchmann for R2.5."
			REVISION "200609131522Z"		-- September 13, 2006 at 15:22 GMT
			DESCRIPTION 
				"Small correction after review."
			REVISION "200610161011Z"		-- October 16, 2006 at 10:11 GMT
			DESCRIPTION 
				"Merge update for new SHE R2.3 MIB-Version 154."
			::= { dsShe 17 }

		
	
--
-- Textual conventions
--
	
-- GENERAL VALUES FOR USER COMMAND HANDLING
		SheTopologyControlRequestType ::= TEXTUAL-CONVENTION
			STATUS current
			DESCRIPTION 
				"The type for SHE-TOPOLOGY MIB(LLDP & PTOPO) control commands."
			SYNTAX INTEGER
				{
				configureMessageTxInterval(1),
				configureMessageTxHoldMultiplier(2),
				configureReinitDelay(3),
				configureTxDelay(4),
				configureNotificationInterval(5),
				configurePort(6),
				addManagementAddress(7),
				deleteManagementAddress(8),
				clearStatistics(9),
				configureTrapInterval(10),
				configureMaxHoldTime(11),
				createConnectionEntry(12),
				deleteConnectionEntry(13),
				modifyConnectionEntry(14),
				configureLLDPMulticastAddress(15)
				}

--  RETURN VALUES
		SheTopologyControlRequestResultType ::= TEXTUAL-CONVENTION
			STATUS current
			DESCRIPTION 
				"The result type for Topology control commands."
			SYNTAX INTEGER
				{
				noRequest(1),
				commExecStarted(30),
				paramFaulty(31),
				requestBusy(32),
				setDataFailed(34),
				aswTimeout(35),
				commandFailed(36),
				commandSucceeded(37)
				}

--  ADMINSTATUS VALUES FOR LLDP-MIB
		SheTopologyControlAdminStatus ::= TEXTUAL-CONVENTION
			STATUS current
			DESCRIPTION 
				"The type for LLDP-MIB AdminStatus control."
			SYNTAX INTEGER
				{
				txOnly(1),
				rxOnly(2),
				txAndRx(3),
				disable(4)
				}

--  TLVS TX ENABLE VALUES FOR LLDP-MIB
		SheTopologyControlTLVsTxEnable ::= TEXTUAL-CONVENTION
			STATUS current
			DESCRIPTION 
				"The type for LLDP-MIB TLVs Tx Enable Status control."
			SYNTAX BITS
				{
				portDesc(0),
				sysName(1),
				sysDesc(2),
				sysCap(3)
				}

--  MULTICAST ADDRESS VALUES FOR LLDP-MIB
		SheTopologyControlMulticastAddress ::= TEXTUAL-CONVENTION
			STATUS current
			DESCRIPTION 
				"The type for Slow Multicast Address that LLDP packets uses control."
			SYNTAX INTEGER
				{
				ieee8021xPAEAddress(1),
				ieee8021abLLDPMulticastAddress(2)
				}

	
--
-- Node definitions
--
	
-- MIB contains the following groups
-- 1.3.6.1.4.1.231.7.1.2.2.1.17.1
		sheTopologyConfigurationObjects OBJECT IDENTIFIER ::= { sheTopology 1 }

		
--  -----------------------------------------------------------------
-- SHE TOPOLOGY Control group(LLDP)
-- ----------------------------------------------------------------- 
-- 1.3.6.1.4.1.231.7.1.2.2.1.17.1.1
		sheLldpControl OBJECT IDENTIFIER ::= { sheTopologyConfigurationObjects 1 }

		
--  1.3.6.1.4.1.231.7.1.2.2.1.17.1.1.1
		sheLldpControlRequest OBJECT-TYPE
			SYNTAX SheTopologyControlRequestType
			MAX-ACCESS read-write
			STATUS current
			DESCRIPTION
				" This attribute identifies the control commands.
				
				configureMessageTxInterval: This object is configured interval to transmit LLDPDU.
				
				configureMessageTxHoldMultiplier: This object is configured actual time-to-live value used in LLDP frames
				
				configureReinitDelay: This object indicates the delay until re-initialization will be attempted.
				
				configureTxDelay: This object indicates the delay between successive LLDP frame transmission.
				
				configureNotificationInterval: This objects controls the transmission of LLDP notification.
				
				changedPort: This objects controls attributes of local port.
				
				addManagemnetAddress: This objects control the addition of management address to transmit.
				
				deleteManagemnetAddress: This objects control the deletion of management address to transmit.
				
				clearStatistics: This object is cleared all counters as to statictics of LLDP-MIB.
				
				configureLLDPMulticastAddress: This objects controls LLDP's Slow Multicast Address.
				
				Notifications : changedMessageTxInterval / changedMessageTxHoldMultiplier / 
						changedReinitDelay / changedTxDelay / changedNotificationInterval / 
						changedPort, clearedLldpStatistics / changedLLDPMulticastAddress"
			::= { sheLldpControl 1 }

		
--  1.3.6.1.4.1.231.7.1.2.2.1.17.1.1.2
		sheLldpControlStatus OBJECT-TYPE
			SYNTAX SheControlStatusType
			MAX-ACCESS read-only
			STATUS current
			DESCRIPTION
				" The status of a control request. "
			::= { sheLldpControl 2 }

		
--  1.3.6.1.4.1.231.7.1.2.2.1.17.1.1.3
		sheLldpControlTimer OBJECT-TYPE
			SYNTAX Unsigned32
			MAX-ACCESS read-only
			STATUS current
			DESCRIPTION
				" The maximum wait time for the manager for command ending.
				For long running commands.
				The manager reads this value from the DSLAM. "
			::= { sheLldpControl 3 }

		
--  1.3.6.1.4.1.231.7.1.2.2.1.17.1.1.4
		sheLldpControlReqResult OBJECT-TYPE
			SYNTAX SheTopologyControlRequestResultType
			MAX-ACCESS read-only
			STATUS current
			DESCRIPTION
				" The result of the last user command. "
			::= { sheLldpControl 4 }

		
--  1.3.6.1.4.1.231.7.1.2.2.1.17.1.1.5
		sheLldpControlTimeStamp OBJECT-TYPE
			SYNTAX Unsigned32
			UNITS "sec"
			MAX-ACCESS read-only
			STATUS current
			DESCRIPTION
				" The time stamp of the last command (end of command). "
			::= { sheLldpControl 5 }

		
--  1.3.6.1.4.1.231.7.1.2.2.1.17.1.1.6
		sheLldpControlMessageTxInterval OBJECT-TYPE
			SYNTAX Integer32 (5..32768)
			UNITS "seconds"
			MAX-ACCESS read-write
			STATUS current
			DESCRIPTION
				" The interval at which LLDP frames are transmitted on behalf of this LLDP agent. "
			DEFVAL { 30 }
			::= { sheLldpControl 6 }

		
--  1.3.6.1.4.1.231.7.1.2.2.1.17.1.1.7
		sheLldpControlMessageTxHoldMultiplier OBJECT-TYPE
			SYNTAX Integer32 (2..10)
			UNITS "secconds"
			MAX-ACCESS read-write
			STATUS current
			DESCRIPTION
				" The time-to-live value expressed as a multiple of the lldpMessageTxInterval object. "
			DEFVAL { 4 }
			::= { sheLldpControl 7 }

		
--  1.3.6.1.4.1.231.7.1.2.2.1.17.1.1.8
		sheLldpControlReinitDelay OBJECT-TYPE
			SYNTAX Integer32 (1..10)
			UNITS "secconds"
			MAX-ACCESS read-write
			STATUS current
			DESCRIPTION
				" The lldpReinitDelay indicates the delay (in units of seconds) from 
				when lldpPortConfigAdminStatus object of a particular port becomes 'disabled' 
				                            until re-initialization will be attempted."
			DEFVAL { 2 }
			::= { sheLldpControl 8 }

		
--  1.3.6.1.4.1.231.7.1.2.2.1.17.1.1.9
		sheLldpControlTxDelay OBJECT-TYPE
			SYNTAX Integer32 (1..8192)
			UNITS "secconds"
			MAX-ACCESS read-write
			STATUS current
			DESCRIPTION
				" The lldpTxDelay indicates the delay (in units of seconds) 
				between successive LLDP frame transmissions initiated by value/status changes 
				                            in the LLDP local systems MIB."
			DEFVAL { 2 }
			::= { sheLldpControl 9 }

		
--  1.3.6.1.4.1.231.7.1.2.2.1.17.1.1.10
		sheLldpControlNotificationInterval OBJECT-TYPE
			SYNTAX Integer32 (5..3600)
			UNITS "secconds"
			MAX-ACCESS read-write
			STATUS current
			DESCRIPTION
				" This object controls the transmission of LLDP notifications. "
			DEFVAL { 5 }
			::= { sheLldpControl 10 }

		
--  1.3.6.1.4.1.231.7.1.2.2.1.17.1.1.11
		sheLldpControlPortIndex OBJECT-TYPE
			SYNTAX Integer32 (1..6)
			MAX-ACCESS read-write
			STATUS current
			DESCRIPTION
				" This object controls the configured port index"
			::= { sheLldpControl 11 }

		
--  1.3.6.1.4.1.231.7.1.2.2.1.17.1.1.12
		sheLldpControlPortAdminStatus OBJECT-TYPE
			SYNTAX SheTopologyControlAdminStatus
			MAX-ACCESS read-write
			STATUS current
			DESCRIPTION
				" The administratively desired status of the local LLDP agent. "
			DEFVAL { disable }
			::= { sheLldpControl 12 }

		
--  1.3.6.1.4.1.231.7.1.2.2.1.17.1.1.13
		sheLldpControlPortNotificationEnable OBJECT-TYPE
			SYNTAX TruthValue
			MAX-ACCESS read-write
			STATUS current
			DESCRIPTION
				" The lldpPortConfigNotificationEnable controls, on a per
				port basis,  whether or not notifications from the agent are enabled."
			DEFVAL { false }
			::= { sheLldpControl 13 }

		
--  1.3.6.1.4.1.231.7.1.2.2.1.17.1.1.14
		sheLldpControlPortTLVsTxEnable OBJECT-TYPE
			SYNTAX SheTopologyControlTLVsTxEnable
			MAX-ACCESS read-write
			STATUS current
			DESCRIPTION
				" The lldpPortConfigTLVsTxEnable, defined as a bitmap,
				includes the basic set of LLDP TLVs whose transmission is
					  allowed on the local LLDP agent by the network management."
			DEFVAL { {  } }
			::= { sheLldpControl 14 }

		
--  1.3.6.1.4.1.231.7.1.2.2.1.17.1.1.15
		sheLldpControlPortManagementAddress OBJECT-TYPE
			SYNTAX IpAddress
			MAX-ACCESS read-write
			STATUS current
			DESCRIPTION
				" A management IP address for a given port. This address is used for identifying an NE."
			::= { sheLldpControl 15 }

		
--  1.3.6.1.4.1.231.7.1.2.2.1.17.1.1.16
		sheLldpControlPortMulticastAddress OBJECT-TYPE
			SYNTAX SheTopologyControlMulticastAddress
			MAX-ACCESS read-write
			STATUS current
			DESCRIPTION
				" a control of LLDP Multicast Address. "
			::= { sheLldpControl 16 }

		
--  -----------------------------------------------------------------
-- SHE TOPOLOGY Control group(PTOPO)
-- ----------------------------------------------------------------- 
-- 1.3.6.1.4.1.231.7.1.2.2.1.17.1.2	
		shePtopoControl OBJECT IDENTIFIER ::= { sheTopologyConfigurationObjects 2 }

		
--  1.3.6.1.4.1.231.7.1.2.2.1.17.1.2.1
		shePtopoControlRequest OBJECT-TYPE
			SYNTAX SheTopologyControlRequestType
			MAX-ACCESS read-write
			STATUS current
			DESCRIPTION
				" This attribute identifies the control commands.
				
				configureTrapInterval: This object controls the transmission of PTOPO notifications. 
					If this object has a value of zero, then no ptopoConfigChange notifications 
					will be transmitted by the agent. If this object has a non-zero value, then 
					the agent must not generate more than one ptopoConfigChange trap-event 
					in the indicated period
				
				configureMaxHoldTime: This object specifies the desired time interval for which 
					an agent will maintain dynamic ptopoConnEntries. 
				
				createConnectionEntry: Create the information about a particular physical network 
					connection if a physical topology discovery process is active. That information
					are remote chassis, remote port, agent Net addr. 
				
				deleteConnectionEntry: Delete the information about a physical network connected 
					with specific chassis and port.  
				
				modifyConnectionEntry: Modify the information about a physical network connected 
					with specific chassis and port.
				
				clearStatistics: This object is cleared all counters as to statictics of PTOPO-MIB.
				
				Notifications : changedTrapInterval / changedMaxHoldTime, clearedPtopoStatistics, createdConnectionEntry, deletedConnectionEntry"
			::= { shePtopoControl 1 }

		
--  1.3.6.1.4.1.231.7.1.2.2.1.17.1.2.2
		shePtopoControlStatus OBJECT-TYPE
			SYNTAX SheControlStatusType
			MAX-ACCESS read-only
			STATUS current
			DESCRIPTION
				" The status of a control request. "
			::= { shePtopoControl 2 }

		
--  1.3.6.1.4.1.231.7.1.2.2.1.17.1.2.3
		shePtopoControlTimer OBJECT-TYPE
			SYNTAX Unsigned32
			MAX-ACCESS read-only
			STATUS current
			DESCRIPTION
				" The maximum wait time for the manager for command ending.
				For long running commands.
				The manager reads this value from the DSLAM. "
			::= { shePtopoControl 3 }

		
--  1.3.6.1.4.1.231.7.1.2.2.1.17.1.2.4
		shePtopoControlReqResult OBJECT-TYPE
			SYNTAX SheTopologyControlRequestResultType
			MAX-ACCESS read-only
			STATUS current
			DESCRIPTION
				" The result of the last user command. "
			::= { shePtopoControl 4 }

		
--  1.3.6.1.4.1.231.7.1.2.2.1.17.1.2.5
		shePtopoControlTimeStamp OBJECT-TYPE
			SYNTAX Unsigned32
			UNITS "sec"
			MAX-ACCESS read-only
			STATUS current
			DESCRIPTION
				" The time stamp of the last command (end of command). "
			::= { shePtopoControl 5 }

		
--  1.3.6.1.4.1.231.7.1.2.2.1.17.1.2.6
		shePtopoControlTrapInterval OBJECT-TYPE
			SYNTAX Integer32 (0 | 5..3600)
			UNITS "seconds"
			MAX-ACCESS read-write
			STATUS current
			DESCRIPTION
				" This object controls the transmission of PTOPO notifications. Range is 5..3600"
			DEFVAL { 0 }
			::= { shePtopoControl 6 }

		
--  1.3.6.1.4.1.231.7.1.2.2.1.17.1.2.7
		shePtopoControlMaxHoldTime OBJECT-TYPE
			SYNTAX Integer32 (1..2147483647)
			UNITS "seconds"
			MAX-ACCESS read-write
			STATUS current
			DESCRIPTION
				" This object controls to maintain dynamic ptopoConnEntries. Range is 1..2147483647"
			DEFVAL { 300 }
			::= { shePtopoControl 7 }

		
--  1.3.6.1.4.1.231.7.1.2.2.1.17.1.2.8
		shePtopoControlConnTimeMark OBJECT-TYPE
			SYNTAX TimeFilter
			MAX-ACCESS read-write
			STATUS current
			DESCRIPTION
				"A TimeFilter for this entry.  See the TimeFilter textual
				convention in RFC 2021 to see how this works."
			::= { shePtopoControl 8 }

		
--  1.3.6.1.4.1.231.7.1.2.2.1.17.1.2.9
		shePtopoControlConnLocalChassis OBJECT-TYPE
			SYNTAX PhysicalIndex
			MAX-ACCESS read-write
			STATUS current
			DESCRIPTION
				"The entPhysicalIndex value used to identify the chassis
				component associated with the local connection endpoint."
			::= { shePtopoControl 9 }

		
--  1.3.6.1.4.1.231.7.1.2.2.1.17.1.2.10
		shePtopoControlConnLocalPort OBJECT-TYPE
			SYNTAX PhysicalIndex
			MAX-ACCESS read-write
			STATUS current
			DESCRIPTION
				"The entPhysicalIndex value used to identify the port
				component associated with the local connection endpoint.
				However, since entPhysicalIndex is not available for uplink ports, 
				ifIndex is used instead."
			::= { shePtopoControl 10 }

		
--  1.3.6.1.4.1.231.7.1.2.2.1.17.1.2.11
		shePtopoControlConnIndex OBJECT-TYPE
			SYNTAX Integer32 (1..2147483647)
			MAX-ACCESS read-write
			STATUS current
			DESCRIPTION
				"This object represents an arbitrary local integer value
				used by this agent to identify a particular connection
				instance, unique only for the indicated local connection
				endpoint.
				
				A particular ptopoConnIndex value may be reused in the event
				an entry is aged out and later re-learned with the same (or
				different) remote chassis and port identifiers.
				
				An agent is encouraged to assign monotonically increasing
				index values to new entries, starting with one, after each
				reboot.  It is considered unlikely that the ptopoConnIndex
				will wrap between reboots."
			::= { shePtopoControl 11 }

		
--  1.3.6.1.4.1.231.7.1.2.2.1.17.1.2.12
		shePtopoControlConnRemoteChassisType OBJECT-TYPE
			SYNTAX PtopoChassisIdType
			MAX-ACCESS read-write
			STATUS current
			DESCRIPTION
				"The type of encoding used to identify the chassis
				associated with the remote connection endpoint.
				
				This object may not be modified if the associated
				ptopoConnRowStatus object has a value of active(1)."
			::= { shePtopoControl 12 }

		
--  1.3.6.1.4.1.231.7.1.2.2.1.17.1.2.13
		sheptopoControlConnRemoteChassis OBJECT-TYPE
			SYNTAX PtopoChassisId
			MAX-ACCESS read-write
			STATUS current
			DESCRIPTION
				"The string value used to identify the chassis component
				associated with the remote connection endpoint.
				
				This object may not be modified if the associated
				ptopoConnRowStatus object has a value of active(1)."
			::= { shePtopoControl 13 }

		
--  1.3.6.1.4.1.231.7.1.2.2.1.17.1.2.14
		sheptopoControlConnRemotePortType OBJECT-TYPE
			SYNTAX PtopoPortIdType
			MAX-ACCESS read-write
			STATUS current
			DESCRIPTION
				"The type of port identifier encoding used in the associated
				'ptopoConnRemotePort' object.
				
				This object may not be modified if the associated
				ptopoConnRowStatus object has a value of active(1)."
			::= { shePtopoControl 14 }

		
--  1.3.6.1.4.1.231.7.1.2.2.1.17.1.2.15
		sheptopoControlConnRemotePort OBJECT-TYPE
			SYNTAX PtopoPortId
			MAX-ACCESS read-write
			STATUS current
			DESCRIPTION
				"The type of port identifier encoding used in the associated
				'ptopoConnRemotePort' object.
				
				This object may not be modified if the associated
				ptopoConnRowStatus object has a value of active(1)."
			::= { shePtopoControl 15 }

		
--  1.3.6.1.4.1.231.7.1.2.2.1.17.1.2.16
		sheptopoControlConnAgentNetAddrType OBJECT-TYPE
			SYNTAX AddressFamilyNumbers
			MAX-ACCESS read-write
			STATUS current
			DESCRIPTION
				"This network address type of the associated
				ptopoConnNetAddr object, unless that object contains a zero
				length string.  In such a case, an NMS application should
				ignore any returned value for this object.
				
				This object may not be modified if the associated
				ptopoConnRowStatus object has a value of active(1)."
			::= { shePtopoControl 16 }

		
--  1.3.6.1.4.1.231.7.1.2.2.1.17.1.2.17
		sheptopoControlConnAgentNetAddr OBJECT-TYPE
			SYNTAX PtopoGenAddr
			MAX-ACCESS read-write
			STATUS current
			DESCRIPTION
				"This object identifies a network address which may be used
				to reach an SNMP agent entity containing information for the
				chassis and port components represented by the associated
				'ptopoConnRemoteChassis' and 'ptopoConnRemotePort' objects.
				If no such address is known, then this object shall contain
				an empty string.
				
				This object may not be modified if the associated
				ptopoConnRowStatus object has a value of active(1)."
			::= { shePtopoControl 17 }

		
--  -----------------------------------------------------------------
-- SHE TOPOLOGY TABLE(LLDP Multicast Address)
-- ----------------------------------------------------------------- 
-- 1.3.6.1.4.1.231.7.1.2.2.1.17.1.3	
		sheLldpMulticastAddressTable OBJECT-TYPE
			SYNTAX SEQUENCE OF SheLldpMulticastAddressEntry
			MAX-ACCESS not-accessible
			STATUS current
			DESCRIPTION
				"The Multicast Address of lldpTable."
			::= { sheTopologyConfigurationObjects 3 }

		
--  1.3.6.1.4.1.231.7.1.2.2.1.17.1.3.1	
		sheLldpMulticastAddressEntry OBJECT-TYPE
			SYNTAX SheLldpMulticastAddressEntry
			MAX-ACCESS not-accessible
			STATUS current
			DESCRIPTION
				"One entry for every existing uplink ports in the system."
			INDEX { lldpLocPortNum }
			::= { sheLldpMulticastAddressTable 1 }

		
		SheLldpMulticastAddressEntry ::=
			SEQUENCE { 
				sheLlpdMulticastAddress
					SheTopologyControlMulticastAddress
			 }

--  1.3.6.1.4.1.231.7.1.2.2.1.17.1.3.1.1
		sheLlpdMulticastAddress OBJECT-TYPE
			SYNTAX SheTopologyControlMulticastAddress
			MAX-ACCESS read-only
			STATUS current
			DESCRIPTION
				"Multicast Address  that LLDP packet is using"
			::= { sheLldpMulticastAddressEntry 1 }

		
--  1.3.6.1.4.1.231.7.1.2.2.1.17.2
		sheTopologyNotifications OBJECT IDENTIFIER ::= { sheTopology 2 }

		
--  -----------------------------------------------------------------
-- SHE TOPOLOGY Notification Group
-- ----------------------------------------------------------------- 
-- 1.3.6.1.4.1.231.7.1.2.2.1.17.2.1	
		sheTopologyAlarms OBJECT IDENTIFIER ::= { sheTopologyNotifications 1 }

		
--  1.3.6.1.4.1.231.7.1.2.2.1.17.2.2	
		sheTopologyTraps OBJECT IDENTIFIER ::= { sheTopologyNotifications 2 }

		
--  1.3.6.1.4.1.231.7.1.2.2.1.17.2.2.1
		sheTopologyChangedMessageTxInterval NOTIFICATION-TYPE
			OBJECTS { sheLldpControlStatus, sheLldpControlReqResult, sheLldpControlTimeStamp, sheLldpControlMessageTxInterval }
			STATUS current
			DESCRIPTION 
				"Notification for command execution."
			::= { sheTopologyTraps 1 }

		
--  1.3.6.1.4.1.231.7.1.2.2.1.17.2.2.2
		sheTopologyChangedMessageTxHoldMultiplier NOTIFICATION-TYPE
			OBJECTS { sheLldpControlStatus, sheLldpControlReqResult, sheLldpControlTimeStamp, sheLldpControlMessageTxHoldMultiplier }
			STATUS current
			DESCRIPTION 
				"Notification for command execution."
			::= { sheTopologyTraps 2 }

		
--  1.3.6.1.4.1.231.7.1.2.2.1.17.2.2.3
		sheTopologyChangedReinitDelay NOTIFICATION-TYPE
			OBJECTS { sheLldpControlStatus, sheLldpControlReqResult, sheLldpControlTimeStamp, sheLldpControlReinitDelay }
			STATUS current
			DESCRIPTION 
				"Notification for command execution."
			::= { sheTopologyTraps 3 }

		
--  1.3.6.1.4.1.231.7.1.2.2.1.17.2.2.4
		sheTopologyChangedTxDelay NOTIFICATION-TYPE
			OBJECTS { sheLldpControlStatus, sheLldpControlReqResult, sheLldpControlTimeStamp, sheLldpControlTxDelay }
			STATUS current
			DESCRIPTION 
				"Notification for command execution."
			::= { sheTopologyTraps 4 }

		
--  1.3.6.1.4.1.231.7.1.2.2.1.17.2.2.5
		sheTopologyChangedNotificationInterval NOTIFICATION-TYPE
			OBJECTS { sheLldpControlStatus, sheLldpControlReqResult, sheLldpControlTimeStamp, sheLldpControlNotificationInterval }
			STATUS current
			DESCRIPTION 
				"Notification for command execution."
			::= { sheTopologyTraps 5 }

		
--  1.3.6.1.4.1.231.7.1.2.2.1.17.2.2.6
		sheTopologyChangedPort NOTIFICATION-TYPE
			OBJECTS { sheLldpControlStatus, sheLldpControlReqResult, sheLldpControlTimeStamp, sheLldpControlPortIndex, sheLldpControlPortAdminStatus, 
				sheLldpControlPortNotificationEnable, sheLldpControlPortTLVsTxEnable }
			STATUS current
			DESCRIPTION 
				"Notification for command execution."
			::= { sheTopologyTraps 6 }

		
--  1.3.6.1.4.1.231.7.1.2.2.1.17.2.2.7
		sheTopologyAddManagemnetAddress NOTIFICATION-TYPE
			OBJECTS { sheLldpControlStatus, sheLldpControlReqResult, sheLldpControlTimeStamp, sheLldpControlPortIndex, sheLldpControlPortManagementAddress
				 }
			STATUS current
			DESCRIPTION 
				"Notification for command execution."
			::= { sheTopologyTraps 7 }

		
--  1.3.6.1.4.1.231.7.1.2.2.1.17.2.2.8
		sheTopologyDeleteManagemnetAddress NOTIFICATION-TYPE
			OBJECTS { sheLldpControlStatus, sheLldpControlReqResult, sheLldpControlTimeStamp, sheLldpControlPortIndex, sheLldpControlPortManagementAddress
				 }
			STATUS current
			DESCRIPTION 
				"Notification for command execution."
			::= { sheTopologyTraps 8 }

		
--  1.3.6.1.4.1.231.7.1.2.2.1.17.2.2.9
		sheTopologyClearedLldpStatistics NOTIFICATION-TYPE
			OBJECTS { sheLldpControlStatus, sheLldpControlReqResult, sheLldpControlTimeStamp }
			STATUS current
			DESCRIPTION 
				"Notification for command execution."
			::= { sheTopologyTraps 9 }

		
--  1.3.6.1.4.1.231.7.1.2.2.1.17.2.2.10
		sheTopologyChangedTrapInterval NOTIFICATION-TYPE
			OBJECTS { shePtopoControlStatus, shePtopoControlReqResult, shePtopoControlTimeStamp, shePtopoControlTrapInterval }
			STATUS current
			DESCRIPTION 
				"Notification for command execution."
			::= { sheTopologyTraps 10 }

		
--  1.3.6.1.4.1.231.7.1.2.2.1.17.2.2.11
		sheTopologyChangedMaxHoldTime NOTIFICATION-TYPE
			OBJECTS { shePtopoControlStatus, shePtopoControlReqResult, shePtopoControlTimeStamp, shePtopoControlMaxHoldTime }
			STATUS current
			DESCRIPTION 
				"Notification for command execution."
			::= { sheTopologyTraps 11 }

		
--  1.3.6.1.4.1.231.7.1.2.2.1.17.2.2.12
		sheTopologyClearedPtopoStatistics NOTIFICATION-TYPE
			OBJECTS { shePtopoControlStatus, shePtopoControlReqResult, shePtopoControlTimeStamp }
			STATUS current
			DESCRIPTION 
				"Notification for command execution."
			::= { sheTopologyTraps 12 }

		
--  1.3.6.1.4.1.231.7.1.2.2.1.17.2.2.13
		sheTopologyCreatedConnEntry NOTIFICATION-TYPE
			OBJECTS { shePtopoControlStatus, shePtopoControlReqResult, shePtopoControlTimeStamp, shePtopoControlConnTimeMark, shePtopoControlConnIndex, 
				shePtopoControlConnLocalChassis, shePtopoControlConnLocalPort, sheptopoControlConnAgentNetAddrType, sheptopoControlConnAgentNetAddr, shePtopoControlConnRemoteChassisType
				 }
			STATUS current
			DESCRIPTION 
				"Notification for command execution."
			::= { sheTopologyTraps 13 }

		
--  1.3.6.1.4.1.231.7.1.2.2.1.17.2.2.14
		sheTopologyDeletedConnEntry NOTIFICATION-TYPE
			OBJECTS { shePtopoControlStatus, shePtopoControlReqResult, shePtopoControlTimeStamp, shePtopoControlConnTimeMark, shePtopoControlConnLocalChassis, 
				shePtopoControlConnLocalPort, shePtopoControlConnIndex }
			STATUS current
			DESCRIPTION 
				"Notification for command execution."
			::= { sheTopologyTraps 14 }

		
--  1.3.6.1.4.1.231.7.1.2.2.1.17.2.2.15
		sheTopologyModifiedConnEntry NOTIFICATION-TYPE
			OBJECTS { shePtopoControlStatus, shePtopoControlReqResult, shePtopoControlTimeStamp, shePtopoControlConnLocalPort, shePtopoControlConnIndex, 
				shePtopoControlConnRemoteChassisType, sheptopoControlConnRemoteChassis, sheptopoControlConnRemotePortType, sheptopoControlConnRemotePort, sheptopoControlConnAgentNetAddrType, 
				sheptopoControlConnAgentNetAddr }
			STATUS current
			DESCRIPTION 
				"Notification for command execution."
			::= { sheTopologyTraps 15 }

		
--  1.3.6.1.4.1.231.7.1.2.2.1.17.2.2.16
		sheTopologyFault NOTIFICATION-TYPE
			OBJECTS { lldpRemIndex }
			STATUS current
			DESCRIPTION 
				"Topology Fault Trap."
			::= { sheTopologyTraps 16 }

		
--  1.3.6.1.4.1.231.7.1.2.2.1.17.2.2.17
		sheTopologyChangedLLDPMulticastAddress NOTIFICATION-TYPE
			OBJECTS { sheLldpControlStatus, sheLldpControlReqResult, sheLldpControlTimeStamp, sheLldpControlPortMulticastAddress }
			STATUS current
			DESCRIPTION 
				"Multicast Address of LLDP"
			::= { sheTopologyTraps 17 }

		
-- 1.3.6.1.4.1.231.7.1.2.2.1.4.2.4
		sheTopologyConformance OBJECT IDENTIFIER ::= { sheTopology 100 }

		
-- 1.3.6.1.4.1.231.7.1.2.2.1.17.100.1
		sheTopologyCompliances OBJECT IDENTIFIER ::= { sheTopologyConformance 1 }

		
-- 1.3.6.1.4.1.231.7.1.2.2.1.17.100.1.1
-- this module
		sheTopologyCompliance MODULE-COMPLIANCE
			STATUS current
			DESCRIPTION 
				"Description."
			MODULE -- this module
				MANDATORY-GROUPS { sheTopologyGroup, sheTopologyControlGroup, sheTopologyNotificationGroup }
			::= { sheTopologyCompliances 1 }

		
-- 1.3.6.1.4.1.231.7.1.2.2.1.17.100.2
		sheTopologyGroups OBJECT IDENTIFIER ::= { sheTopologyConformance 2 }

		
-- 1.3.6.1.4.1.231.7.1.2.2.1.17.100.2.1
		sheTopologyGroup OBJECT-GROUP
			OBJECTS { sheLlpdMulticastAddress }
			STATUS current
			DESCRIPTION 
				"Description."
			::= { sheTopologyGroups 1 }

		
-- 1.3.6.1.4.1.231.7.1.2.2.1.17.100.2.2
		sheTopologyControlGroup OBJECT-GROUP
			OBJECTS { sheLldpControlRequest, sheLldpControlStatus, sheLldpControlTimer, sheLldpControlReqResult, sheLldpControlTimeStamp, 
				sheLldpControlMessageTxInterval, sheLldpControlMessageTxHoldMultiplier, sheLldpControlReinitDelay, sheLldpControlTxDelay, sheLldpControlNotificationInterval, 
				sheLldpControlPortIndex, sheLldpControlPortAdminStatus, sheLldpControlPortNotificationEnable, sheLldpControlPortTLVsTxEnable, sheLldpControlPortManagementAddress, 
				sheLldpControlPortMulticastAddress, shePtopoControlRequest, shePtopoControlStatus, shePtopoControlTimer, shePtopoControlReqResult, 
				shePtopoControlTimeStamp, shePtopoControlTrapInterval, shePtopoControlMaxHoldTime, shePtopoControlConnTimeMark, shePtopoControlConnLocalChassis, 
				shePtopoControlConnLocalPort, shePtopoControlConnIndex, shePtopoControlConnRemoteChassisType, sheptopoControlConnRemoteChassis, sheptopoControlConnRemotePortType, 
				sheptopoControlConnRemotePort, sheptopoControlConnAgentNetAddrType, sheptopoControlConnAgentNetAddr }
			STATUS current
			DESCRIPTION 
				"Description."
			::= { sheTopologyGroups 2 }

		
-- 1.3.6.1.4.1.231.7.1.2.2.1.17.100.2.1
		sheTopologyNotificationGroup NOTIFICATION-GROUP
			NOTIFICATIONS { sheTopologyChangedMessageTxInterval, sheTopologyChangedMessageTxHoldMultiplier, sheTopologyChangedReinitDelay, sheTopologyChangedTxDelay, sheTopologyChangedNotificationInterval, 
				sheTopologyChangedPort, sheTopologyAddManagemnetAddress, sheTopologyDeleteManagemnetAddress, sheTopologyClearedLldpStatistics, sheTopologyChangedTrapInterval, 
				sheTopologyChangedMaxHoldTime, sheTopologyClearedPtopoStatistics, sheTopologyCreatedConnEntry, sheTopologyDeletedConnEntry, sheTopologyModifiedConnEntry, 
				sheTopologyFault, sheTopologyChangedLLDPMulticastAddress }
			STATUS current
			DESCRIPTION 
				"Description."
			::= { sheTopologyGroups 3 }

		
	
	END

--
-- she-topology-mib.mib
--
