--
-- she-products-mib.mib
-- MIB generated by MG-SOFT Visual MIB Builder Version 5.0  Build 250
-- Thursday, November 23, 2006 at 09:41:26
--

	DS-SHE-PRODUCTS-MIB DEFINITIONS ::= BEGIN
 
		IMPORTS
			she			
				FROM AN-MIB
			dsShe
				FROM DASAN-SMI							
			MODULE-IDENTITY			
				FROM SNMPv2-SMI;
	
	
		sheProducts MODULE-IDENTITY 
			LAST-UPDATED "200611231000Z"		-- November 23, 2006 at 10:00 GMT
			ORGANIZATION 
				"Siemens AG"
			CONTACT-INFO 
				"."
			DESCRIPTION 
				"This module defines the object identifiers that are
				assigned to various hardware platforms, and hence are
				returned as values for sysObjectID"
			REVISION "200608111121Z"		-- August 11, 2006 at 11:21 GMT
			DESCRIPTION 
				"Take over by Gerd Barchmann for R2.5."
			REVISION "200611230938Z"		-- November 23, 2006 at 09:38 GMT
			DESCRIPTION 
				"Add values for new supported shelftypes."
			::= { dsShe 101 }

		
	
--
-- Node definitions
--
	
		shehiX OBJECT IDENTIFIER ::= { sheProducts 1 }

		
--   Hix5630/35/25 series
-- 
		hiX5630-M600 OBJECT IDENTIFIER ::= { shehiX 1 }

		
		hiX5635-M1200 OBJECT IDENTIFIER ::= { shehiX 2 }

		
		hiX5625-M400 OBJECT IDENTIFIER ::= { shehiX 3 }

		
		hiX5635-M1100 OBJECT IDENTIFIER ::= { shehiX 4 }

		
		hiX5635-G1100 OBJECT IDENTIFIER ::= { shehiX 5 }


		
	
	END

--
-- she-products-mib.mib
--
