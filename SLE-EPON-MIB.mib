--
-- SLE-EPON-MIB.my
-- MIB generated by MG-SOFT Visual MIB Builder Version 6.0  Build 88
-- Wednesday, July 02, 2008 at 19:41:54
--

--  SLE-EPON-MIB.my
-- MIB generated by MG-SOFT Visual MIB Builder Version 6.0  Build 88
-- Wednesday, June 27, 2007 at 19:24:02
-- 

	SLE-EPON-MIB DEFINITIONS ::= BEGIN
 
		IMPORTS
			sleMgmt			
				FROM DASAN-SMI			
			ifIndex			
				FROM IF-MIB			
			VlanIndex, PortList			
				FROM Q-BRIDGE-MIB			
			sysDescr			
				FROM RFC1213-MIB			
			SleControlStatusType, SleControlRequestResultType			
				FROM SLE-TC-MIB			
			OBJECT-GROUP, NOTIFICATION-GROUP			
				FROM SNMPv2-CONF			
			TimeTicks, IpAddress, Integer32, Gauge32, Counter32, 
			Counter64, BITS, OBJECT-TYPE, MODULE-IDENTITY, NOTIFICATION-TYPE			
				FROM SNMPv2-SMI			
			MacAddress, TEXTUAL-CONVENTION			
				FROM SNMPv2-TC;
	
	
--  1.3.6.1.4.1.6296.101.20
-- January 25, 2006 at 17:53 GMT
		-- 1.3.6.1.4.1.6296.101.20
		sleEpon MODULE-IDENTITY 
			LAST-UPDATED "200601251753Z"		-- January 25, 2006 at 17:53 GMT
			ORGANIZATION 
				"Organization."
			CONTACT-INFO 
				"Contact-info."
			DESCRIPTION 
				"Description."
			::= { sleMgmt 20 }

		
	
	
--
-- Textual conventions
--
	
--  Textual conventions
-- 
		EnableFlag ::= TEXTUAL-CONVENTION
			STATUS current
			DESCRIPTION 
				"Description."
			SYNTAX INTEGER
				{
				enable(1),
				disable(2)
				}

	
--
-- Node definitions
--
	
--  Node definitions
-- 
-- 1.3.6.1.4.1.6296.101.20.1
		-- 1.3.6.1.4.1.6296.101.20.1
		sleEponBase OBJECT IDENTIFIER ::= { sleEpon 1 }

		
--  1.3.6.1.4.1.6296.101.20.1.1
		-- 1.3.6.1.4.1.6296.101.20.1.1
		sleEponBaseInfo OBJECT IDENTIFIER ::= { sleEponBase 1 }

		
--  1.3.6.1.4.1.6296.101.20.1.1.1
		-- 1.3.6.1.4.1.6296.101.20.1.1.1
		sleEponBaseSlaPlatoMaxBandwdith OBJECT-TYPE
			SYNTAX INTEGER (1000..900000 | 1000000)
			UNITS "kbps"
			MAX-ACCESS read-only
			STATUS current
			DESCRIPTION
				"Description."
			::= { sleEponBaseInfo 1 }

		
--  1.3.6.1.4.1.6296.101.20.1.1.2
		-- 1.3.6.1.4.1.6296.101.20.1.1.2
		sleEponBaseDPShapingMaxBandwidth OBJECT-TYPE
			SYNTAX INTEGER (0 | 1000..900000)
			UNITS "kbps"
			MAX-ACCESS read-only
			STATUS current
			DESCRIPTION
				"Description."
			::= { sleEponBaseInfo 2 }

		
--  1.3.6.1.4.1.6296.101.20.1.1.3
		-- 1.3.6.1.4.1.6296.101.20.1.1.3
		sleEponBasePortMaxHost OBJECT-TYPE
			SYNTAX INTEGER (0 | 1..16)
			MAX-ACCESS read-only
			STATUS current
			DESCRIPTION
				"Description."
			::= { sleEponBaseInfo 3 }

		
		-- 1.3.6.1.4.1.6296.101.20.1.1.4
		sleEponBaseOnuAutoUpgrade OBJECT-TYPE
			SYNTAX EnableFlag
			MAX-ACCESS read-only
			STATUS current
			DESCRIPTION
				"The status of ONU auto-upgrade."
			::= { sleEponBaseInfo 4 }

		
		-- 1.3.6.1.4.1.6296.101.20.1.1.5
		sleEponBaseOnuAutoUpgradeRebootTime OBJECT-TYPE
			SYNTAX INTEGER (-1 | 0..23)
			UNITS "hour"
			MAX-ACCESS read-only
			STATUS current
			DESCRIPTION
				"The reboot-time of ONU auto-upgrade."
			::= { sleEponBaseInfo 5 }

		
		-- 1.3.6.1.4.1.6296.101.20.1.1.6
		sleEponBaseOnuAgingTime OBJECT-TYPE
			SYNTAX Integer32 (0..30)
			UNITS "day"
			MAX-ACCESS read-only
			STATUS current
			DESCRIPTION
				"Description."
			::= { sleEponBaseInfo 6 }

		
		-- 1.3.6.1.4.1.6296.101.20.1.1.7
		sleEponBaseAlarmStatus OBJECT-TYPE
			SYNTAX BITS
				{
				critical(0),
				major(1),
				minor(2)
				}
			MAX-ACCESS read-only
			STATUS current
			DESCRIPTION
				"Description."
			::= { sleEponBaseInfo 7 }

		
		-- 1.3.6.1.4.1.6296.101.20.1.1.8
		sleEponBaseAlarmMode OBJECT-TYPE
			SYNTAX INTEGER
				{
				auto(0),
				manual(1)
				}
			MAX-ACCESS read-only
			STATUS current
			DESCRIPTION
				"Description."
			::= { sleEponBaseInfo 8 }

		
--  1.3.6.1.4.1.6296.101.20.1.2
		-- 1.3.6.1.4.1.6296.101.20.1.2
		sleEponBaseControl OBJECT IDENTIFIER ::= { sleEponBase 2 }

		
--  1.3.6.1.4.1.6296.101.20.1.2.1
		-- 1.3.6.1.4.1.6296.101.20.1.2.1
		sleEponBaseControlRequest OBJECT-TYPE
			SYNTAX INTEGER
				{
				setEponBaseDefaultBandwidth(1),
				setEponBaseDefaultMaxhost(2),
				setEponBaseOnuAutoUpgrade(3),
				setEponBaseOnuAgingTime(4),
				setEponBaseAlarmStatus(5),
				setEponBaseAlarmMode(6)
				}
			MAX-ACCESS read-write
			STATUS current
			DESCRIPTION
				"Description."
			::= { sleEponBaseControl 1 }

		
--  1.3.6.1.4.1.6296.101.20.1.2.2
		-- 1.3.6.1.4.1.6296.101.20.1.2.2
		sleEponBaseControlStatus OBJECT-TYPE
			SYNTAX SleControlStatusType
			MAX-ACCESS read-only
			STATUS current
			DESCRIPTION
				"Description."
			::= { sleEponBaseControl 2 }

		
--  1.3.6.1.4.1.6296.101.20.1.2.3
		-- 1.3.6.1.4.1.6296.101.20.1.2.3
		sleEponBaseControlTimer OBJECT-TYPE
			SYNTAX Gauge32
			MAX-ACCESS read-write
			STATUS current
			DESCRIPTION
				"Description."
			::= { sleEponBaseControl 3 }

		
--  1.3.6.1.4.1.6296.101.20.1.2.4
		-- 1.3.6.1.4.1.6296.101.20.1.2.4
		sleEponBaseControlTimeStamp OBJECT-TYPE
			SYNTAX TimeTicks
			MAX-ACCESS read-only
			STATUS current
			DESCRIPTION
				"Description."
			::= { sleEponBaseControl 4 }

		
--  1.3.6.1.4.1.6296.101.20.1.2.5
		-- 1.3.6.1.4.1.6296.101.20.1.2.5
		sleEponBaseControlReqResult OBJECT-TYPE
			SYNTAX SleControlRequestResultType
			MAX-ACCESS read-only
			STATUS current
			DESCRIPTION
				"Description."
			::= { sleEponBaseControl 5 }

		
--  1.3.6.1.4.1.6296.101.20.1.2.6
		-- 1.3.6.1.4.1.6296.101.20.1.2.6
		sleEponBaseControlSlaPlatoMaxBandwdith OBJECT-TYPE
			SYNTAX INTEGER (1000..900000 | 1000000)
			UNITS "kbps"
			MAX-ACCESS read-write
			STATUS current
			DESCRIPTION
				"Description."
			::= { sleEponBaseControl 6 }

		
--  1.3.6.1.4.1.6296.101.20.1.2.7
		-- 1.3.6.1.4.1.6296.101.20.1.2.7
		sleEponBaseControlDPShapingMaxBandwidth OBJECT-TYPE
			SYNTAX INTEGER (0 | 1000..900000)
			UNITS "Mbps"
			MAX-ACCESS read-write
			STATUS current
			DESCRIPTION
				"Description."
			::= { sleEponBaseControl 7 }

		
--  1.3.6.1.4.1.6296.101.20.1.2.8
		-- 1.3.6.1.4.1.6296.101.20.1.2.8
		sleEponBaseControlPortMaxHost OBJECT-TYPE
			SYNTAX INTEGER (0 | 1..16)
			MAX-ACCESS read-write
			STATUS current
			DESCRIPTION
				"Description."
			::= { sleEponBaseControl 8 }

		
		-- 1.3.6.1.4.1.6296.101.20.1.2.9
		sleEponBaseControlOnuAutoUpgrade OBJECT-TYPE
			SYNTAX EnableFlag
			MAX-ACCESS read-write
			STATUS current
			DESCRIPTION
				"The status of ONU auto-upgrade."
			::= { sleEponBaseControl 9 }

		
		-- 1.3.6.1.4.1.6296.101.20.1.2.10
		sleEponBaseControlOnuAutoUpgradeRebootTime OBJECT-TYPE
			SYNTAX INTEGER (-1 | 0..23)
			UNITS "hour"
			MAX-ACCESS read-write
			STATUS current
			DESCRIPTION
				"The reboot-time of ONU auto-upgrade."
			::= { sleEponBaseControl 10 }

		
		-- 1.3.6.1.4.1.6296.101.20.1.2.11
		sleEponBaseControlOnuAgingTime OBJECT-TYPE
			SYNTAX Integer32 (0..30)
			UNITS "day"
			MAX-ACCESS read-write
			STATUS current
			DESCRIPTION
				"Description."
			::= { sleEponBaseControl 11 }

		
		-- 1.3.6.1.4.1.6296.101.20.1.2.12
		sleEponBaseControlAlarmStatus OBJECT-TYPE
			SYNTAX BITS
				{
				critical(0),
				major(1),
				minor(2)
				}
			MAX-ACCESS read-write
			STATUS current
			DESCRIPTION
				"Description."
			::= { sleEponBaseControl 12 }

		
		-- 1.3.6.1.4.1.6296.101.20.1.2.13
		sleEponBaseControlAlarmMode OBJECT-TYPE
			SYNTAX INTEGER
				{
				auto(0),
				manual(1)
				}
			MAX-ACCESS read-write
			STATUS current
			DESCRIPTION
				"Description."
			::= { sleEponBaseControl 13 }

		
--  1.3.6.1.4.1.6296.101.20.1.3
		-- 1.3.6.1.4.1.6296.101.20.1.3
		sleEponBaseNotification OBJECT IDENTIFIER ::= { sleEponBase 3 }

		
--  1.3.6.1.4.1.6296.101.20.1.3.1
		-- 1.3.6.1.4.1.6296.101.20.1.3.1
		sleEponBaseDefaultBandwidthChanged NOTIFICATION-TYPE
			OBJECTS { sleEponBaseControlRequest, sleEponBaseControlTimeStamp, sleEponBaseControlReqResult, sleEponBaseControlSlaPlatoMaxBandwdith, sleEponBaseControlDPShapingMaxBandwidth
				 }
			STATUS current
			DESCRIPTION 
				"Description."
			::= { sleEponBaseNotification 1 }

		
--  1.3.6.1.4.1.6296.101.20.1.3.2
		-- 1.3.6.1.4.1.6296.101.20.1.3.2
		sleEponBaseDefaultMaxHost NOTIFICATION-TYPE
			OBJECTS { sleEponBaseControlRequest, sleEponBaseControlTimeStamp, sleEponBaseControlReqResult, sleEponBaseControlPortMaxHost }
			STATUS current
			DESCRIPTION 
				"Description."
			::= { sleEponBaseNotification 2 }

		
		-- 1.3.6.1.4.1.6296.101.20.1.3.3
		sleEponBaseOnuAutoUpgradeChanged NOTIFICATION-TYPE
			OBJECTS { sleEponBaseControlRequest, sleEponBaseControlTimeStamp, sleEponBaseControlReqResult, sleEponBaseControlOnuAutoUpgrade, sleEponBaseControlOnuAutoUpgradeRebootTime
				 }
			STATUS current
			DESCRIPTION 
				"Description."
			::= { sleEponBaseNotification 3 }

		
		-- 1.3.6.1.4.1.6296.101.20.1.3.4
		sleEponBaseOnuAgingTimeChanged NOTIFICATION-TYPE
			OBJECTS { sleEponBaseControlRequest, sleEponBaseControlTimeStamp, sleEponBaseControlReqResult, sleEponBaseControlOnuAgingTime }
			STATUS current
			DESCRIPTION 
				"Description."
			::= { sleEponBaseNotification 4 }

		
		-- 1.3.6.1.4.1.6296.101.20.1.3.5
		sleEponBaseAlarmStatusChanged NOTIFICATION-TYPE
			OBJECTS { sleEponBaseControlRequest, sleEponBaseControlTimeStamp, sleEponBaseControlReqResult, sleEponBaseControlAlarmStatus }
			STATUS current
			DESCRIPTION 
				"Description."
			::= { sleEponBaseNotification 5 }

		
		-- 1.3.6.1.4.1.6296.101.20.1.3.6
		sleEponBaseAlarmModeChanged NOTIFICATION-TYPE
			OBJECTS { sleEponBaseControlRequest, sleEponBaseControlTimeStamp, sleEponBaseControlReqResult, sleEponBaseAlarmMode }
			STATUS current
			DESCRIPTION 
				"Description."
			::= { sleEponBaseNotification 6 }

		
--  1.3.6.1.4.1.6296.101.20.2
		-- 1.3.6.1.4.1.6296.101.20.2
		sleEponOlt OBJECT IDENTIFIER ::= { sleEpon 2 }

		
--  1.3.6.1.4.1.6296.101.20.2.1
		-- 1.3.6.1.4.1.6296.101.20.2.1
		sleEponOltTable OBJECT-TYPE
			SYNTAX SEQUENCE OF SleEponOltEntry
			MAX-ACCESS not-accessible
			STATUS current
			DESCRIPTION
				"Description."
			::= { sleEponOlt 1 }

		
--  1.3.6.1.4.1.6296.101.20.2.1.1
		-- 1.3.6.1.4.1.6296.101.20.2.1.1
		sleEponOltEntry OBJECT-TYPE
			SYNTAX SleEponOltEntry
			MAX-ACCESS not-accessible
			STATUS current
			DESCRIPTION
				"Description."
			INDEX { sleEponOltIndex }
			::= { sleEponOltTable 1 }

		
		SleEponOltEntry ::=
			SEQUENCE { 
				sleEponOltIndex
					INTEGER,
				sleEponOltRegMode
					INTEGER,
				sleEponOltStatus
					EnableFlag,
				sleEponOltEncryptionPolicy
					INTEGER,
				sleEponOltP2pAccessControl
					EnableFlag,
				sleEponOltDbaInternal
					EnableFlag,
				sleEponOltDbaCycle
					INTEGER,
				sleEponOltDbaDiscoveryFrequency
					INTEGER,
				sleEponOltDbaDiscoveryLength
					INTEGER,
				sleEponOltProfile
					OCTET STRING,
				sleEponOltTxFault
					INTEGER,
				sleEponOltLossOfSignal
					INTEGER,
				sleEponOltAdminRegMode
					INTEGER,
				sleEponOltSC
					EnableFlag,
				sleEponOltSCAutoOnuBlock
					EnableFlag,
				sleEponOltOperStatus
					INTEGER,
				sleEponOltFirmwareRev
					OCTET STRING
			 }

--  1.3.6.1.4.1.6296.101.20.2.1.1.1
		-- 1.3.6.1.4.1.6296.101.20.2.1.1.1
		sleEponOltIndex OBJECT-TYPE
			SYNTAX INTEGER (1..512)
			MAX-ACCESS read-only
			STATUS current
			DESCRIPTION
				"OLT port Index"
			::= { sleEponOltEntry 1 }

		
--  1.3.6.1.4.1.6296.101.20.2.1.1.2
		-- 1.3.6.1.4.1.6296.101.20.2.1.1.2
		sleEponOltRegMode OBJECT-TYPE
			SYNTAX INTEGER
				{
				auto(1),
				manual(2)
				}
			MAX-ACCESS read-only
			STATUS current
			DESCRIPTION
				"OLT port registeraton Mode {auto(1), manual(2)}"
			DEFVAL { auto }
			::= { sleEponOltEntry 2 }

		
--  1.3.6.1.4.1.6296.101.20.2.1.1.3
		-- 1.3.6.1.4.1.6296.101.20.2.1.1.3
		sleEponOltStatus OBJECT-TYPE
			SYNTAX EnableFlag
			MAX-ACCESS read-only
			STATUS current
			DESCRIPTION
				"OLT port status "
			::= { sleEponOltEntry 3 }

		
--  1.3.6.1.4.1.6296.101.20.2.1.1.4
		-- 1.3.6.1.4.1.6296.101.20.2.1.1.4
		sleEponOltEncryptionPolicy OBJECT-TYPE
			SYNTAX INTEGER
				{
				disable(1),
				down(2),
				both(3)
				}
			MAX-ACCESS read-only
			STATUS current
			DESCRIPTION
				"OLT port encryption policy"
			DEFVAL { disable }
			::= { sleEponOltEntry 4 }

		
--  1.3.6.1.4.1.6296.101.20.2.1.1.5
		-- 1.3.6.1.4.1.6296.101.20.2.1.1.5
		sleEponOltP2pAccessControl OBJECT-TYPE
			SYNTAX EnableFlag
			MAX-ACCESS read-only
			STATUS current
			DESCRIPTION
				"OLT port p2p access Control "
			DEFVAL { disable }
			::= { sleEponOltEntry 5 }

		
--  1.3.6.1.4.1.6296.101.20.2.1.1.6
		-- 1.3.6.1.4.1.6296.101.20.2.1.1.6
		sleEponOltDbaInternal OBJECT-TYPE
			SYNTAX EnableFlag
			MAX-ACCESS read-only
			STATUS current
			DESCRIPTION
				"OLT port DBA internal "
			DEFVAL { disable }
			::= { sleEponOltEntry 6 }

		
--  1.3.6.1.4.1.6296.101.20.2.1.1.7
		-- 1.3.6.1.4.1.6296.101.20.2.1.1.7
		sleEponOltDbaCycle OBJECT-TYPE
			SYNTAX INTEGER (0 | 200..16777215)
			MAX-ACCESS read-only
			STATUS current
			DESCRIPTION
				"OLT port DBA cycle "
			::= { sleEponOltEntry 7 }

		
--  1.3.6.1.4.1.6296.101.20.2.1.1.8
		-- 1.3.6.1.4.1.6296.101.20.2.1.1.8
		sleEponOltDbaDiscoveryFrequency OBJECT-TYPE
			SYNTAX INTEGER (0 | 1..65535)
			MAX-ACCESS read-only
			STATUS current
			DESCRIPTION
				"OLT port DBA Discovery Frequency"
			::= { sleEponOltEntry 8 }

		
--  1.3.6.1.4.1.6296.101.20.2.1.1.9
		-- 1.3.6.1.4.1.6296.101.20.2.1.1.9
		sleEponOltDbaDiscoveryLength OBJECT-TYPE
			SYNTAX INTEGER (0 | 1..65535)
			MAX-ACCESS read-only
			STATUS current
			DESCRIPTION
				"OLT port DBA Discovery Length"
			::= { sleEponOltEntry 9 }

		
--  1.3.6.1.4.1.6296.101.20.2.1.1.10
		-- 1.3.6.1.4.1.6296.101.20.2.1.1.10
		sleEponOltProfile OBJECT-TYPE
			SYNTAX OCTET STRING (SIZE (1..64))
			MAX-ACCESS read-only
			STATUS current
			DESCRIPTION
				"OLT port auto profile name"
			::= { sleEponOltEntry 10 }

		
--  1.3.6.1.4.1.6296.101.20.2.1.1.11
		-- 1.3.6.1.4.1.6296.101.20.2.1.1.11
		sleEponOltTxFault OBJECT-TYPE
			SYNTAX INTEGER
				{
				unknown(0),
				normal(1),
				lagerFault(2)
				}
			MAX-ACCESS read-only
			STATUS current
			DESCRIPTION
				"This object indicates the status of Tx fault."
			::= { sleEponOltEntry 11 }

		
--  1.3.6.1.4.1.6296.101.20.2.1.1.12
		-- 1.3.6.1.4.1.6296.101.20.2.1.1.12
		sleEponOltLossOfSignal OBJECT-TYPE
			SYNTAX INTEGER
				{
				unknown(0),
				normal(1),
				loss(2)
				}
			MAX-ACCESS read-only
			STATUS current
			DESCRIPTION
				"This object indicates the status of loss of signal"
			::= { sleEponOltEntry 12 }

		
--  1.3.6.1.4.1.6296.101.20.2.1.1.13
		-- 1.3.6.1.4.1.6296.101.20.2.1.1.13
		sleEponOltAdminRegMode OBJECT-TYPE
			SYNTAX INTEGER
				{
				auto(1),
				manual(2),
				autoToManual(3),
				webBasedRegistry(4)
				}
			MAX-ACCESS read-only
			STATUS current
			DESCRIPTION
				"OLT port admin registeraton Mode {auto(1), manual(2), auto-to-manual(3), web-based-registry(4)}"
			::= { sleEponOltEntry 13 }

		
--  1.3.6.1.4.1.6296.101.20.2.1.1.14
		-- 1.3.6.1.4.1.6296.101.20.2.1.1.14
		sleEponOltSC OBJECT-TYPE
			SYNTAX EnableFlag
			MAX-ACCESS read-only
			STATUS current
			DESCRIPTION
				"Description."
			::= { sleEponOltEntry 14 }

		
--  1.3.6.1.4.1.6296.101.20.2.1.1.15
		-- 1.3.6.1.4.1.6296.101.20.2.1.1.15
		sleEponOltSCAutoOnuBlock OBJECT-TYPE
			SYNTAX EnableFlag
			MAX-ACCESS read-only
			STATUS current
			DESCRIPTION
				"Description."
			::= { sleEponOltEntry 15 }

		
--  1.3.6.1.4.1.6296.101.20.2.1.1.16
		-- 1.3.6.1.4.1.6296.101.20.2.1.1.16
		sleEponOltOperStatus OBJECT-TYPE
			SYNTAX INTEGER
				{
				up(1),
				down(2),
				cableDown(3)
				}
			MAX-ACCESS read-only
			STATUS current
			DESCRIPTION
				"Description."
			::= { sleEponOltEntry 16 }

		
		-- 1.3.6.1.4.1.6296.101.20.2.1.1.17
		sleEponOltFirmwareRev OBJECT-TYPE
			SYNTAX OCTET STRING (SIZE (1..64))
			MAX-ACCESS read-only
			STATUS current
			DESCRIPTION
				"The firmware revision of OLT port."
			::= { sleEponOltEntry 17 }

		
--  1.3.6.1.4.1.6296.101.20.2.2
		-- 1.3.6.1.4.1.6296.101.20.2.2
		sleEponOltControl OBJECT IDENTIFIER ::= { sleEponOlt 2 }

		
--  1.3.6.1.4.1.6296.101.20.2.2.1
		-- 1.3.6.1.4.1.6296.101.20.2.2.1
		sleEponOltControlRequest OBJECT-TYPE
			SYNTAX INTEGER
				{
				setEponOltRegMode(1),
				setEponOltStatus(2),
				setEponOltAttributes(3),
				setEponOltProfile(4),
				setEponOltAttributeSC(5),
				setEponOltUpgrade(6),
				setEponOltReset(7)
				}
			MAX-ACCESS read-write
			STATUS current
			DESCRIPTION
				"The request of a user command"
			::= { sleEponOltControl 1 }

		
--  1.3.6.1.4.1.6296.101.20.2.2.2
		-- 1.3.6.1.4.1.6296.101.20.2.2.2
		sleEponOltControlStatus OBJECT-TYPE
			SYNTAX SleControlStatusType
			MAX-ACCESS read-only
			STATUS current
			DESCRIPTION
				"The status of user command"
			::= { sleEponOltControl 2 }

		
--  1.3.6.1.4.1.6296.101.20.2.2.3
		-- 1.3.6.1.4.1.6296.101.20.2.2.3
		sleEponOltControlTimer OBJECT-TYPE
			SYNTAX Gauge32
			MAX-ACCESS read-write
			STATUS current
			DESCRIPTION
				"The maximum time for the manager for a long running user command"
			::= { sleEponOltControl 3 }

		
--  1.3.6.1.4.1.6296.101.20.2.2.4
		-- 1.3.6.1.4.1.6296.101.20.2.2.4
		sleEponOltControlTimeStamp OBJECT-TYPE
			SYNTAX TimeTicks
			MAX-ACCESS read-only
			STATUS current
			DESCRIPTION
				"The time stamp of the last command(end of command)"
			::= { sleEponOltControl 4 }

		
--  1.3.6.1.4.1.6296.101.20.2.2.5
		-- 1.3.6.1.4.1.6296.101.20.2.2.5
		sleEponOltControlReqResult OBJECT-TYPE
			SYNTAX SleControlRequestResultType
			MAX-ACCESS read-only
			STATUS current
			DESCRIPTION
				"The result of the last user command"
			::= { sleEponOltControl 5 }

		
--  1.3.6.1.4.1.6296.101.20.2.2.6
		-- 1.3.6.1.4.1.6296.101.20.2.2.6
		sleEponOltControlOltIndex OBJECT-TYPE
			SYNTAX Integer32
			MAX-ACCESS read-write
			STATUS current
			DESCRIPTION
				"OLT port Index"
			::= { sleEponOltControl 6 }

		
--  1.3.6.1.4.1.6296.101.20.2.2.7
		-- 1.3.6.1.4.1.6296.101.20.2.2.7
		sleEponOltControlRegMode OBJECT-TYPE
			SYNTAX INTEGER
				{
				auto(1),
				manual(2),
				fixed(3),
				autoToManual(4),
				webBasedRegistry(5)
				}
			MAX-ACCESS read-write
			STATUS current
			DESCRIPTION
				"auto(1), manual(2), fixed(3) / DEFVAL : auto"
			DEFVAL { auto }
			::= { sleEponOltControl 7 }

		
--  1.3.6.1.4.1.6296.101.20.2.2.8
		-- 1.3.6.1.4.1.6296.101.20.2.2.8
		sleEponOltControlOltStatus OBJECT-TYPE
			SYNTAX EnableFlag
			MAX-ACCESS read-write
			STATUS current
			DESCRIPTION
				"enable(1), disable(2)"
			::= { sleEponOltControl 8 }

		
--  1.3.6.1.4.1.6296.101.20.2.2.9
		-- 1.3.6.1.4.1.6296.101.20.2.2.9
		sleEponOltControlEncryptionPolicy OBJECT-TYPE
			SYNTAX INTEGER
				{
				disable(1),
				down(2),
				both(3)
				}
			MAX-ACCESS read-write
			STATUS current
			DESCRIPTION
				"disable(1), down(2), both(3) / DEFVAL : disable"
			DEFVAL { disable }
			::= { sleEponOltControl 9 }

		
--  1.3.6.1.4.1.6296.101.20.2.2.10
		-- 1.3.6.1.4.1.6296.101.20.2.2.10
		sleEponOltControlP2pAccessControl OBJECT-TYPE
			SYNTAX EnableFlag
			MAX-ACCESS read-write
			STATUS current
			DESCRIPTION
				"enable(1), disable(2)  / DEFVAL : disable "
			DEFVAL { disable }
			::= { sleEponOltControl 10 }

		
--  1.3.6.1.4.1.6296.101.20.2.2.11
		-- 1.3.6.1.4.1.6296.101.20.2.2.11
		sleEponOltControlDbaInternal OBJECT-TYPE
			SYNTAX EnableFlag
			MAX-ACCESS read-write
			STATUS current
			DESCRIPTION
				"enable(1), disable(2)  / DEFVAL : disable"
			DEFVAL { disable }
			::= { sleEponOltControl 11 }

		
--  1.3.6.1.4.1.6296.101.20.2.2.12
		-- 1.3.6.1.4.1.6296.101.20.2.2.12
		sleEponOltControlDbaCycle OBJECT-TYPE
			SYNTAX INTEGER (200..16777215)
			MAX-ACCESS read-write
			STATUS current
			DESCRIPTION
				"< 0 | 200..16777215>  / DEFVAL : 65536"
			DEFVAL { 65536 }
			::= { sleEponOltControl 12 }

		
--  1.3.6.1.4.1.6296.101.20.2.2.13
		-- 1.3.6.1.4.1.6296.101.20.2.2.13
		sleEponOltControlDbaDiscoveryFrequency OBJECT-TYPE
			SYNTAX INTEGER (1..65535)
			MAX-ACCESS read-write
			STATUS current
			DESCRIPTION
				"< 0 | 1..65535>  /DEFVAL : 1792"
			DEFVAL { 1792 }
			::= { sleEponOltControl 13 }

		
--  1.3.6.1.4.1.6296.101.20.2.2.14
		-- 1.3.6.1.4.1.6296.101.20.2.2.14
		sleEponOltControlDbaDiscoveryLength OBJECT-TYPE
			SYNTAX INTEGER (1..65535)
			MAX-ACCESS read-write
			STATUS current
			DESCRIPTION
				"< 0 | 1..65535>  /DEFVAL : 500"
			DEFVAL { 500 }
			::= { sleEponOltControl 14 }

		
--  1.3.6.1.4.1.6296.101.20.2.2.15
		-- 1.3.6.1.4.1.6296.101.20.2.2.15
		sleEponOltControlProfile OBJECT-TYPE
			SYNTAX OCTET STRING (SIZE (1..64))
			MAX-ACCESS read-write
			STATUS current
			DESCRIPTION
				"OLT port auto profile name"
			::= { sleEponOltControl 15 }

		
--  1.3.6.1.4.1.6296.101.20.2.2.16
		-- 1.3.6.1.4.1.6296.101.20.2.2.16
		sleEponOltControlSC OBJECT-TYPE
			SYNTAX EnableFlag
			MAX-ACCESS read-write
			STATUS current
			DESCRIPTION
				"Description."
			::= { sleEponOltControl 16 }

		
--  1.3.6.1.4.1.6296.101.20.2.2.17
		-- 1.3.6.1.4.1.6296.101.20.2.2.17
		sleEponOltControlSCAutoOnuBlock OBJECT-TYPE
			SYNTAX EnableFlag
			MAX-ACCESS read-write
			STATUS current
			DESCRIPTION
				"Description."
			::= { sleEponOltControl 17 }

		
--  1.3.6.1.4.1.6296.101.20.2.2.18
		-- 1.3.6.1.4.1.6296.101.20.2.2.18
		sleEponOltControlUpgradeFilename OBJECT-TYPE
			SYNTAX OCTET STRING (SIZE (1..64))
			MAX-ACCESS read-write
			STATUS current
			DESCRIPTION
				"Description."
			::= { sleEponOltControl 18 }

		
--  1.3.6.1.4.1.6296.101.20.2.3
		-- 1.3.6.1.4.1.6296.101.20.2.3
		sleEponOltNotification OBJECT IDENTIFIER ::= { sleEponOlt 3 }

		
--  1.3.6.1.4.1.6296.101.20.2.3.1
		-- 1.3.6.1.4.1.6296.101.20.2.3.1
		sleEponOltRegModeChanged NOTIFICATION-TYPE
			OBJECTS { sleEponOltControlRequest, sleEponOltControlTimeStamp, sleEponOltControlReqResult, sleEponOltControlOltIndex, sleEponOltControlRegMode
				 }
			STATUS current
			DESCRIPTION 
				"Description."
			::= { sleEponOltNotification 1 }

		
--  1.3.6.1.4.1.6296.101.20.2.3.2
		-- 1.3.6.1.4.1.6296.101.20.2.3.2
		sleEponOltStatusChanged NOTIFICATION-TYPE
			OBJECTS { sleEponOltControlRequest, sleEponOltControlTimeStamp, sleEponOltControlReqResult, sleEponOltControlOltIndex, sleEponOltControlOltStatus
				 }
			STATUS current
			DESCRIPTION 
				"Description."
			::= { sleEponOltNotification 2 }

		
--  1.3.6.1.4.1.6296.101.20.2.3.3
		-- 1.3.6.1.4.1.6296.101.20.2.3.3
		sleEponOltAttributesChanged NOTIFICATION-TYPE
			OBJECTS { sleEponOltControlRequest, sleEponOltControlTimeStamp, sleEponOltControlReqResult, sleEponOltControlOltIndex, sleEponOltControlDbaInternal, 
				sleEponOltControlDbaCycle, sleEponOltControlDbaDiscoveryFrequency, sleEponOltControlDbaDiscoveryLength }
			STATUS current
			DESCRIPTION 
				"Description."
			::= { sleEponOltNotification 3 }

		
--  1.3.6.1.4.1.6296.101.20.2.3.4
		-- 1.3.6.1.4.1.6296.101.20.2.3.4
		sleEponOltProfileChanged NOTIFICATION-TYPE
			OBJECTS { sleEponOltControlRequest, sleEponOltControlTimeStamp, sleEponOltControlReqResult, sleEponOltControlOltIndex, sleEponOltControlProfile
				 }
			STATUS current
			DESCRIPTION 
				"Description."
			::= { sleEponOltNotification 4 }

		
--  1.3.6.1.4.1.6296.101.20.2.3.5
		-- 1.3.6.1.4.1.6296.101.20.2.3.5
		sleEponOltSCChanged NOTIFICATION-TYPE
			OBJECTS { sleEponOltControlRequest, sleEponOltControlTimeStamp, sleEponOltControlReqResult, sleEponOltControlOltIndex, sleEponOltControlSC, 
				sleEponOltControlSCAutoOnuBlock }
			STATUS current
			DESCRIPTION 
				"Description."
			::= { sleEponOltNotification 5 }

		
--  1.3.6.1.4.1.6296.101.20.2.3.6
		-- 1.3.6.1.4.1.6296.101.20.2.3.6
		sleEponOltUpgraded NOTIFICATION-TYPE
			OBJECTS { sleEponOltControlRequest, sleEponOltControlTimeStamp, sleEponOltControlReqResult, sleEponOltControlOltIndex, sleEponOltControlUpgradeFilename
				 }
			STATUS current
			DESCRIPTION 
				"Description."
			::= { sleEponOltNotification 6 }

		
--  1.3.6.1.4.1.6296.101.20.2.3.7
		-- 1.3.6.1.4.1.6296.101.20.2.3.7
		sleEponOltReset NOTIFICATION-TYPE
			OBJECTS { sleEponOltControlRequest, sleEponOltControlTimeStamp, sleEponOltControlReqResult, sleEponOltControlOltIndex }
			STATUS current
			DESCRIPTION 
				"Description."
			::= { sleEponOltNotification 7 }

		
--  1.3.6.1.4.1.6296.101.20.3
		-- 1.3.6.1.4.1.6296.101.20.3
		sleEponOnu OBJECT IDENTIFIER ::= { sleEpon 3 }

		
--  1.3.6.1.4.1.6296.101.20.3.1
		-- 1.3.6.1.4.1.6296.101.20.3.1
		sleEponOnuTable OBJECT-TYPE
			SYNTAX SEQUENCE OF SleEponOnuEntry
			MAX-ACCESS not-accessible
			STATUS current
			DESCRIPTION
				"Description."
			::= { sleEponOnu 1 }

		
--  1.3.6.1.4.1.6296.101.20.3.1.1
		-- 1.3.6.1.4.1.6296.101.20.3.1.1
		sleEponOnuEntry OBJECT-TYPE
			SYNTAX SleEponOnuEntry
			MAX-ACCESS not-accessible
			STATUS current
			DESCRIPTION
				"Description."
			INDEX { sleEponOltIndex, sleEponOnuIndex }
			::= { sleEponOnuTable 1 }

		
		SleEponOnuEntry ::=
			SEQUENCE { 
				sleEponOnuIndex
					INTEGER,
				sleEponOnuLlid
					INTEGER,
				sleEponOnuRegMode
					INTEGER,
				sleEponOnuStatus
					INTEGER,
				sleEponOnuMacAddress
					MacAddress,
				sleEponOnuRtt
					Integer32,
				sleEponOnuDescription
					OCTET STRING,
				sleEponOnuProfile
					OCTET STRING,
				sleEponOnuLoopbackProvision
					Integer32,
				sleEponOnuVendor
					OCTET STRING,
				sleEponOnuFirmwareRev
					OCTET STRING,
				sleEponOnuTxPowerOffTimer
					INTEGER
			 }

--  1.3.6.1.4.1.6296.101.20.3.1.1.1
		-- 1.3.6.1.4.1.6296.101.20.3.1.1.1
		sleEponOnuIndex OBJECT-TYPE
			SYNTAX INTEGER (1..32)
			MAX-ACCESS read-only
			STATUS current
			DESCRIPTION
				"ONU Index"
			::= { sleEponOnuEntry 1 }

		
--  1.3.6.1.4.1.6296.101.20.3.1.1.2
		-- 1.3.6.1.4.1.6296.101.20.3.1.1.2
		sleEponOnuLlid OBJECT-TYPE
			SYNTAX INTEGER (1..32)
			MAX-ACCESS read-only
			STATUS current
			DESCRIPTION
				"ONU LLID"
			::= { sleEponOnuEntry 2 }

		
--  1.3.6.1.4.1.6296.101.20.3.1.1.3
		-- 1.3.6.1.4.1.6296.101.20.3.1.1.3
		sleEponOnuRegMode OBJECT-TYPE
			SYNTAX INTEGER
				{
				auto(1),
				manual(2)
				}
			MAX-ACCESS read-only
			STATUS current
			DESCRIPTION
				"ONU registration mode"
			DEFVAL { auto }
			::= { sleEponOnuEntry 3 }

		
--  1.3.6.1.4.1.6296.101.20.3.1.1.4
		-- 1.3.6.1.4.1.6296.101.20.3.1.1.4
		sleEponOnuStatus OBJECT-TYPE
			SYNTAX INTEGER
				{
				inactive(1),
				deny(2),
				block(3),
				active(4)
				}
			MAX-ACCESS read-only
			STATUS current
			DESCRIPTION
				"ONU current status"
			::= { sleEponOnuEntry 4 }

		
--  1.3.6.1.4.1.6296.101.20.3.1.1.5
		-- 1.3.6.1.4.1.6296.101.20.3.1.1.5
		sleEponOnuMacAddress OBJECT-TYPE
			SYNTAX MacAddress
			MAX-ACCESS read-only
			STATUS current
			DESCRIPTION
				"ONU Hardware address"
			::= { sleEponOnuEntry 5 }

		
--  1.3.6.1.4.1.6296.101.20.3.1.1.6
		-- 1.3.6.1.4.1.6296.101.20.3.1.1.6
		sleEponOnuRtt OBJECT-TYPE
			SYNTAX Integer32
			MAX-ACCESS read-only
			STATUS current
			DESCRIPTION
				"ONU Round Trip Time"
			::= { sleEponOnuEntry 6 }

		
--  1.3.6.1.4.1.6296.101.20.3.1.1.7
		-- 1.3.6.1.4.1.6296.101.20.3.1.1.7
		sleEponOnuDescription OBJECT-TYPE
			SYNTAX OCTET STRING (SIZE (1..64))
			MAX-ACCESS read-only
			STATUS current
			DESCRIPTION
				"ONU Description"
			::= { sleEponOnuEntry 7 }

		
--  1.3.6.1.4.1.6296.101.20.3.1.1.8
		-- 1.3.6.1.4.1.6296.101.20.3.1.1.8
		sleEponOnuProfile OBJECT-TYPE
			SYNTAX OCTET STRING (SIZE (1..64))
			MAX-ACCESS read-only
			STATUS current
			DESCRIPTION
				"ONU assigned-profile"
			::= { sleEponOnuEntry 8 }

		
--  1.3.6.1.4.1.6296.101.20.3.1.1.9
		-- 1.3.6.1.4.1.6296.101.20.3.1.1.9
		sleEponOnuLoopbackProvision OBJECT-TYPE
			SYNTAX Integer32
			MAX-ACCESS read-write
			STATUS current
			DESCRIPTION
				"ONU loopback test result
				-2 : not exist
				-1 : fail
				 X > 0  : Time.
				"
			::= { sleEponOnuEntry 9 }

		
--  1.3.6.1.4.1.6296.101.20.3.1.1.10
		-- 1.3.6.1.4.1.6296.101.20.3.1.1.10
		sleEponOnuVendor OBJECT-TYPE
			SYNTAX OCTET STRING
			MAX-ACCESS read-only
			STATUS current
			DESCRIPTION
				"The name of ONU vendor"
			::= { sleEponOnuEntry 10 }

		
--  1.3.6.1.4.1.6296.101.20.3.1.1.11
		-- 1.3.6.1.4.1.6296.101.20.3.1.1.11
		sleEponOnuFirmwareRev OBJECT-TYPE
			SYNTAX OCTET STRING
			MAX-ACCESS read-only
			STATUS current
			DESCRIPTION
				"The vendor-specific firmware revision"
			::= { sleEponOnuEntry 11 }

		
--  1.3.6.1.4.1.6296.101.20.3.1.1.12
		-- 1.3.6.1.4.1.6296.101.20.3.1.1.12
		sleEponOnuTxPowerOffTimer OBJECT-TYPE
			SYNTAX INTEGER (0 | 10..65535)
			MAX-ACCESS read-only
			STATUS current
			DESCRIPTION
				"Description."
			::= { sleEponOnuEntry 12 }

		
--  1.3.6.1.4.1.6296.101.20.3.2
		-- 1.3.6.1.4.1.6296.101.20.3.2
		sleEponOnuControl OBJECT IDENTIFIER ::= { sleEponOnu 2 }

		
--  1.3.6.1.4.1.6296.101.20.3.2.1
		-- 1.3.6.1.4.1.6296.101.20.3.2.1
		sleEponOnuControlRequest OBJECT-TYPE
			SYNTAX INTEGER
				{
				setEponOnuRegMode(1),
				setEponOnuStatus(2),
				setEponOnuAttributes(3),
				setEponOnuRegister(4),
				setEponOnuDeregister(5),
				setEponOnuProfile(6),
				setEponOnuUpgrade(7),
				setEPonOnuLoopbackProvision(8),
				setEponOnuTxPowerOffTimer(9),
				setEponOnuProfileByMac(10),
				setEponOnuDeregisterByMac(11)
				}
			MAX-ACCESS read-write
			STATUS current
			DESCRIPTION
				"The request of a user command"
			::= { sleEponOnuControl 1 }

		
--  1.3.6.1.4.1.6296.101.20.3.2.2
		-- 1.3.6.1.4.1.6296.101.20.3.2.2
		sleEponOnuControlStatus OBJECT-TYPE
			SYNTAX SleControlStatusType
			MAX-ACCESS read-only
			STATUS current
			DESCRIPTION
				"The status of user command"
			::= { sleEponOnuControl 2 }

		
--  1.3.6.1.4.1.6296.101.20.3.2.3
		-- 1.3.6.1.4.1.6296.101.20.3.2.3
		sleEponOnuControlTimer OBJECT-TYPE
			SYNTAX Gauge32
			MAX-ACCESS read-write
			STATUS current
			DESCRIPTION
				"The maximum time for the manager for a long running user command"
			::= { sleEponOnuControl 3 }

		
--  1.3.6.1.4.1.6296.101.20.3.2.4
		-- 1.3.6.1.4.1.6296.101.20.3.2.4
		sleEponOnuControlTimeStamp OBJECT-TYPE
			SYNTAX TimeTicks
			MAX-ACCESS read-only
			STATUS current
			DESCRIPTION
				"The time stamp of the last command(end of command)"
			::= { sleEponOnuControl 4 }

		
--  1.3.6.1.4.1.6296.101.20.3.2.5
		-- 1.3.6.1.4.1.6296.101.20.3.2.5
		sleEponOnuControlReqResult OBJECT-TYPE
			SYNTAX SleControlRequestResultType
			MAX-ACCESS read-only
			STATUS current
			DESCRIPTION
				"The result of the last user command"
			::= { sleEponOnuControl 5 }

		
--  1.3.6.1.4.1.6296.101.20.3.2.6
		-- 1.3.6.1.4.1.6296.101.20.3.2.6
		sleEponOnuControlOltIndex OBJECT-TYPE
			SYNTAX INTEGER (1..512)
			MAX-ACCESS read-write
			STATUS current
			DESCRIPTION
				"OLT index"
			::= { sleEponOnuControl 6 }

		
--  1.3.6.1.4.1.6296.101.20.3.2.7
		-- 1.3.6.1.4.1.6296.101.20.3.2.7
		sleEponOnuControlOnuIndex OBJECT-TYPE
			SYNTAX INTEGER (1..32)
			MAX-ACCESS read-write
			STATUS current
			DESCRIPTION
				"ONU index <1-32>"
			::= { sleEponOnuControl 7 }

		
--  1.3.6.1.4.1.6296.101.20.3.2.8
		-- 1.3.6.1.4.1.6296.101.20.3.2.8
		sleEponOnuControlRegMode OBJECT-TYPE
			SYNTAX INTEGER
				{
				auto(1),
				manual(2)
				}
			MAX-ACCESS read-write
			STATUS current
			DESCRIPTION
				"ONU register mode {auto(1), manual(2)}"
			DEFVAL { auto }
			::= { sleEponOnuControl 8 }

		
--  1.3.6.1.4.1.6296.101.20.3.2.9
		-- 1.3.6.1.4.1.6296.101.20.3.2.9
		sleEponOnuControlOnuStatus OBJECT-TYPE
			SYNTAX INTEGER
				{
				inactive(1),
				deny(2),
				block(3),
				active(4),
				reset(5)
				}
			MAX-ACCESS read-write
			STATUS current
			DESCRIPTION
				"1 : inactive 
				2 : deny 
				3 : block
				4 : active
				5 : reset
				"
			::= { sleEponOnuControl 9 }

		
--  1.3.6.1.4.1.6296.101.20.3.2.10
		-- 1.3.6.1.4.1.6296.101.20.3.2.10
		sleEponOnuControlMacAddress OBJECT-TYPE
			SYNTAX MacAddress
			MAX-ACCESS read-write
			STATUS current
			DESCRIPTION
				"ONU MAC address"
			::= { sleEponOnuControl 10 }

		
--  1.3.6.1.4.1.6296.101.20.3.2.11
		-- 1.3.6.1.4.1.6296.101.20.3.2.11
		sleEponOnuControlDescription OBJECT-TYPE
			SYNTAX OCTET STRING
			MAX-ACCESS read-write
			STATUS current
			DESCRIPTION
				"ONU description"
			::= { sleEponOnuControl 11 }

		
--  1.3.6.1.4.1.6296.101.20.3.2.12
		-- 1.3.6.1.4.1.6296.101.20.3.2.12
		sleEponOnuControlProfile OBJECT-TYPE
			SYNTAX OCTET STRING (SIZE (1..64))
			MAX-ACCESS read-write
			STATUS current
			DESCRIPTION
				"Profile name"
			::= { sleEponOnuControl 12 }

		
--  1.3.6.1.4.1.6296.101.20.3.2.13
		-- 1.3.6.1.4.1.6296.101.20.3.2.13
		sleEponOnuControlUpgradePath OBJECT-TYPE
			SYNTAX OCTET STRING (SIZE (1..64))
			UNITS "byte"
			MAX-ACCESS read-write
			STATUS current
			DESCRIPTION
				"Upgrade path"
			::= { sleEponOnuControl 13 }

		
--  1.3.6.1.4.1.6296.101.20.3.2.14
		-- 1.3.6.1.4.1.6296.101.20.3.2.14
		sleEponOnuControlLoopbackProvision OBJECT-TYPE
			SYNTAX INTEGER { test(1) }
			MAX-ACCESS read-write
			STATUS current
			DESCRIPTION
				"1 : test"
			::= { sleEponOnuControl 14 }

		
--  1.3.6.1.4.1.6296.101.20.3.2.15
		-- 1.3.6.1.4.1.6296.101.20.3.2.15
		sleEponOnuControlTxPowerOffTimer OBJECT-TYPE
			SYNTAX INTEGER (0 | 10..65535)
			MAX-ACCESS read-write
			STATUS current
			DESCRIPTION
				"Description."
			::= { sleEponOnuControl 15 }

		
--  1.3.6.1.4.1.6296.101.20.3.3
		-- 1.3.6.1.4.1.6296.101.20.3.3
		sleEponOnuNotification OBJECT IDENTIFIER ::= { sleEponOnu 3 }

		
--  1.3.6.1.4.1.6296.101.20.3.3.1
		-- 1.3.6.1.4.1.6296.101.20.3.3.1
		sleEponOnuRegModeChanged NOTIFICATION-TYPE
			OBJECTS { sleEponOnuControlRequest, sleEponOnuControlTimeStamp, sleEponOnuControlReqResult, sleEponOnuControlOltIndex, sleEponOnuControlOnuIndex, 
				sleEponOnuControlRegMode }
			STATUS current
			DESCRIPTION 
				"Description."
			::= { sleEponOnuNotification 1 }

		
--  1.3.6.1.4.1.6296.101.20.3.3.2
		-- 1.3.6.1.4.1.6296.101.20.3.3.2
		sleEponOnuStatusChanged NOTIFICATION-TYPE
			OBJECTS { sleEponOnuControlRequest, sleEponOnuControlTimeStamp, sleEponOnuControlReqResult, sleEponOnuControlOltIndex, sleEponOnuControlOnuIndex, 
				sleEponOnuControlOnuStatus }
			STATUS current
			DESCRIPTION 
				"Description."
			::= { sleEponOnuNotification 2 }

		
--  1.3.6.1.4.1.6296.101.20.3.3.3
		-- 1.3.6.1.4.1.6296.101.20.3.3.3
		sleEponOnuAttibutesChanged NOTIFICATION-TYPE
			OBJECTS { sleEponOnuControlRequest, sleEponOnuControlTimeStamp, sleEponOnuControlReqResult, sleEponOnuControlOltIndex, sleEponOnuControlOnuIndex, 
				sleEponOnuControlDescription }
			STATUS current
			DESCRIPTION 
				"Description."
			::= { sleEponOnuNotification 3 }

		
--  1.3.6.1.4.1.6296.101.20.3.3.4
		-- 1.3.6.1.4.1.6296.101.20.3.3.4
		sleEponOnuRegistered NOTIFICATION-TYPE
			OBJECTS { sleEponOnuControlRequest, sleEponOnuControlTimeStamp, sleEponOnuControlReqResult, sleEponOnuControlOltIndex, sleEponOnuControlOnuIndex, 
				sleEponOnuControlMacAddress, sleEponOnuControlDescription }
			STATUS current
			DESCRIPTION 
				"Description."
			::= { sleEponOnuNotification 4 }

		
--  1.3.6.1.4.1.6296.101.20.3.3.5
		-- 1.3.6.1.4.1.6296.101.20.3.3.5
		sleEponOnuDeregistered NOTIFICATION-TYPE
			OBJECTS { sleEponOnuControlRequest, sleEponOnuControlTimeStamp, sleEponOnuControlReqResult, sleEponOnuControlOltIndex, sleEponOnuControlOnuIndex
				 }
			STATUS current
			DESCRIPTION 
				"Description."
			::= { sleEponOnuNotification 5 }

		
--  1.3.6.1.4.1.6296.101.20.3.3.6
		-- 1.3.6.1.4.1.6296.101.20.3.3.6
		sleEponOnuProfileChanged NOTIFICATION-TYPE
			OBJECTS { sleEponOnuControlRequest, sleEponOnuControlTimeStamp, sleEponOnuControlReqResult, sleEponOnuControlOltIndex, sleEponOnuControlOnuIndex, 
				sleEponOnuControlProfile }
			STATUS current
			DESCRIPTION 
				"Description."
			::= { sleEponOnuNotification 6 }

		
--  1.3.6.1.4.1.6296.101.20.3.3.7
		-- 1.3.6.1.4.1.6296.101.20.3.3.7
		sleEponOnuUpgraded NOTIFICATION-TYPE
			OBJECTS { sleEponOnuControlRequest, sleEponOnuControlTimeStamp, sleEponOnuControlReqResult, sleEponOnuControlOltIndex, sleEponOnuControlOnuIndex, 
				sleEponOnuControlUpgradePath }
			STATUS current
			DESCRIPTION 
				"Description."
			::= { sleEponOnuNotification 7 }

		
--  1.3.6.1.4.1.6296.101.20.3.3.8
		-- 1.3.6.1.4.1.6296.101.20.3.3.8
		sleEponOnuLoopbackProvisioned NOTIFICATION-TYPE
			OBJECTS { sleEponOnuControlRequest, sleEponOnuControlTimeStamp, sleEponOnuControlReqResult, sleEponOnuControlOltIndex, sleEponOnuControlOnuIndex, 
				sleEponOnuControlLoopbackProvision }
			STATUS current
			DESCRIPTION 
				"Description."
			::= { sleEponOnuNotification 8 }

		
--  1.3.6.1.4.1.6296.101.20.3.3.10
		-- 1.3.6.1.4.1.6296.101.20.3.3.9
		sleEponOnuTxPowerOffChanged NOTIFICATION-TYPE
			OBJECTS { sleEponOnuControlRequest, sleEponOnuControlTimeStamp, sleEponOnuControlReqResult, sleEponOnuControlOltIndex, sleEponOnuControlOnuIndex, 
				sleEponOnuControlTxPowerOffTimer }
			STATUS current
			DESCRIPTION 
				"Description."
			::= { sleEponOnuNotification 9 }

		
		-- 1.3.6.1.4.1.6296.101.20.3.3.10
		sleEponOnuFristRegisteredOnAutoToManual NOTIFICATION-TYPE
			OBJECTS { sysDescr, sleEponOltIndex, sleEponOnuIndex }
			STATUS current
			DESCRIPTION 
				"Description."
			::= { sleEponOnuNotification 10 }

		
--  1.3.6.1.4.1.6296.101.20.3.3.6
		-- 1.3.6.1.4.1.6296.101.20.3.3.11
		sleEponOnuProfileChangedByMac NOTIFICATION-TYPE
			OBJECTS { sleEponOnuControlRequest, sleEponOnuControlTimeStamp, sleEponOnuControlReqResult, sleEponOnuControlOltIndex, sleEponOnuControlMacAddress, 
				sleEponOnuControlProfile }
			STATUS current
			DESCRIPTION 
				"Description."
			::= { sleEponOnuNotification 11 }

		
--  1.3.6.1.4.1.6296.101.20.3.3.5
		-- 1.3.6.1.4.1.6296.101.20.3.3.12
		sleEponOnuDeregisteredByMac NOTIFICATION-TYPE
			OBJECTS { sleEponOnuControlRequest, sleEponOnuControlTimeStamp, sleEponOnuControlReqResult, sleEponOnuControlOltIndex, sleEponOnuControlMacAddress
				 }
			STATUS current
			DESCRIPTION 
				"Description."
			::= { sleEponOnuNotification 12 }

		
--  1.3.6.1.4.1.6296.101.20.4
		-- 1.3.6.1.4.1.6296.101.20.4
		sleEponOnuBridge OBJECT IDENTIFIER ::= { sleEpon 4 }

		
--  1.3.6.1.4.1.6296.101.20.4.1
		-- 1.3.6.1.4.1.6296.101.20.4.1
		sleEponOnuVlan OBJECT IDENTIFIER ::= { sleEponOnuBridge 1 }

		
--  1.3.6.1.4.1.6296.101.20.4.1.1
		-- 1.3.6.1.4.1.6296.101.20.4.1.1
		sleEponOnuVlanTable OBJECT-TYPE
			SYNTAX SEQUENCE OF SleEponOnuVlanEntry
			MAX-ACCESS not-accessible
			STATUS current
			DESCRIPTION
				"Description."
			::= { sleEponOnuVlan 1 }

		
--  1.3.6.1.4.1.6296.101.20.4.1.1.1
		-- 1.3.6.1.4.1.6296.101.20.4.1.1.1
		sleEponOnuVlanEntry OBJECT-TYPE
			SYNTAX SleEponOnuVlanEntry
			MAX-ACCESS not-accessible
			STATUS current
			DESCRIPTION
				"Description."
			INDEX { sleEponOltIndex, sleEponOnuIndex, sleEponOnuVlanIndex }
			::= { sleEponOnuVlanTable 1 }

		
		SleEponOnuVlanEntry ::=
			SEQUENCE { 
				sleEponOnuVlanIndex
					VlanIndex,
				sleEponOnuVlanEgressPorts
					PortList,
				sleEponOnuVlanUntaggedPorts
					PortList
			 }

--  1.3.6.1.4.1.6296.101.20.4.1.1.1.1
		-- 1.3.6.1.4.1.6296.101.20.4.1.1.1.1
		sleEponOnuVlanIndex OBJECT-TYPE
			SYNTAX VlanIndex (1..4094)
			MAX-ACCESS read-only
			STATUS current
			DESCRIPTION
				"The index of ONU VLAN"
			::= { sleEponOnuVlanEntry 1 }

		
--  1.3.6.1.4.1.6296.101.20.4.1.1.1.2
		-- 1.3.6.1.4.1.6296.101.20.4.1.1.1.2
		sleEponOnuVlanEgressPorts OBJECT-TYPE
			SYNTAX PortList
			MAX-ACCESS read-only
			STATUS current
			DESCRIPTION
				"The set of ports which are transmitting traffic for this ONU VLAN as either tagged or untagged frames."
			::= { sleEponOnuVlanEntry 2 }

		
--  1.3.6.1.4.1.6296.101.20.4.1.1.1.3
		-- 1.3.6.1.4.1.6296.101.20.4.1.1.1.3
		sleEponOnuVlanUntaggedPorts OBJECT-TYPE
			SYNTAX PortList
			MAX-ACCESS read-only
			STATUS current
			DESCRIPTION
				"The set of ports which are transmitting traffic for this VLAN as untagged frames"
			::= { sleEponOnuVlanEntry 3 }

		
--  1.3.6.1.4.1.6296.101.20.4.2
		-- 1.3.6.1.4.1.6296.101.20.4.2
		sleEponOnuPort OBJECT IDENTIFIER ::= { sleEponOnuBridge 2 }

		
--  1.3.6.1.4.1.6296.101.20.4.2.1
		-- 1.3.6.1.4.1.6296.101.20.4.2.1
		sleEponOnuPortTable OBJECT-TYPE
			SYNTAX SEQUENCE OF SleEponOnuPortEntry
			MAX-ACCESS not-accessible
			STATUS current
			DESCRIPTION
				"Description."
			::= { sleEponOnuPort 1 }

		
--  1.3.6.1.4.1.6296.101.20.4.2.1.1
		-- 1.3.6.1.4.1.6296.101.20.4.2.1.1
		sleEponOnuPortEntry OBJECT-TYPE
			SYNTAX SleEponOnuPortEntry
			MAX-ACCESS not-accessible
			STATUS current
			DESCRIPTION
				"Description."
			INDEX { sleEponOltIndex, sleEponOnuIndex, sleEponOnuPortIndex }
			::= { sleEponOnuPortTable 1 }

		
		SleEponOnuPortEntry ::=
			SEQUENCE { 
				sleEponOnuPortIndex
					INTEGER,
				sleEponOnuPortAdminStatus
					INTEGER,
				sleEponOnuPortOperStatus
					INTEGER,
				sleEponOnuPortNego
					INTEGER,
				sleEponOnuPortSpeed
					Integer32,
				sleEponOnuPortDuplex
					INTEGER,
				sleEponOnuPortMaxHost
					Integer32,
				sleEponOnuPortPvid
					VlanIndex,
				sleEponOnuPortIngressRateLimitMode
					INTEGER,
				sleEponOnuPortIngressRateLimit
					INTEGER,
				sleEponOnuPortEgressRateLimit
					INTEGER,
				sleEponOnuPortFlowControl
					INTEGER
			 }

--  1.3.6.1.4.1.6296.101.20.4.2.1.1.1
		-- 1.3.6.1.4.1.6296.101.20.4.2.1.1.1
		sleEponOnuPortIndex OBJECT-TYPE
			SYNTAX INTEGER (1..256)
			MAX-ACCESS read-only
			STATUS current
			DESCRIPTION
				"The index of the ONU port"
			::= { sleEponOnuPortEntry 1 }

		
--  1.3.6.1.4.1.6296.101.20.4.2.1.1.2
		-- 1.3.6.1.4.1.6296.101.20.4.2.1.1.2
		sleEponOnuPortAdminStatus OBJECT-TYPE
			SYNTAX INTEGER
				{
				na(0),
				enable(1),
				disable(2)
				}
			MAX-ACCESS read-only
			STATUS current
			DESCRIPTION
				"The desired state of the ONU port"
			::= { sleEponOnuPortEntry 2 }

		
--  1.3.6.1.4.1.6296.101.20.4.2.1.1.3
		-- 1.3.6.1.4.1.6296.101.20.4.2.1.1.3
		sleEponOnuPortOperStatus OBJECT-TYPE
			SYNTAX INTEGER
				{
				na(0),
				enable(1),
				disable(2)
				}
			MAX-ACCESS read-only
			STATUS current
			DESCRIPTION
				"The current operational state of the ONU port"
			::= { sleEponOnuPortEntry 3 }

		
--  1.3.6.1.4.1.6296.101.20.4.2.1.1.4
		-- 1.3.6.1.4.1.6296.101.20.4.2.1.1.4
		sleEponOnuPortNego OBJECT-TYPE
			SYNTAX INTEGER
				{
				na(0),
				on(1),
				off(2)
				}
			MAX-ACCESS read-only
			STATUS current
			DESCRIPTION
				"It's auto-negotiation for a port, automatically to match the transmission speed and the duplex mode of the attached device"
			::= { sleEponOnuPortEntry 4 }

		
--  1.3.6.1.4.1.6296.101.20.4.2.1.1.5
		-- 1.3.6.1.4.1.6296.101.20.4.2.1.1.5
		sleEponOnuPortSpeed OBJECT-TYPE
			SYNTAX Integer32
			MAX-ACCESS read-only
			STATUS current
			DESCRIPTION
				"It express port speed that configure transmit rate of each port."
			::= { sleEponOnuPortEntry 5 }

		
--  1.3.6.1.4.1.6296.101.20.4.2.1.1.6
		-- 1.3.6.1.4.1.6296.101.20.4.2.1.1.6
		sleEponOnuPortDuplex OBJECT-TYPE
			SYNTAX INTEGER
				{
				na(0),
				full(1),
				half(2)
				}
			MAX-ACCESS read-only
			STATUS current
			DESCRIPTION
				"It express half duplex or full duplex mode. Only unidirectional communication is possible on half duplex mode and bi-directional communication is possible on full duplex mode to transmit packet for two ways."
			::= { sleEponOnuPortEntry 6 }

		
--  1.3.6.1.4.1.6296.101.20.4.2.1.1.7
		-- 1.3.6.1.4.1.6296.101.20.4.2.1.1.7
		sleEponOnuPortMaxHost OBJECT-TYPE
			SYNTAX Integer32
			MAX-ACCESS read-only
			STATUS current
			DESCRIPTION
				"It can limit the number of users by configuring maximum number of users also named as Max host for each ONU port"
			::= { sleEponOnuPortEntry 7 }

		
--  1.3.6.1.4.1.6296.101.20.4.2.1.1.8
		-- 1.3.6.1.4.1.6296.101.20.4.2.1.1.8
		sleEponOnuPortPvid OBJECT-TYPE
			SYNTAX VlanIndex
			MAX-ACCESS read-only
			STATUS current
			DESCRIPTION
				"It is PVID that configure in ONU port"
			::= { sleEponOnuPortEntry 8 }

		
--  1.3.6.1.4.1.6296.101.20.4.2.1.1.9
		-- 1.3.6.1.4.1.6296.101.20.4.2.1.1.9
		sleEponOnuPortIngressRateLimitMode OBJECT-TYPE
			SYNTAX INTEGER
				{
				all(0),
				multiBroadUnicast(1),
				multiBroadcast(2),
				broadcast(3)
				}
			MAX-ACCESS read-only
			STATUS current
			DESCRIPTION
				"It is rate limit mode in Ingress"
			::= { sleEponOnuPortEntry 9 }

		
--  1.3.6.1.4.1.6296.101.20.4.2.1.1.10
		-- 1.3.6.1.4.1.6296.101.20.4.2.1.1.10
		sleEponOnuPortIngressRateLimit OBJECT-TYPE
			SYNTAX INTEGER (0 | 62..100000)
			MAX-ACCESS read-only
			STATUS current
			DESCRIPTION
				"It is configurable port rate limit in Ingress"
			::= { sleEponOnuPortEntry 10 }

		
--  1.3.6.1.4.1.6296.101.20.4.2.1.1.11
		-- 1.3.6.1.4.1.6296.101.20.4.2.1.1.11
		sleEponOnuPortEgressRateLimit OBJECT-TYPE
			SYNTAX INTEGER (0 | 62..100000)
			MAX-ACCESS read-only
			STATUS current
			DESCRIPTION
				"It is configurable port rate limit in Egress"
			::= { sleEponOnuPortEntry 11 }

		
--  1.3.6.1.4.1.6296.101.20.4.2.1.1.12
		-- 1.3.6.1.4.1.6296.101.20.4.2.1.1.12
		sleEponOnuPortFlowControl OBJECT-TYPE
			SYNTAX INTEGER
				{
				none(0),
				on(1),
				off(2)
				}
			MAX-ACCESS read-only
			STATUS current
			DESCRIPTION
				"Description."
			::= { sleEponOnuPortEntry 12 }

		
--  1.3.6.1.4.1.6296.101.20.4.2.2
		-- 1.3.6.1.4.1.6296.101.20.4.2.2
		sleEponOnuPortControl OBJECT IDENTIFIER ::= { sleEponOnuPort 2 }

		
--  1.3.6.1.4.1.6296.101.20.4.2.2.1
		-- 1.3.6.1.4.1.6296.101.20.4.2.2.1
		sleEponOnuPortControlRequest OBJECT-TYPE
			SYNTAX INTEGER { setEponOnuPortReset(1) }
			MAX-ACCESS read-write
			STATUS current
			DESCRIPTION
				"The request of a user command"
			::= { sleEponOnuPortControl 1 }

		
--  1.3.6.1.4.1.6296.101.20.4.2.2.2
		-- 1.3.6.1.4.1.6296.101.20.4.2.2.2
		sleEponOnuPortControlStatus OBJECT-TYPE
			SYNTAX SleControlStatusType
			MAX-ACCESS read-only
			STATUS current
			DESCRIPTION
				"The status of user command"
			::= { sleEponOnuPortControl 2 }

		
--  1.3.6.1.4.1.6296.101.20.4.2.2.3
		-- 1.3.6.1.4.1.6296.101.20.4.2.2.3
		sleEponOnuPortControlTimer OBJECT-TYPE
			SYNTAX Gauge32
			MAX-ACCESS read-write
			STATUS current
			DESCRIPTION
				"The maximum time for the manager for a long running user command"
			::= { sleEponOnuPortControl 3 }

		
--  1.3.6.1.4.1.6296.101.20.4.2.2.4
		-- 1.3.6.1.4.1.6296.101.20.4.2.2.4
		sleEponOnuPortControlTimeStamp OBJECT-TYPE
			SYNTAX TimeTicks
			MAX-ACCESS read-only
			STATUS current
			DESCRIPTION
				"The time stamp of the last command(end of command)"
			::= { sleEponOnuPortControl 4 }

		
--  1.3.6.1.4.1.6296.101.20.4.2.2.5
		-- 1.3.6.1.4.1.6296.101.20.4.2.2.5
		sleEponOnuPortControlReqResult OBJECT-TYPE
			SYNTAX SleControlRequestResultType
			MAX-ACCESS read-only
			STATUS current
			DESCRIPTION
				"The result of the last user command"
			::= { sleEponOnuPortControl 5 }

		
--  1.3.6.1.4.1.6296.101.20.4.2.2.6
		-- 1.3.6.1.4.1.6296.101.20.4.2.2.6
		sleEponOnuPortControlOltIndex OBJECT-TYPE
			SYNTAX INTEGER (1..512)
			MAX-ACCESS read-write
			STATUS current
			DESCRIPTION
				"OLT port Index"
			::= { sleEponOnuPortControl 6 }

		
--  1.3.6.1.4.1.6296.101.20.4.2.2.7
		-- 1.3.6.1.4.1.6296.101.20.4.2.2.7
		sleEponOnuPortControlOnuIndex OBJECT-TYPE
			SYNTAX INTEGER (1..32)
			MAX-ACCESS read-write
			STATUS current
			DESCRIPTION
				"ONU Index"
			::= { sleEponOnuPortControl 7 }

		
--  1.3.6.1.4.1.6296.101.20.4.2.2.8
		-- 1.3.6.1.4.1.6296.101.20.4.2.2.8
		sleEponOnuPortControlPortIndex OBJECT-TYPE
			SYNTAX INTEGER (1..256)
			MAX-ACCESS read-write
			STATUS current
			DESCRIPTION
				"The index of the ONU port"
			::= { sleEponOnuPortControl 8 }

		
--  1.3.6.1.4.1.6296.101.20.4.2.3
		-- 1.3.6.1.4.1.6296.101.20.4.2.3
		sleEponOnuPortNotification OBJECT IDENTIFIER ::= { sleEponOnuPort 3 }

		
--  1.3.6.1.4.1.6296.101.20.4.2.3.1
		-- 1.3.6.1.4.1.6296.101.20.4.2.3.1
		sleEponOnuPortReset NOTIFICATION-TYPE
			OBJECTS { sleEponOnuPortControlRequest, sleEponOnuPortControlTimeStamp, sleEponOnuPortControlReqResult, sleEponOnuPortControlOltIndex, sleEponOnuPortControlOnuIndex, 
				sleEponOnuPortControlPortIndex }
			STATUS current
			DESCRIPTION 
				"Description."
			::= { sleEponOnuPortNotification 1 }

		
--  1.3.6.1.4.1.6296.101.20.4.3
		-- 1.3.6.1.4.1.6296.101.20.4.3
		sleEponOnuFdb OBJECT IDENTIFIER ::= { sleEponOnuBridge 3 }

		
--  1.3.6.1.4.1.6296.101.20.4.3.1
		-- 1.3.6.1.4.1.6296.101.20.4.3.1
		sleEponOnuFdbTable OBJECT-TYPE
			SYNTAX SEQUENCE OF SleEponOnuFdbEntry
			MAX-ACCESS not-accessible
			STATUS current
			DESCRIPTION
				"Description."
			::= { sleEponOnuFdb 1 }

		
--  1.3.6.1.4.1.6296.101.20.4.3.1.1
		-- 1.3.6.1.4.1.6296.101.20.4.3.1.1
		sleEponOnuFdbEntry OBJECT-TYPE
			SYNTAX SleEponOnuFdbEntry
			MAX-ACCESS not-accessible
			STATUS current
			DESCRIPTION
				"Description."
			INDEX { sleEponOltIndex, sleEponOnuIndex, sleEponOnuFdbMacAddress }
			::= { sleEponOnuFdbTable 1 }

		
		SleEponOnuFdbEntry ::=
			SEQUENCE { 
				sleEponOnuFdbMacAddress
					MacAddress,
				sleEponOnuFdbType
					INTEGER,
				sleEponOnuFdbPermission
					INTEGER
			 }

--  1.3.6.1.4.1.6296.101.20.4.3.1.1.1
		-- 1.3.6.1.4.1.6296.101.20.4.3.1.1.1
		sleEponOnuFdbMacAddress OBJECT-TYPE
			SYNTAX MacAddress
			MAX-ACCESS read-only
			STATUS current
			DESCRIPTION
				"The fdb address of ONT"
			::= { sleEponOnuFdbEntry 1 }

		
--  1.3.6.1.4.1.6296.101.20.4.3.1.1.2
		-- 1.3.6.1.4.1.6296.101.20.4.3.1.1.2
		sleEponOnuFdbType OBJECT-TYPE
			SYNTAX INTEGER
				{
				local(0),
				static(1),
				dynamic(2)
				}
			MAX-ACCESS read-only
			STATUS current
			DESCRIPTION
				"The type of fdb address."
			::= { sleEponOnuFdbEntry 2 }

		
--  1.3.6.1.4.1.6296.101.20.4.3.1.1.3
		-- 1.3.6.1.4.1.6296.101.20.4.3.1.1.3
		sleEponOnuFdbPermission OBJECT-TYPE
			SYNTAX INTEGER
				{
				deny(0),
				permit(1)
				}
			MAX-ACCESS read-only
			STATUS current
			DESCRIPTION
				"Description."
			::= { sleEponOnuFdbEntry 3 }

		
--  1.3.6.1.4.1.6296.101.20.4.3.2
		-- 1.3.6.1.4.1.6296.101.20.4.3.2
		sleEponOnuFdbControl OBJECT IDENTIFIER ::= { sleEponOnuFdb 2 }

		
--  1.3.6.1.4.1.6296.101.20.4.3.2.1
		-- 1.3.6.1.4.1.6296.101.20.4.3.2.1
		sleEponOnuFdbControlRequest OBJECT-TYPE
			SYNTAX INTEGER { clearOltMac(1) }
			MAX-ACCESS read-write
			STATUS current
			DESCRIPTION
				"Description."
			::= { sleEponOnuFdbControl 1 }

		
--  1.3.6.1.4.1.6296.101.20.4.3.2.2
		-- 1.3.6.1.4.1.6296.101.20.4.3.2.2
		sleEponOnuFdbControlStatus OBJECT-TYPE
			SYNTAX SleControlStatusType
			MAX-ACCESS read-only
			STATUS current
			DESCRIPTION
				"Description."
			::= { sleEponOnuFdbControl 2 }

		
--  1.3.6.1.4.1.6296.101.20.4.3.2.3
		-- 1.3.6.1.4.1.6296.101.20.4.3.2.3
		sleEponOnuFdbControlTimer OBJECT-TYPE
			SYNTAX Gauge32
			MAX-ACCESS read-write
			STATUS current
			DESCRIPTION
				"Description."
			::= { sleEponOnuFdbControl 3 }

		
--  1.3.6.1.4.1.6296.101.20.4.3.2.4
		-- 1.3.6.1.4.1.6296.101.20.4.3.2.4
		sleEponOnuFdbControlTimeStamp OBJECT-TYPE
			SYNTAX TimeTicks
			MAX-ACCESS read-only
			STATUS current
			DESCRIPTION
				"Description."
			::= { sleEponOnuFdbControl 4 }

		
--  1.3.6.1.4.1.6296.101.20.4.3.2.5
		-- 1.3.6.1.4.1.6296.101.20.4.3.2.5
		sleEponOnuFdbControlReqResult OBJECT-TYPE
			SYNTAX SleControlRequestResultType
			MAX-ACCESS read-only
			STATUS current
			DESCRIPTION
				"Description."
			::= { sleEponOnuFdbControl 5 }

		
--  1.3.6.1.4.1.6296.101.20.4.3.2.6
		-- 1.3.6.1.4.1.6296.101.20.4.3.2.6
		sleEponOnuFdbControlOltIndex OBJECT-TYPE
			SYNTAX INTEGER (1..512)
			MAX-ACCESS read-write
			STATUS current
			DESCRIPTION
				"Description."
			::= { sleEponOnuFdbControl 6 }

		
--  1.3.6.1.4.1.6296.101.20.4.3.2.7
		-- 1.3.6.1.4.1.6296.101.20.4.3.2.7
		sleEponOnuFdbControlOnuIndex OBJECT-TYPE
			SYNTAX INTEGER (1..32)
			MAX-ACCESS read-write
			STATUS current
			DESCRIPTION
				"Description."
			::= { sleEponOnuFdbControl 7 }

		
--  1.3.6.1.4.1.6296.101.20.4.3.2.8
		-- 1.3.6.1.4.1.6296.101.20.4.3.2.8
		sleEponOnuFdbControlType OBJECT-TYPE
			SYNTAX INTEGER
				{
				dynamic(1),
				static(2),
				all(3)
				}
			MAX-ACCESS read-write
			STATUS current
			DESCRIPTION
				"Description."
			::= { sleEponOnuFdbControl 8 }

		
--  1.3.6.1.4.1.6296.101.20.4.3.3
		-- 1.3.6.1.4.1.6296.101.20.4.3.3
		sleEponOnuFdbNotification OBJECT IDENTIFIER ::= { sleEponOnuFdb 3 }

		
--  1.3.6.1.4.1.6296.101.20.4.3.3.1
		-- 1.3.6.1.4.1.6296.101.20.4.3.3.1
		sleEponOnuFdbMacCleared NOTIFICATION-TYPE
			OBJECTS { sleEponOnuFdbControlRequest, sleEponOnuFdbControlTimeStamp, sleEponOnuFdbControlReqResult, sleEponOnuFdbControlOltIndex, sleEponOnuFdbControlOnuIndex, 
				sleEponOnuFdbControlType }
			STATUS current
			DESCRIPTION 
				"Description."
			::= { sleEponOnuFdbNotification 1 }

		
--  1.3.6.1.4.1.6296.101.20.4.4
		-- 1.3.6.1.4.1.6296.101.20.4.4
		sleEponOnuUserMac OBJECT IDENTIFIER ::= { sleEponOnuBridge 4 }

		
--  1.3.6.1.4.1.6296.101.20.4.4.1
		-- 1.3.6.1.4.1.6296.101.20.4.4.1
		sleEponOnuUserMacTable OBJECT-TYPE
			SYNTAX SEQUENCE OF SleEponOnuUserMacEntry
			MAX-ACCESS not-accessible
			STATUS current
			DESCRIPTION
				"Description."
			::= { sleEponOnuUserMac 1 }

		
--  1.3.6.1.4.1.6296.101.20.4.4.1.1
		-- 1.3.6.1.4.1.6296.101.20.4.4.1.1
		sleEponOnuUserMacEntry OBJECT-TYPE
			SYNTAX SleEponOnuUserMacEntry
			MAX-ACCESS not-accessible
			STATUS current
			DESCRIPTION
				"Description."
			INDEX { sleEponOltIndex, sleEponOnuIndex, sleEponOnuUserMacIndex }
			::= { sleEponOnuUserMacTable 1 }

		
		SleEponOnuUserMacEntry ::=
			SEQUENCE { 
				sleEponOnuUserMacIndex
					INTEGER,
				sleEponOnuUserMacMacAddress
					MacAddress,
				sleEponOnuUserMacUsedTime
					TimeTicks
			 }

--  1.3.6.1.4.1.6296.101.20.4.4.1.1.1
		-- 1.3.6.1.4.1.6296.101.20.4.4.1.1.1
		sleEponOnuUserMacIndex OBJECT-TYPE
			SYNTAX INTEGER (1..8)
			MAX-ACCESS read-only
			STATUS current
			DESCRIPTION
				"Description."
			::= { sleEponOnuUserMacEntry 1 }

		
--  1.3.6.1.4.1.6296.101.20.4.4.1.1.2
		-- 1.3.6.1.4.1.6296.101.20.4.4.1.1.2
		sleEponOnuUserMacMacAddress OBJECT-TYPE
			SYNTAX MacAddress
			MAX-ACCESS read-only
			STATUS current
			DESCRIPTION
				"Description."
			::= { sleEponOnuUserMacEntry 2 }

		
--  1.3.6.1.4.1.6296.101.20.4.4.1.1.3
		-- 1.3.6.1.4.1.6296.101.20.4.4.1.1.3
		sleEponOnuUserMacUsedTime OBJECT-TYPE
			SYNTAX TimeTicks
			MAX-ACCESS read-only
			STATUS current
			DESCRIPTION
				"Description."
			::= { sleEponOnuUserMacEntry 3 }

		
--  1.3.6.1.4.1.6296.101.20.4.5
		-- 1.3.6.1.4.1.6296.101.20.4.5
		sleEponOnuSubscriber OBJECT IDENTIFIER ::= { sleEponOnuBridge 5 }

		
--  1.3.6.1.4.1.6296.101.20.4.5.1
		-- 1.3.6.1.4.1.6296.101.20.4.5.1
		sleEponOnuSubscriberCurrentTable OBJECT-TYPE
			SYNTAX SEQUENCE OF SleEponOnuSubscriberCurrentEntry
			MAX-ACCESS not-accessible
			STATUS current
			DESCRIPTION
				"Description."
			::= { sleEponOnuSubscriber 1 }

		
--  1.3.6.1.4.1.6296.101.20.4.5.1.1
		-- 1.3.6.1.4.1.6296.101.20.4.5.1.1
		sleEponOnuSubscriberCurrentEntry OBJECT-TYPE
			SYNTAX SleEponOnuSubscriberCurrentEntry
			MAX-ACCESS not-accessible
			STATUS current
			DESCRIPTION
				"Description."
			INDEX { sleEponOltIndex, sleEponOnuIndex, sleEponOnuSubscriberCurrentIpAddress }
			::= { sleEponOnuSubscriberCurrentTable 1 }

		
		SleEponOnuSubscriberCurrentEntry ::=
			SEQUENCE { 
				sleEponOnuSubscriberCurrentIpAddress
					IpAddress,
				sleEponOnuSubscriberCurrentMacAddress
					MacAddress,
				sleEponOnuSubscriberCurrentPort
					INTEGER,
				sleEponOnuSubscriberCurrentTime
					Gauge32
			 }

--  1.3.6.1.4.1.6296.101.20.4.5.1.1.1
		-- 1.3.6.1.4.1.6296.101.20.4.5.1.1.1
		sleEponOnuSubscriberCurrentIpAddress OBJECT-TYPE
			SYNTAX IpAddress
			MAX-ACCESS read-only
			STATUS current
			DESCRIPTION
				"Description."
			::= { sleEponOnuSubscriberCurrentEntry 1 }

		
--  1.3.6.1.4.1.6296.101.20.4.5.1.1.2
		-- 1.3.6.1.4.1.6296.101.20.4.5.1.1.2
		sleEponOnuSubscriberCurrentMacAddress OBJECT-TYPE
			SYNTAX MacAddress
			MAX-ACCESS read-only
			STATUS current
			DESCRIPTION
				"Description."
			::= { sleEponOnuSubscriberCurrentEntry 2 }

		
--  1.3.6.1.4.1.6296.101.20.4.5.1.1.3
		-- 1.3.6.1.4.1.6296.101.20.4.5.1.1.3
		sleEponOnuSubscriberCurrentPort OBJECT-TYPE
			SYNTAX INTEGER (1..256)
			MAX-ACCESS read-only
			STATUS current
			DESCRIPTION
				"Description."
			::= { sleEponOnuSubscriberCurrentEntry 3 }

		
--  1.3.6.1.4.1.6296.101.20.4.5.1.1.4
		-- 1.3.6.1.4.1.6296.101.20.4.5.1.1.4
		sleEponOnuSubscriberCurrentTime OBJECT-TYPE
			SYNTAX Gauge32
			MAX-ACCESS read-only
			STATUS current
			DESCRIPTION
				"Description."
			::= { sleEponOnuSubscriberCurrentEntry 4 }

		
--  1.3.6.1.4.1.6296.101.20.4.5.2
		-- 1.3.6.1.4.1.6296.101.20.4.5.2
		sleEponOnuSubscriberHistoryTable OBJECT-TYPE
			SYNTAX SEQUENCE OF SleEponOnuSubscriberHistoryEntry
			MAX-ACCESS not-accessible
			STATUS current
			DESCRIPTION
				"Description."
			::= { sleEponOnuSubscriber 2 }

		
--  1.3.6.1.4.1.6296.101.20.4.5.2.1
		-- 1.3.6.1.4.1.6296.101.20.4.5.2.1
		sleEponOnuSubscriberHistoryEntry OBJECT-TYPE
			SYNTAX SleEponOnuSubscriberHistoryEntry
			MAX-ACCESS not-accessible
			STATUS current
			DESCRIPTION
				"Description."
			INDEX { sleEponOltIndex, sleEponOnuIndex, sleEponOnuSubscriberHistoryTime, sleEponOnuSubscriberHistoryIpAddress }
			::= { sleEponOnuSubscriberHistoryTable 1 }

		
		SleEponOnuSubscriberHistoryEntry ::=
			SEQUENCE { 
				sleEponOnuSubscriberHistoryIpAddress
					IpAddress,
				sleEponOnuSubscriberHistoryMacAddress
					MacAddress,
				sleEponOnuSubscriberHistoryPort
					INTEGER,
				sleEponOnuSubscriberHistoryTime
					Gauge32
			 }

--  1.3.6.1.4.1.6296.101.20.4.5.2.1.1
		-- 1.3.6.1.4.1.6296.101.20.4.5.2.1.1
		sleEponOnuSubscriberHistoryIpAddress OBJECT-TYPE
			SYNTAX IpAddress
			MAX-ACCESS read-only
			STATUS current
			DESCRIPTION
				"Description."
			::= { sleEponOnuSubscriberHistoryEntry 1 }

		
--  1.3.6.1.4.1.6296.101.20.4.5.2.1.2
		-- 1.3.6.1.4.1.6296.101.20.4.5.2.1.2
		sleEponOnuSubscriberHistoryMacAddress OBJECT-TYPE
			SYNTAX MacAddress
			MAX-ACCESS read-only
			STATUS current
			DESCRIPTION
				"Description."
			::= { sleEponOnuSubscriberHistoryEntry 2 }

		
--  1.3.6.1.4.1.6296.101.20.4.5.2.1.3
		-- 1.3.6.1.4.1.6296.101.20.4.5.2.1.3
		sleEponOnuSubscriberHistoryPort OBJECT-TYPE
			SYNTAX INTEGER (1..256)
			MAX-ACCESS read-only
			STATUS current
			DESCRIPTION
				"Description."
			::= { sleEponOnuSubscriberHistoryEntry 3 }

		
--  1.3.6.1.4.1.6296.101.20.4.5.2.1.4
		-- 1.3.6.1.4.1.6296.101.20.4.5.2.1.4
		sleEponOnuSubscriberHistoryTime OBJECT-TYPE
			SYNTAX Gauge32 (1..65535)
			MAX-ACCESS read-only
			STATUS current
			DESCRIPTION
				"Description."
			::= { sleEponOnuSubscriberHistoryEntry 4 }

		
--  1.3.6.1.4.1.6296.101.20.4.5.3
		-- 1.3.6.1.4.1.6296.101.20.4.5.3
		sleEponOnuSubscriberControl OBJECT IDENTIFIER ::= { sleEponOnuSubscriber 3 }

		
--  1.3.6.1.4.1.6296.101.20.4.5.3.1
		-- 1.3.6.1.4.1.6296.101.20.4.5.3.1
		sleEponOnuSubscriberControlRequest OBJECT-TYPE
			SYNTAX INTEGER
				{
				clearSubscriberHistoryOlt(1),
				clearSubscriberHistoryOnu(2)
				}
			MAX-ACCESS read-write
			STATUS current
			DESCRIPTION
				"Description."
			::= { sleEponOnuSubscriberControl 1 }

		
--  1.3.6.1.4.1.6296.101.20.4.5.3.2
		-- 1.3.6.1.4.1.6296.101.20.4.5.3.2
		sleEponOnuSubscriberControlStatus OBJECT-TYPE
			SYNTAX SleControlStatusType
			MAX-ACCESS read-only
			STATUS current
			DESCRIPTION
				"Description."
			::= { sleEponOnuSubscriberControl 2 }

		
--  1.3.6.1.4.1.6296.101.20.4.5.3.3
		-- 1.3.6.1.4.1.6296.101.20.4.5.3.3
		sleEponOnuSubscriberControlTimer OBJECT-TYPE
			SYNTAX Gauge32
			MAX-ACCESS read-write
			STATUS current
			DESCRIPTION
				"Description."
			::= { sleEponOnuSubscriberControl 3 }

		
--  1.3.6.1.4.1.6296.101.20.4.5.3.4
		-- 1.3.6.1.4.1.6296.101.20.4.5.3.4
		sleEponOnuSubscriberControlTimeStamp OBJECT-TYPE
			SYNTAX Counter64
			MAX-ACCESS read-only
			STATUS current
			DESCRIPTION
				"Description."
			::= { sleEponOnuSubscriberControl 4 }

		
--  1.3.6.1.4.1.6296.101.20.4.5.3.5
		-- 1.3.6.1.4.1.6296.101.20.4.5.3.5
		sleEponOnuSubscriberControlReqResult OBJECT-TYPE
			SYNTAX Integer32
			MAX-ACCESS read-write
			STATUS current
			DESCRIPTION
				"Description."
			::= { sleEponOnuSubscriberControl 5 }

		
--  1.3.6.1.4.1.6296.101.20.4.5.3.6
		-- 1.3.6.1.4.1.6296.101.20.4.5.3.6
		sleEponOnuSubscriberControlOltIndex OBJECT-TYPE
			SYNTAX INTEGER (1..512)
			MAX-ACCESS read-write
			STATUS current
			DESCRIPTION
				"Description."
			::= { sleEponOnuSubscriberControl 6 }

		
--  1.3.6.1.4.1.6296.101.20.4.5.3.7
		-- 1.3.6.1.4.1.6296.101.20.4.5.3.7
		sleEponOnuSubscriberControlOnuIndex OBJECT-TYPE
			SYNTAX INTEGER (1..32)
			MAX-ACCESS read-write
			STATUS current
			DESCRIPTION
				"Description."
			::= { sleEponOnuSubscriberControl 7 }

		
--  1.3.6.1.4.1.6296.101.20.4.5.4
		-- 1.3.6.1.4.1.6296.101.20.4.5.4
		sleEponOnuSubscriberNotification OBJECT IDENTIFIER ::= { sleEponOnuSubscriber 4 }

		
--  1.3.6.1.4.1.6296.101.20.4.5.4.1
		-- 1.3.6.1.4.1.6296.101.20.4.5.4.1
		sleEponOnuSubscriberHistoryOltCleared NOTIFICATION-TYPE
			OBJECTS { sleEponOnuSubscriberControlRequest, sleEponOnuSubscriberControlTimeStamp, sleEponOnuSubscriberControlReqResult, sleEponOnuSubscriberControlOltIndex }
			STATUS current
			DESCRIPTION 
				"Description."
			::= { sleEponOnuSubscriberNotification 1 }

		
--  1.3.6.1.4.1.6296.101.20.4.5.4.2
		-- 1.3.6.1.4.1.6296.101.20.4.5.4.2
		sleEponOnuSubscriberHistroyOnuCleared NOTIFICATION-TYPE
			OBJECTS { sleEponOnuSubscriberControlRequest, sleEponOnuSubscriberControlTimeStamp, sleEponOnuSubscriberControlReqResult, sleEponOnuSubscriberControlOltIndex, sleEponOnuSubscriberControlOnuIndex
				 }
			STATUS current
			DESCRIPTION 
				"Description."
			::= { sleEponOnuSubscriberNotification 2 }

		
--  1.3.6.1.4.1.6296.101.20.5
		-- 1.3.6.1.4.1.6296.101.20.5
		sleEponProfile OBJECT IDENTIFIER ::= { sleEpon 5 }

		
--  1.3.6.1.4.1.6296.101.20.5.1
		-- 1.3.6.1.4.1.6296.101.20.5.1
		sleEponProfileBase OBJECT IDENTIFIER ::= { sleEponProfile 1 }

		
--  1.3.6.1.4.1.6296.101.20.5.1.1
		-- 1.3.6.1.4.1.6296.101.20.5.1.1
		sleEponProfileTable OBJECT-TYPE
			SYNTAX SEQUENCE OF SleEponProfileEntry
			MAX-ACCESS not-accessible
			STATUS current
			DESCRIPTION
				"Description."
			::= { sleEponProfileBase 1 }

		
--  1.3.6.1.4.1.6296.101.20.5.4.1.1
		-- 1.3.6.1.4.1.6296.101.20.5.1.1.1
		sleEponProfileEntry OBJECT-TYPE
			SYNTAX SleEponProfileEntry
			MAX-ACCESS not-accessible
			STATUS current
			DESCRIPTION
				"Description."
			INDEX { sleEponProfileIndex }
			::= { sleEponProfileTable 1 }

		
		SleEponProfileEntry ::=
			SEQUENCE { 
				sleEponProfileIndex
					INTEGER,
				sleEponProfileName
					OCTET STRING,
				sleEponProfileDPDownMaxBandwidth
					INTEGER,
				sleEponProfileDPDownMaxBurstSize
					INTEGER,
				sleEponProfileDPP2pMaxBandwidth
					INTEGER,
				sleEponProfileDPP2pMaxBurstSize
					INTEGER,
				sleEponProfileSlaGuaranteedBandwidth
					INTEGER,
				sleEponProfileSlaBestEffortBandwidth
					INTEGER,
				sleEponProfileSlaPlatoClass
					INTEGER,
				sleEponProfileSlaPlatoMinBandwidth1m
					INTEGER,
				sleEponProfileSlaPlatoMinBandwdith64k
					INTEGER,
				sleEponProfileSlaPlatoMaxBandwidth1m
					INTEGER,
				sleEponProfileSlaPlatoMaxBandwidth64k
					INTEGER,
				sleEponProfileSlaPlatoDelayLevel
					INTEGER,
				sleEponProfileExtendMtu
					EnableFlag,
				sleEponProfileIgmpFilter
					EnableFlag,
				sleEponProfileIgmpSnooping
					EnableFlag,
				sleEponProfileSTPenable
					EnableFlag,
				sleEponProfileSubscriberInfoCollection
					EnableFlag,
				sleEponProfileLoopDetectStatus
					EnableFlag,
				sleEponProfileLoopDetectBlockTimer
					INTEGER,
				sleEponProfileLoopDetectSendingpacket
					INTEGER
			 }

--  1.3.6.1.4.1.6296.101.20.5.4.1.1.1
		-- 1.3.6.1.4.1.6296.101.20.5.1.1.1.1
		sleEponProfileIndex OBJECT-TYPE
			SYNTAX INTEGER (1..32)
			MAX-ACCESS read-only
			STATUS current
			DESCRIPTION
				"Profile Index"
			::= { sleEponProfileEntry 1 }

		
--  1.3.6.1.4.1.6296.101.20.5.4.1.1.2
		-- 1.3.6.1.4.1.6296.101.20.5.1.1.1.2
		sleEponProfileName OBJECT-TYPE
			SYNTAX OCTET STRING (SIZE (1..64))
			MAX-ACCESS read-only
			STATUS current
			DESCRIPTION
				"Profile name"
			::= { sleEponProfileEntry 2 }

		
--  1.3.6.1.4.1.6296.101.20.5.4.1.1.3
		-- 1.3.6.1.4.1.6296.101.20.5.1.1.1.3
		sleEponProfileDPDownMaxBandwidth OBJECT-TYPE
			SYNTAX INTEGER (0 | 1..1000000)
			UNITS "kbps"
			MAX-ACCESS read-only
			STATUS current
			DESCRIPTION
				"Download policy Down Max Bandwidth 
				
				"
			::= { sleEponProfileEntry 3 }

		
--  1.3.6.1.4.1.6296.101.20.5.4.1.1.4
		-- 1.3.6.1.4.1.6296.101.20.5.1.1.1.4
		sleEponProfileDPDownMaxBurstSize OBJECT-TYPE
			SYNTAX INTEGER (0 | 128..8388479)
			UNITS "byte"
			MAX-ACCESS read-only
			STATUS current
			DESCRIPTION
				"Download policy Down Max Burst Size 
				
				"
			::= { sleEponProfileEntry 4 }

		
--  1.3.6.1.4.1.6296.101.20.5.4.1.1.5
		-- 1.3.6.1.4.1.6296.101.20.5.1.1.1.5
		sleEponProfileDPP2pMaxBandwidth OBJECT-TYPE
			SYNTAX INTEGER (0 | 1..1000000)
			UNITS "kbps"
			MAX-ACCESS read-only
			STATUS current
			DESCRIPTION
				"Download policy P2P Max Bandwidth "
			::= { sleEponProfileEntry 5 }

		
--  1.3.6.1.4.1.6296.101.20.5.4.1.1.6
		-- 1.3.6.1.4.1.6296.101.20.5.1.1.1.6
		sleEponProfileDPP2pMaxBurstSize OBJECT-TYPE
			SYNTAX INTEGER (0 | 128..8388479)
			UNITS "byte"
			MAX-ACCESS read-only
			STATUS current
			DESCRIPTION
				"Download policy P2P Max Burst Size "
			::= { sleEponProfileEntry 6 }

		
--  1.3.6.1.4.1.6296.101.20.5.4.1.1.7
		-- 1.3.6.1.4.1.6296.101.20.5.1.1.1.7
		sleEponProfileSlaGuaranteedBandwidth OBJECT-TYPE
			SYNTAX INTEGER (43..65535)
			UNITS "TQ"
			MAX-ACCESS read-only
			STATUS current
			DESCRIPTION
				"SLA-internal Guranteed Bandwidth"
			DEFVAL { 85 }
			::= { sleEponProfileEntry 7 }

		
--  1.3.6.1.4.1.6296.101.20.5.4.1.1.8
		-- 1.3.6.1.4.1.6296.101.20.5.1.1.1.8
		sleEponProfileSlaBestEffortBandwidth OBJECT-TYPE
			SYNTAX INTEGER (43..65535)
			UNITS "TQ"
			MAX-ACCESS read-only
			STATUS current
			DESCRIPTION
				"SLA-internal Best effort Bandwidth"
			DEFVAL { 85 }
			::= { sleEponProfileEntry 8 }

		
--  1.3.6.1.4.1.6296.101.20.5.4.1.1.9
		-- 1.3.6.1.4.1.6296.101.20.5.1.1.1.9
		sleEponProfileSlaPlatoClass OBJECT-TYPE
			SYNTAX INTEGER (0..7)
			MAX-ACCESS read-only
			STATUS current
			DESCRIPTION
				"SLA-Plato Class"
			DEFVAL { 1 }
			::= { sleEponProfileEntry 9 }

		
--  1.3.6.1.4.1.6296.101.20.5.4.1.1.10
		-- 1.3.6.1.4.1.6296.101.20.5.1.1.1.10
		sleEponProfileSlaPlatoMinBandwidth1m OBJECT-TYPE
			SYNTAX INTEGER (1..1000)
			UNITS "Mbps"
			MAX-ACCESS read-only
			STATUS current
			DESCRIPTION
				"SLA-Plato Minimum Bandwidth_1m"
			DEFVAL { '1'b }
			::= { sleEponProfileEntry 10 }

		
--  1.3.6.1.4.1.6296.101.20.5.4.1.1.11
		-- 1.3.6.1.4.1.6296.101.20.5.1.1.1.11
		sleEponProfileSlaPlatoMinBandwdith64k OBJECT-TYPE
			SYNTAX INTEGER (0..1024)
			UNITS "64Kbps"
			MAX-ACCESS read-only
			STATUS current
			DESCRIPTION
				"SLA-plato Minimum Bandwidth_64k"
			DEFVAL { '0'b }
			::= { sleEponProfileEntry 11 }

		
--  1.3.6.1.4.1.6296.101.20.5.4.1.1.12
		-- 1.3.6.1.4.1.6296.101.20.5.1.1.1.12
		sleEponProfileSlaPlatoMaxBandwidth1m OBJECT-TYPE
			SYNTAX INTEGER (1..1000)
			UNITS "Mbps"
			MAX-ACCESS read-only
			STATUS current
			DESCRIPTION
				"SLA-plato Max bandwidth_1m"
			DEFVAL { 2 }
			::= { sleEponProfileEntry 12 }

		
--  1.3.6.1.4.1.6296.101.20.5.4.1.1.13
		-- 1.3.6.1.4.1.6296.101.20.5.1.1.1.13
		sleEponProfileSlaPlatoMaxBandwidth64k OBJECT-TYPE
			SYNTAX INTEGER (0..1024)
			UNITS "64Kbps"
			MAX-ACCESS read-only
			STATUS current
			DESCRIPTION
				"SLA-plato Max bandwidth_64k"
			DEFVAL { 0 }
			::= { sleEponProfileEntry 13 }

		
--  1.3.6.1.4.1.6296.101.20.5.4.1.1.14
		-- 1.3.6.1.4.1.6296.101.20.5.1.1.1.14
		sleEponProfileSlaPlatoDelayLevel OBJECT-TYPE
			SYNTAX INTEGER (1..2)
			MAX-ACCESS read-only
			STATUS current
			DESCRIPTION
				"SLA-plato Delay  level"
			DEFVAL { 1 }
			::= { sleEponProfileEntry 14 }

		
--  1.3.6.1.4.1.6296.101.20.5.4.1.1.15
		-- 1.3.6.1.4.1.6296.101.20.5.1.1.1.15
		sleEponProfileExtendMtu OBJECT-TYPE
			SYNTAX EnableFlag
			MAX-ACCESS read-only
			STATUS current
			DESCRIPTION
				"Description."
			::= { sleEponProfileEntry 15 }

		
--  1.3.6.1.4.1.6296.101.20.5.4.1.1.16
		-- 1.3.6.1.4.1.6296.101.20.5.1.1.1.16
		sleEponProfileIgmpFilter OBJECT-TYPE
			SYNTAX EnableFlag
			MAX-ACCESS read-only
			STATUS current
			DESCRIPTION
				"Description."
			::= { sleEponProfileEntry 16 }

		
--  1.3.6.1.4.1.6296.101.20.5.4.1.1.17
		-- 1.3.6.1.4.1.6296.101.20.5.1.1.1.17
		sleEponProfileIgmpSnooping OBJECT-TYPE
			SYNTAX EnableFlag
			MAX-ACCESS read-only
			STATUS current
			DESCRIPTION
				"Description."
			::= { sleEponProfileEntry 17 }

		
--  1.3.6.1.4.1.6296.101.20.5.4.1.1.18
		-- 1.3.6.1.4.1.6296.101.20.5.1.1.1.18
		sleEponProfileSTPenable OBJECT-TYPE
			SYNTAX EnableFlag
			MAX-ACCESS read-only
			STATUS current
			DESCRIPTION
				"Description."
			::= { sleEponProfileEntry 18 }

		
--  1.3.6.1.4.1.6296.101.20.5.4.1.1.20
		-- 1.3.6.1.4.1.6296.101.20.5.1.1.1.19
		sleEponProfileSubscriberInfoCollection OBJECT-TYPE
			SYNTAX EnableFlag
			MAX-ACCESS read-only
			STATUS current
			DESCRIPTION
				"Description."
			::= { sleEponProfileEntry 19 }

		
--  1.3.6.1.4.1.6296.101.20.5.4.1.1.21
		-- 1.3.6.1.4.1.6296.101.20.5.1.1.1.20
		sleEponProfileLoopDetectStatus OBJECT-TYPE
			SYNTAX EnableFlag
			MAX-ACCESS read-only
			STATUS current
			DESCRIPTION
				"Description."
			::= { sleEponProfileEntry 20 }

		
--  1.3.6.1.4.1.6296.101.20.5.4.1.1.22
		-- 1.3.6.1.4.1.6296.101.20.5.1.1.1.21
		sleEponProfileLoopDetectBlockTimer OBJECT-TYPE
			SYNTAX INTEGER (0 | 10..86400)
			MAX-ACCESS read-only
			STATUS current
			DESCRIPTION
				"Description."
			::= { sleEponProfileEntry 21 }

		
--  1.3.6.1.4.1.6296.101.20.5.4.1.1.23
		-- 1.3.6.1.4.1.6296.101.20.5.1.1.1.22
		sleEponProfileLoopDetectSendingpacket OBJECT-TYPE
			SYNTAX INTEGER (0 | 1..60)
			MAX-ACCESS read-only
			STATUS current
			DESCRIPTION
				"Description."
			::= { sleEponProfileEntry 22 }

		
--  1.3.6.1.4.1.6296.101.20.5.1.2
		-- 1.3.6.1.4.1.6296.101.20.5.1.2
		sleEponProfileControl OBJECT IDENTIFIER ::= { sleEponProfileBase 2 }

		
--  1.3.6.1.4.1.6296.101.20.5.1.2.1
		-- 1.3.6.1.4.1.6296.101.20.5.1.2.1
		sleEponProfileControlRequest OBJECT-TYPE
			SYNTAX INTEGER
				{
				createProfile(1),
				modifyProfile(2),
				destroyProfile(3),
				modifyProfileMtu(4),
				modifyProfileIgmp(5),
				modifyProfileSTP(6),
				createDefaultProfile(7),
				modifyProfileSubscriber(8),
				modifyProfileLoopDetect(9)
				}
			MAX-ACCESS read-write
			STATUS current
			DESCRIPTION
				"The request of a user command"
			::= { sleEponProfileControl 1 }

		
--  1.3.6.1.4.1.6296.101.20.5.1.2.2
		-- 1.3.6.1.4.1.6296.101.20.5.1.2.2
		sleEponProfileControlStatus OBJECT-TYPE
			SYNTAX SleControlStatusType
			MAX-ACCESS read-only
			STATUS current
			DESCRIPTION
				"The status of user command"
			::= { sleEponProfileControl 2 }

		
--  1.3.6.1.4.1.6296.101.20.5.1.2.3
		-- 1.3.6.1.4.1.6296.101.20.5.1.2.3
		sleEponProfileControlTimer OBJECT-TYPE
			SYNTAX Gauge32
			MAX-ACCESS read-write
			STATUS current
			DESCRIPTION
				"The maximum time for the manager for a long running user command"
			::= { sleEponProfileControl 3 }

		
--  1.3.6.1.4.1.6296.101.20.5.1.2.4
		-- 1.3.6.1.4.1.6296.101.20.5.1.2.4
		sleEponProfileControlTimeStamp OBJECT-TYPE
			SYNTAX TimeTicks
			MAX-ACCESS read-only
			STATUS current
			DESCRIPTION
				"The time stamp of the last command(end of command)"
			::= { sleEponProfileControl 4 }

		
--  1.3.6.1.4.1.6296.101.20.5.1.2.5
		-- 1.3.6.1.4.1.6296.101.20.5.1.2.5
		sleEponProfileControlReqResult OBJECT-TYPE
			SYNTAX SleControlRequestResultType
			MAX-ACCESS read-only
			STATUS current
			DESCRIPTION
				"The result of the last user command"
			::= { sleEponProfileControl 5 }

		
--  1.3.6.1.4.1.6296.101.20.5.1.2.6
		-- 1.3.6.1.4.1.6296.101.20.5.1.2.6
		sleEponProfileControlIndex OBJECT-TYPE
			SYNTAX INTEGER (1..32)
			MAX-ACCESS read-write
			STATUS current
			DESCRIPTION
				"Profile index"
			::= { sleEponProfileControl 6 }

		
--  1.3.6.1.4.1.6296.101.20.5.1.2.7
		-- 1.3.6.1.4.1.6296.101.20.5.1.2.7
		sleEponProfileControlName OBJECT-TYPE
			SYNTAX OCTET STRING (SIZE (1..64))
			MAX-ACCESS read-write
			STATUS current
			DESCRIPTION
				"Profile name"
			::= { sleEponProfileControl 7 }

		
--  1.3.6.1.4.1.6296.101.20.5.1.2.8
		-- 1.3.6.1.4.1.6296.101.20.5.1.2.8
		sleEponProfileControlDPDownMaxBandwidth OBJECT-TYPE
			SYNTAX INTEGER (0 | 1..1000000)
			UNITS "kbps"
			MAX-ACCESS read-write
			STATUS current
			DESCRIPTION
				"Download policy Down Max Bandwidth "
			::= { sleEponProfileControl 8 }

		
--  1.3.6.1.4.1.6296.101.20.5.1.2.9
		-- 1.3.6.1.4.1.6296.101.20.5.1.2.9
		sleEponProfileControlDPDownMaxBurstSize OBJECT-TYPE
			SYNTAX INTEGER (0 | 128..8388479)
			UNITS "byte"
			MAX-ACCESS read-write
			STATUS current
			DESCRIPTION
				"Download policy Down Max Burst Size"
			::= { sleEponProfileControl 9 }

		
--  1.3.6.1.4.1.6296.101.20.5.1.2.10
		-- 1.3.6.1.4.1.6296.101.20.5.1.2.10
		sleEponProfileControlDPP2pMaxBandwidth OBJECT-TYPE
			SYNTAX INTEGER (0 | 1..1000000)
			UNITS "kbps"
			MAX-ACCESS read-write
			STATUS current
			DESCRIPTION
				"Download policy P2P Max Bandwidth"
			::= { sleEponProfileControl 10 }

		
--  1.3.6.1.4.1.6296.101.20.5.1.2.11
		-- 1.3.6.1.4.1.6296.101.20.5.1.2.11
		sleEponProfileControlDPP2pMaxBurstSize OBJECT-TYPE
			SYNTAX INTEGER (0 | 128..8388479)
			UNITS "byte"
			MAX-ACCESS read-write
			STATUS current
			DESCRIPTION
				"Download policy P2P Max Burst Size "
			::= { sleEponProfileControl 11 }

		
--  1.3.6.1.4.1.6296.101.20.5.1.2.12
		-- 1.3.6.1.4.1.6296.101.20.5.1.2.12
		sleEponProfileControlSlaGuaranteedBandwidth OBJECT-TYPE
			SYNTAX INTEGER (43..65535)
			UNITS "TQ"
			MAX-ACCESS read-write
			STATUS current
			DESCRIPTION
				"SLA-internal Guranteed Bandwidth"
			DEFVAL { 85 }
			::= { sleEponProfileControl 12 }

		
--  1.3.6.1.4.1.6296.101.20.5.1.2.13
		-- 1.3.6.1.4.1.6296.101.20.5.1.2.13
		sleEponProfileControlSlaBestEffortBandwidth OBJECT-TYPE
			SYNTAX INTEGER (43..65535)
			UNITS "TQ"
			MAX-ACCESS read-write
			STATUS current
			DESCRIPTION
				"SLA-internal Best effort Bandwidth"
			DEFVAL { 85 }
			::= { sleEponProfileControl 13 }

		
--  1.3.6.1.4.1.6296.101.20.5.1.2.14
		-- 1.3.6.1.4.1.6296.101.20.5.1.2.14
		sleEponProfileControlSlaPlatoClass OBJECT-TYPE
			SYNTAX INTEGER (0..7)
			MAX-ACCESS read-write
			STATUS current
			DESCRIPTION
				"SLA-Plato Class"
			::= { sleEponProfileControl 14 }

		
--  1.3.6.1.4.1.6296.101.20.5.1.2.15
		-- 1.3.6.1.4.1.6296.101.20.5.1.2.15
		sleEponProfileControlSlaPlatoGuaranteedBandwidth1m OBJECT-TYPE
			SYNTAX INTEGER (1..1000)
			UNITS "Mbps"
			MAX-ACCESS read-write
			STATUS current
			DESCRIPTION
				"SLA-Plato Minimum Bandwidth_1m"
			DEFVAL { 1 }
			::= { sleEponProfileControl 15 }

		
--  1.3.6.1.4.1.6296.101.20.5.1.2.16
		-- 1.3.6.1.4.1.6296.101.20.5.1.2.16
		sleEponProfileControlSlaPlatoGuaranteedBandwdith64k OBJECT-TYPE
			SYNTAX INTEGER (0..1024)
			UNITS "64Kbps"
			MAX-ACCESS read-write
			STATUS current
			DESCRIPTION
				"SLA-plato Minimum Bandwidth_64k"
			DEFVAL { 0 }
			::= { sleEponProfileControl 16 }

		
--  1.3.6.1.4.1.6296.101.20.5.1.2.17
		-- 1.3.6.1.4.1.6296.101.20.5.1.2.17
		sleEponProfileControlSlaPlatoBestEffortBandwidth1m OBJECT-TYPE
			SYNTAX INTEGER (1..1000)
			UNITS "Mbps"
			MAX-ACCESS read-write
			STATUS current
			DESCRIPTION
				"SLA-plato Max bandwidth_1m"
			DEFVAL { 2 }
			::= { sleEponProfileControl 17 }

		
--  1.3.6.1.4.1.6296.101.20.5.1.2.18
		-- 1.3.6.1.4.1.6296.101.20.5.1.2.18
		sleEponProfileControlSlaPlatoBestEffortBandwidth64k OBJECT-TYPE
			SYNTAX INTEGER (0..1024)
			UNITS "64Kbps"
			MAX-ACCESS read-write
			STATUS current
			DESCRIPTION
				"SLA-plato Max bandwidth_64k"
			DEFVAL { 0 }
			::= { sleEponProfileControl 18 }

		
--  1.3.6.1.4.1.6296.101.20.5.1.2.19
		-- 1.3.6.1.4.1.6296.101.20.5.1.2.19
		sleEponProfileControlSlaPlatoDelayLevel OBJECT-TYPE
			SYNTAX INTEGER (1..2)
			MAX-ACCESS read-write
			STATUS current
			DESCRIPTION
				"SLA-plato Delay  level"
			DEFVAL { 1 }
			::= { sleEponProfileControl 19 }

		
--  1.3.6.1.4.1.6296.101.20.5.1.2.20
		-- 1.3.6.1.4.1.6296.101.20.5.1.2.20
		sleEponProfileControlExtendMtu OBJECT-TYPE
			SYNTAX EnableFlag
			MAX-ACCESS read-write
			STATUS current
			DESCRIPTION
				"Description."
			::= { sleEponProfileControl 20 }

		
--  1.3.6.1.4.1.6296.101.20.5.1.2.21
		-- 1.3.6.1.4.1.6296.101.20.5.1.2.21
		sleEponProfileControlIgmpFilter OBJECT-TYPE
			SYNTAX EnableFlag
			MAX-ACCESS read-write
			STATUS current
			DESCRIPTION
				"Description."
			::= { sleEponProfileControl 21 }

		
--  1.3.6.1.4.1.6296.101.20.5.1.2.22
		-- 1.3.6.1.4.1.6296.101.20.5.1.2.22
		sleEponProfileControlSnooping OBJECT-TYPE
			SYNTAX EnableFlag
			MAX-ACCESS read-write
			STATUS current
			DESCRIPTION
				"Description."
			::= { sleEponProfileControl 22 }

		
--  1.3.6.1.4.1.6296.101.20.5.1.2.23
		-- 1.3.6.1.4.1.6296.101.20.5.1.2.23
		sleEponProfileControlSTPenable OBJECT-TYPE
			SYNTAX EnableFlag
			MAX-ACCESS read-write
			STATUS current
			DESCRIPTION
				"Description."
			::= { sleEponProfileControl 23 }

		
--  1.3.6.1.4.1.6296.101.20.5.1.2.25
		-- 1.3.6.1.4.1.6296.101.20.5.1.2.24
		sleEponProfileControlSubscriberInfoCollection OBJECT-TYPE
			SYNTAX EnableFlag
			MAX-ACCESS read-write
			STATUS current
			DESCRIPTION
				"Description."
			::= { sleEponProfileControl 24 }

		
--  1.3.6.1.4.1.6296.101.20.5.1.2.26
		-- 1.3.6.1.4.1.6296.101.20.5.1.2.25
		sleEponProfileControlLoopDetectStatus OBJECT-TYPE
			SYNTAX EnableFlag
			MAX-ACCESS read-write
			STATUS current
			DESCRIPTION
				"Description."
			::= { sleEponProfileControl 25 }

		
--  1.3.6.1.4.1.6296.101.20.5.1.2.27
		-- 1.3.6.1.4.1.6296.101.20.5.1.2.26
		sleEponProfileControlLoopDetectBlockTimer OBJECT-TYPE
			SYNTAX INTEGER (0 | 10..86400)
			MAX-ACCESS read-write
			STATUS current
			DESCRIPTION
				"Description."
			::= { sleEponProfileControl 26 }

		
--  1.3.6.1.4.1.6296.101.20.5.1.2.28
		-- 1.3.6.1.4.1.6296.101.20.5.1.2.27
		sleEponProfileControlLoopDetectSendingpacket OBJECT-TYPE
			SYNTAX INTEGER (0 | 1..60)
			MAX-ACCESS read-write
			STATUS current
			DESCRIPTION
				"Description."
			::= { sleEponProfileControl 27 }

		
--  1.3.6.1.4.1.6296.101.20.5.1.3
		-- 1.3.6.1.4.1.6296.101.20.5.1.3
		sleEponProfileNotification OBJECT IDENTIFIER ::= { sleEponProfileBase 3 }

		
--  1.3.6.1.4.1.6296.101.20.5.1.3.1
		-- 1.3.6.1.4.1.6296.101.20.5.1.3.1
		sleEponProfileCreated NOTIFICATION-TYPE
			OBJECTS { sleEponProfileControlRequest, sleEponProfileControlTimeStamp, sleEponProfileControlReqResult, sleEponProfileControlIndex, sleEponProfileControlName
				 }
			STATUS current
			DESCRIPTION 
				"Description."
			::= { sleEponProfileNotification 1 }

		
--  1.3.6.1.4.1.6296.101.20.5.1.3.2
		-- 1.3.6.1.4.1.6296.101.20.5.1.3.2
		sleEponProfileModified NOTIFICATION-TYPE
			OBJECTS { sleEponProfileControlRequest, sleEponProfileControlTimeStamp, sleEponProfileControlReqResult, sleEponProfileControlIndex, sleEponProfileControlName
				 }
			STATUS current
			DESCRIPTION 
				"Description."
			::= { sleEponProfileNotification 2 }

		
--  1.3.6.1.4.1.6296.101.20.5.1.3.3
		-- 1.3.6.1.4.1.6296.101.20.5.1.3.3
		sleEponProfileDestroyed NOTIFICATION-TYPE
			OBJECTS { sleEponProfileControlRequest, sleEponProfileControlTimeStamp, sleEponProfileControlReqResult, sleEponProfileControlIndex, sleEponProfileControlName
				 }
			STATUS current
			DESCRIPTION 
				"Description."
			::= { sleEponProfileNotification 3 }

		
--  1.3.6.1.4.1.6296.101.20.5.1.3.4
		-- 1.3.6.1.4.1.6296.101.20.5.1.3.4
		sleEponProfileExtendMtuChanged NOTIFICATION-TYPE
			OBJECTS { sleEponProfileControlRequest, sleEponProfileControlTimeStamp, sleEponProfileControlReqResult, sleEponProfileControlIndex, sleEponProfileControlName, 
				sleEponProfileControlExtendMtu }
			STATUS current
			DESCRIPTION 
				"Description."
			::= { sleEponProfileNotification 4 }

		
--  1.3.6.1.4.1.6296.101.20.5.1.3.5
		-- 1.3.6.1.4.1.6296.101.20.5.1.3.5
		sleEponProfileIgmpChanged NOTIFICATION-TYPE
			OBJECTS { sleEponProfileControlRequest, sleEponProfileControlTimeStamp, sleEponProfileControlReqResult, sleEponProfileControlIndex, sleEponProfileControlName, 
				sleEponProfileControlIgmpFilter, sleEponProfileControlSnooping }
			STATUS current
			DESCRIPTION 
				"Description."
			::= { sleEponProfileNotification 5 }

		
--  1.3.6.1.4.1.6296.101.20.5.1.3.6
		-- 1.3.6.1.4.1.6296.101.20.5.1.3.6
		sleEponProfileSTPChanged NOTIFICATION-TYPE
			OBJECTS { sleEponProfileControlRequest, sleEponProfileControlTimeStamp, sleEponProfileControlReqResult, sleEponProfileControlIndex, sleEponProfileControlName, 
				sleEponProfileControlSTPenable }
			STATUS current
			DESCRIPTION 
				"Description."
			::= { sleEponProfileNotification 6 }

		
--  1.3.6.1.4.1.6296.101.20.5.1.3.7
		-- 1.3.6.1.4.1.6296.101.20.5.1.3.7
		sleEponProfileDefaultProfileCreated NOTIFICATION-TYPE
			OBJECTS { sleEponProfileQueueControlRequest, sleEponProfileQueueControlTimeStamp, sleEponProfileQueueControlReqResult }
			STATUS current
			DESCRIPTION 
				"Description."
			::= { sleEponProfileNotification 7 }

		
--  1.3.6.1.4.1.6296.101.20.5.1.3.9
		-- 1.3.6.1.4.1.6296.101.20.5.1.3.8
		sleEponProfileSubscriberChanged NOTIFICATION-TYPE
			OBJECTS { sleEponProfileControlRequest, sleEponProfileControlTimeStamp, sleEponProfileControlReqResult, sleEponProfileControlIndex, sleEponProfileControlName, 
				sleEponProfileControlSubscriberInfoCollection }
			STATUS current
			DESCRIPTION 
				"Description."
			::= { sleEponProfileNotification 8 }

		
--  1.3.6.1.4.1.6296.101.20.5.1.3.10
		-- 1.3.6.1.4.1.6296.101.20.5.1.3.9
		sleEponProfileLoopDetectChanged NOTIFICATION-TYPE
			OBJECTS { sleEponProfileControlRequest, sleEponProfileControlTimeStamp, sleEponProfileControlReqResult, sleEponProfileControlIndex, sleEponProfileControlName, 
				sleEponProfileControlLoopDetectStatus, sleEponProfileControlLoopDetectBlockTimer, sleEponProfileControlLoopDetectSendingpacket }
			STATUS current
			DESCRIPTION 
				"Description."
			::= { sleEponProfileNotification 9 }

		
--  1.3.6.1.4.1.6296.101.20.5.2
		-- 1.3.6.1.4.1.6296.101.20.5.2
		sleEponProfileQueue OBJECT IDENTIFIER ::= { sleEponProfile 2 }

		
--  1.3.6.1.4.1.6296.101.20.5.2.1
		-- 1.3.6.1.4.1.6296.101.20.5.2.1
		sleEponProfileQueueTable OBJECT-TYPE
			SYNTAX SEQUENCE OF SleEponProfileQueueEntry
			MAX-ACCESS not-accessible
			STATUS current
			DESCRIPTION
				"Description."
			::= { sleEponProfileQueue 1 }

		
--  1.3.6.1.4.1.6296.101.20.5.5.1.1
		-- 1.3.6.1.4.1.6296.101.20.5.2.1.1
		sleEponProfileQueueEntry OBJECT-TYPE
			SYNTAX SleEponProfileQueueEntry
			MAX-ACCESS not-accessible
			STATUS current
			DESCRIPTION
				"Description."
			INDEX { sleEponProfileIndex, sleEponProfileQueueIndex }
			::= { sleEponProfileQueueTable 1 }

		
		SleEponProfileQueueEntry ::=
			SEQUENCE { 
				sleEponProfileQueueIndex
					INTEGER,
				sleEponProfileQueueQPUpQueue
					INTEGER,
				sleEponProfileQueueQPUpMaxBandwidth
					INTEGER,
				sleEponProfileQueueQPUpMAxBurstSize
					INTEGER,
				sleEponProfileQueueQPDownQueue
					INTEGER,
				sleEponProfileQueueQPDownMaxBandwidth
					INTEGER,
				sleEponProfileQueueQPDownMAxBurstSize
					INTEGER,
				sleEponProfileQueueQLimitUpBlockSize
					INTEGER,
				sleEponProfileQueueQLimitDownBlockSize
					INTEGER
			 }

--  1.3.6.1.4.1.6296.101.20.5.5.1.1.1
		-- 1.3.6.1.4.1.6296.101.20.5.2.1.1.1
		sleEponProfileQueueIndex OBJECT-TYPE
			SYNTAX INTEGER (1..8)
			MAX-ACCESS read-only
			STATUS current
			DESCRIPTION
				"Profile Queue index "
			::= { sleEponProfileQueueEntry 1 }

		
--  1.3.6.1.4.1.6296.101.20.5.5.1.1.2
		-- 1.3.6.1.4.1.6296.101.20.5.2.1.1.2
		sleEponProfileQueueQPUpQueue OBJECT-TYPE
			SYNTAX INTEGER (0..7)
			MAX-ACCESS read-only
			STATUS current
			DESCRIPTION
				"Upstream queue number"
			::= { sleEponProfileQueueEntry 2 }

		
--  1.3.6.1.4.1.6296.101.20.5.5.1.1.3
		-- 1.3.6.1.4.1.6296.101.20.5.2.1.1.3
		sleEponProfileQueueQPUpMaxBandwidth OBJECT-TYPE
			SYNTAX INTEGER (0 | 100..1000000)
			UNITS "kbps"
			MAX-ACCESS read-only
			STATUS current
			DESCRIPTION
				"Upstream queue max bandwidth"
			::= { sleEponProfileQueueEntry 3 }

		
--  1.3.6.1.4.1.6296.101.20.5.5.1.1.4
		-- 1.3.6.1.4.1.6296.101.20.5.2.1.1.4
		sleEponProfileQueueQPUpMAxBurstSize OBJECT-TYPE
			SYNTAX INTEGER (0 | 2..16777214)
			UNITS "byte"
			MAX-ACCESS read-only
			STATUS current
			DESCRIPTION
				"Upstream queue max burst size"
			::= { sleEponProfileQueueEntry 4 }

		
--  1.3.6.1.4.1.6296.101.20.5.5.1.1.5
		-- 1.3.6.1.4.1.6296.101.20.5.2.1.1.5
		sleEponProfileQueueQPDownQueue OBJECT-TYPE
			SYNTAX INTEGER (0..7)
			MAX-ACCESS read-only
			STATUS current
			DESCRIPTION
				"Downstream queue number"
			::= { sleEponProfileQueueEntry 5 }

		
--  1.3.6.1.4.1.6296.101.20.5.5.1.1.6
		-- 1.3.6.1.4.1.6296.101.20.5.2.1.1.6
		sleEponProfileQueueQPDownMaxBandwidth OBJECT-TYPE
			SYNTAX INTEGER (0 | 100..1000000)
			UNITS "kbps"
			MAX-ACCESS read-only
			STATUS current
			DESCRIPTION
				"Downtream queue max bandwidth"
			::= { sleEponProfileQueueEntry 6 }

		
--  1.3.6.1.4.1.6296.101.20.5.5.1.1.7
		-- 1.3.6.1.4.1.6296.101.20.5.2.1.1.7
		sleEponProfileQueueQPDownMAxBurstSize OBJECT-TYPE
			SYNTAX INTEGER (0 | 2..16777214)
			UNITS "byte"
			MAX-ACCESS read-only
			STATUS current
			DESCRIPTION
				"Downtream queue max burst size"
			::= { sleEponProfileQueueEntry 7 }

		
--  1.3.6.1.4.1.6296.101.20.5.5.1.1.8
		-- 1.3.6.1.4.1.6296.101.20.5.2.1.1.8
		sleEponProfileQueueQLimitUpBlockSize OBJECT-TYPE
			SYNTAX INTEGER (-1 | 0..9215)
			MAX-ACCESS read-only
			STATUS current
			DESCRIPTION
				"Description."
			::= { sleEponProfileQueueEntry 8 }

		
--  1.3.6.1.4.1.6296.101.20.5.5.1.1.9
		-- 1.3.6.1.4.1.6296.101.20.5.2.1.1.9
		sleEponProfileQueueQLimitDownBlockSize OBJECT-TYPE
			SYNTAX INTEGER (-1 | 0..9215)
			MAX-ACCESS read-only
			STATUS current
			DESCRIPTION
				"Description."
			::= { sleEponProfileQueueEntry 9 }

		
--  1.3.6.1.4.1.6296.101.20.5.2.2
		-- 1.3.6.1.4.1.6296.101.20.5.2.2
		sleEponProfileQueueControl OBJECT IDENTIFIER ::= { sleEponProfileQueue 2 }

		
--  1.3.6.1.4.1.6296.101.20.5.2.2.1
		-- 1.3.6.1.4.1.6296.101.20.5.2.2.1
		sleEponProfileQueueControlRequest OBJECT-TYPE
			SYNTAX INTEGER
				{
				modifyProfileQuuePolicyUp(1),
				modifyProfileQuuePolicyDown(2),
				modifyProfileQueueLimit(3)
				}
			MAX-ACCESS read-write
			STATUS current
			DESCRIPTION
				"The request of a user command"
			::= { sleEponProfileQueueControl 1 }

		
--  1.3.6.1.4.1.6296.101.20.5.2.2.2
		-- 1.3.6.1.4.1.6296.101.20.5.2.2.2
		sleEponProfileQueueControlStatus OBJECT-TYPE
			SYNTAX SleControlStatusType
			MAX-ACCESS read-only
			STATUS current
			DESCRIPTION
				"The status of user command"
			::= { sleEponProfileQueueControl 2 }

		
--  1.3.6.1.4.1.6296.101.20.5.2.2.3
		-- 1.3.6.1.4.1.6296.101.20.5.2.2.3
		sleEponProfileQueueControlTimer OBJECT-TYPE
			SYNTAX Gauge32
			MAX-ACCESS read-write
			STATUS current
			DESCRIPTION
				"The maximum time for the manager for a long running user command"
			::= { sleEponProfileQueueControl 3 }

		
--  1.3.6.1.4.1.6296.101.20.5.2.2.4
		-- 1.3.6.1.4.1.6296.101.20.5.2.2.4
		sleEponProfileQueueControlTimeStamp OBJECT-TYPE
			SYNTAX TimeTicks
			MAX-ACCESS read-only
			STATUS current
			DESCRIPTION
				"The time stamp of the last command(end of command)"
			::= { sleEponProfileQueueControl 4 }

		
--  1.3.6.1.4.1.6296.101.20.5.2.2.5
		-- 1.3.6.1.4.1.6296.101.20.5.2.2.5
		sleEponProfileQueueControlReqResult OBJECT-TYPE
			SYNTAX SleControlRequestResultType
			MAX-ACCESS read-only
			STATUS current
			DESCRIPTION
				"The result of the last user command"
			::= { sleEponProfileQueueControl 5 }

		
--  1.3.6.1.4.1.6296.101.20.5.2.2.6
		-- 1.3.6.1.4.1.6296.101.20.5.2.2.6
		sleEponProfileQueueControlProfileIndex OBJECT-TYPE
			SYNTAX INTEGER (1..32)
			MAX-ACCESS read-write
			STATUS current
			DESCRIPTION
				"Profile Index"
			::= { sleEponProfileQueueControl 6 }

		
--  1.3.6.1.4.1.6296.101.20.5.2.2.7
		-- 1.3.6.1.4.1.6296.101.20.5.2.2.7
		sleEponProfileQueueControlQueueIndex OBJECT-TYPE
			SYNTAX INTEGER (1..8)
			MAX-ACCESS read-write
			STATUS current
			DESCRIPTION
				"Profile Queue index "
			::= { sleEponProfileQueueControl 7 }

		
--  1.3.6.1.4.1.6296.101.20.5.2.2.8
		-- 1.3.6.1.4.1.6296.101.20.5.2.2.8
		sleEponProfileQueueControlQPUpQueue OBJECT-TYPE
			SYNTAX INTEGER (0..7)
			MAX-ACCESS read-write
			STATUS current
			DESCRIPTION
				"Upstream queue number"
			::= { sleEponProfileQueueControl 8 }

		
--  1.3.6.1.4.1.6296.101.20.5.2.2.9
		-- 1.3.6.1.4.1.6296.101.20.5.2.2.9
		sleEponProfileQueueControlQPUpMaxBandwidth OBJECT-TYPE
			SYNTAX INTEGER (0 | 100..1000000)
			UNITS "kbps"
			MAX-ACCESS read-write
			STATUS current
			DESCRIPTION
				"Upstream queue max bandwidth"
			::= { sleEponProfileQueueControl 9 }

		
--  1.3.6.1.4.1.6296.101.20.5.2.2.10
		-- 1.3.6.1.4.1.6296.101.20.5.2.2.10
		sleEponProfileQueueControlQPUpMAxBurstSize OBJECT-TYPE
			SYNTAX INTEGER (0 | 2..16777214)
			UNITS "byte"
			MAX-ACCESS read-write
			STATUS current
			DESCRIPTION
				"Upstream queue max burst size"
			::= { sleEponProfileQueueControl 10 }

		
--  1.3.6.1.4.1.6296.101.20.5.2.2.11
		-- 1.3.6.1.4.1.6296.101.20.5.2.2.11
		sleEponProfileQueueControlQPDownQueue OBJECT-TYPE
			SYNTAX INTEGER (0..7)
			MAX-ACCESS read-write
			STATUS current
			DESCRIPTION
				"Downstream queue number"
			::= { sleEponProfileQueueControl 11 }

		
--  1.3.6.1.4.1.6296.101.20.5.2.2.12
		-- 1.3.6.1.4.1.6296.101.20.5.2.2.12
		sleEponProfileQueueControlQPDownMaxBandwidth OBJECT-TYPE
			SYNTAX INTEGER (0 | 100..1000000)
			UNITS "kbps"
			MAX-ACCESS read-write
			STATUS current
			DESCRIPTION
				"Downtream queue max bandwidth"
			::= { sleEponProfileQueueControl 12 }

		
--  1.3.6.1.4.1.6296.101.20.5.2.2.13
		-- 1.3.6.1.4.1.6296.101.20.5.2.2.13
		sleEponProfileQueueControlQPDownMAxBurstSize OBJECT-TYPE
			SYNTAX INTEGER (0 | 2..16777214)
			UNITS "byte"
			MAX-ACCESS read-write
			STATUS current
			DESCRIPTION
				"Downtream queue max burst size"
			::= { sleEponProfileQueueControl 13 }

		
--  1.3.6.1.4.1.6296.101.20.5.2.2.14
		-- 1.3.6.1.4.1.6296.101.20.5.2.2.14
		sleEponProfileQueueControlLimitFlag OBJECT-TYPE
			SYNTAX INTEGER
				{
				up(1),
				down(2)
				}
			MAX-ACCESS read-write
			STATUS current
			DESCRIPTION
				"Description."
			::= { sleEponProfileQueueControl 14 }

		
--  1.3.6.1.4.1.6296.101.20.5.2.2.15
		-- 1.3.6.1.4.1.6296.101.20.5.2.2.15
		sleEponProfileQueueControlBlockSize0 OBJECT-TYPE
			SYNTAX INTEGER (-1 | 0..9215)
			MAX-ACCESS read-write
			STATUS current
			DESCRIPTION
				"Description."
			::= { sleEponProfileQueueControl 15 }

		
--  1.3.6.1.4.1.6296.101.20.5.2.2.16
		-- 1.3.6.1.4.1.6296.101.20.5.2.2.16
		sleEponProfileQueueControlBlockSize1 OBJECT-TYPE
			SYNTAX INTEGER (-1 | 0..9215)
			MAX-ACCESS read-write
			STATUS current
			DESCRIPTION
				"Description."
			::= { sleEponProfileQueueControl 16 }

		
--  1.3.6.1.4.1.6296.101.20.5.2.2.17
		-- 1.3.6.1.4.1.6296.101.20.5.2.2.17
		sleEponProfileQueueControlBlockSize2 OBJECT-TYPE
			SYNTAX INTEGER (-1 | 0..9215)
			MAX-ACCESS read-write
			STATUS current
			DESCRIPTION
				"Description."
			::= { sleEponProfileQueueControl 17 }

		
--  1.3.6.1.4.1.6296.101.20.5.2.2.18
		-- 1.3.6.1.4.1.6296.101.20.5.2.2.18
		sleEponProfileQueueControlBlockSize3 OBJECT-TYPE
			SYNTAX INTEGER (-1 | 0..9215)
			MAX-ACCESS read-write
			STATUS current
			DESCRIPTION
				"Description."
			::= { sleEponProfileQueueControl 18 }

		
--  1.3.6.1.4.1.6296.101.20.5.2.2.19
		-- 1.3.6.1.4.1.6296.101.20.5.2.2.19
		sleEponProfileQueueControlBlockSize4 OBJECT-TYPE
			SYNTAX INTEGER (-1 | 0..9152)
			MAX-ACCESS read-write
			STATUS current
			DESCRIPTION
				"Description."
			::= { sleEponProfileQueueControl 19 }

		
--  1.3.6.1.4.1.6296.101.20.5.2.2.20
		-- 1.3.6.1.4.1.6296.101.20.5.2.2.20
		sleEponProfileQueueControlBlockSize5 OBJECT-TYPE
			SYNTAX INTEGER (-1 | 0..9152)
			MAX-ACCESS read-write
			STATUS current
			DESCRIPTION
				"Description."
			::= { sleEponProfileQueueControl 20 }

		
--  1.3.6.1.4.1.6296.101.20.5.2.2.21
		-- 1.3.6.1.4.1.6296.101.20.5.2.2.21
		sleEponProfileQueueControlBlockSize6 OBJECT-TYPE
			SYNTAX INTEGER (-1 | 0..9152)
			MAX-ACCESS read-write
			STATUS current
			DESCRIPTION
				"Description."
			::= { sleEponProfileQueueControl 21 }

		
--  1.3.6.1.4.1.6296.101.20.5.2.2.22
		-- 1.3.6.1.4.1.6296.101.20.5.2.2.22
		sleEponProfileQueueControlBlockSize7 OBJECT-TYPE
			SYNTAX INTEGER (-1 | 0..9152)
			MAX-ACCESS read-write
			STATUS current
			DESCRIPTION
				"Description."
			::= { sleEponProfileQueueControl 22 }

		
--  1.3.6.1.4.1.6296.101.20.5.2.3
		-- 1.3.6.1.4.1.6296.101.20.5.2.3
		sleEponProfileQueueNotification OBJECT IDENTIFIER ::= { sleEponProfileQueue 3 }

		
--  1.3.6.1.4.1.6296.101.20.5.2.3.1
		-- 1.3.6.1.4.1.6296.101.20.5.2.3.1
		sleEponProfileQueueModifyQueuePolicy NOTIFICATION-TYPE
			OBJECTS { sleEponProfileQueueControlRequest, sleEponProfileQueueControlTimeStamp, sleEponProfileQueueControlReqResult, sleEponProfileQueueControlProfileIndex, sleEponProfileQueueControlQueueIndex
				 }
			STATUS current
			DESCRIPTION 
				"Description."
			::= { sleEponProfileQueueNotification 1 }

		
--  1.3.6.1.4.1.6296.101.20.5.2.3.2
		-- 1.3.6.1.4.1.6296.101.20.5.2.3.2
		sleEponProfileQueueModifyQueueLimit NOTIFICATION-TYPE
			OBJECTS { sleEponProfileQueueControlRequest, sleEponProfileQueueControlTimeStamp, sleEponProfileQueueControlReqResult, sleEponProfileQueueControlProfileIndex, sleEponProfileQueueControlLimitFlag, 
				sleEponProfileQueueControlBlockSize0, sleEponProfileQueueControlBlockSize1, sleEponProfileQueueControlBlockSize2, sleEponProfileQueueControlBlockSize3, sleEponProfileQueueControlBlockSize4, 
				sleEponProfileQueueControlBlockSize5, sleEponProfileQueueControlBlockSize6, sleEponProfileQueueControlBlockSize7 }
			STATUS current
			DESCRIPTION 
				"Description."
			::= { sleEponProfileQueueNotification 2 }

		
--  1.3.6.1.4.1.6296.101.20.5.3
		-- 1.3.6.1.4.1.6296.101.20.5.3
		sleEponProfileVlan OBJECT IDENTIFIER ::= { sleEponProfile 3 }

		
--  1.3.6.1.4.1.6296.101.20.5.3.1
		-- 1.3.6.1.4.1.6296.101.20.5.3.1
		sleEponProfileVlanTable OBJECT-TYPE
			SYNTAX SEQUENCE OF SleEponProfileVlanEntry
			MAX-ACCESS not-accessible
			STATUS current
			DESCRIPTION
				"Description."
			::= { sleEponProfileVlan 1 }

		
--  1.3.6.1.4.1.6296.101.20.5.3.1.1
		-- 1.3.6.1.4.1.6296.101.20.5.3.1.1
		sleEponProfileVlanEntry OBJECT-TYPE
			SYNTAX SleEponProfileVlanEntry
			MAX-ACCESS not-accessible
			STATUS current
			DESCRIPTION
				"Description."
			INDEX { sleEponProfileIndex, sleEponProfileVlanIndex }
			::= { sleEponProfileVlanTable 1 }

		
		SleEponProfileVlanEntry ::=
			SEQUENCE { 
				sleEponProfileVlanIndex
					VlanIndex,
				sleEponProfileVlanEgressPorts
					PortList,
				sleEponProfileVlanUntaggedPorts
					PortList
			 }

--  1.3.6.1.4.1.6296.101.20.5.3.1.1.1
		-- 1.3.6.1.4.1.6296.101.20.5.3.1.1.1
		sleEponProfileVlanIndex OBJECT-TYPE
			SYNTAX VlanIndex (1..4094)
			MAX-ACCESS read-only
			STATUS current
			DESCRIPTION
				"The index of ONU VLAN"
			::= { sleEponProfileVlanEntry 1 }

		
--  1.3.6.1.4.1.6296.101.20.5.3.1.1.2
		-- 1.3.6.1.4.1.6296.101.20.5.3.1.1.2
		sleEponProfileVlanEgressPorts OBJECT-TYPE
			SYNTAX PortList
			MAX-ACCESS read-only
			STATUS current
			DESCRIPTION
				"The set of ports which are transmitting traffic for this ONU VLAN as either tagged or untagged frames."
			::= { sleEponProfileVlanEntry 2 }

		
--  1.3.6.1.4.1.6296.101.20.5.3.1.1.3
		-- 1.3.6.1.4.1.6296.101.20.5.3.1.1.3
		sleEponProfileVlanUntaggedPorts OBJECT-TYPE
			SYNTAX PortList
			MAX-ACCESS read-only
			STATUS current
			DESCRIPTION
				"The set of ports which are transmitting traffic for this VLAN as untagged frames"
			::= { sleEponProfileVlanEntry 3 }

		
--  1.3.6.1.4.1.6296.101.20.5.3.2
		-- 1.3.6.1.4.1.6296.101.20.5.3.2
		sleEponProfileVlanControl OBJECT IDENTIFIER ::= { sleEponProfileVlan 2 }

		
--  1.3.6.1.4.1.6296.101.20.5.3.2.1
		-- 1.3.6.1.4.1.6296.101.20.5.3.2.1
		sleEponProfileVlanControlRequest OBJECT-TYPE
			SYNTAX INTEGER
				{
				createVlan(1),
				destroyVlan(2),
				setAddVlanProfile(3)
				}
			MAX-ACCESS read-write
			STATUS current
			DESCRIPTION
				"The request of a user command"
			::= { sleEponProfileVlanControl 1 }

		
--  1.3.6.1.4.1.6296.101.20.5.3.2.2
		-- 1.3.6.1.4.1.6296.101.20.5.3.2.2
		sleEponProfileVlanControlStatus OBJECT-TYPE
			SYNTAX SleControlStatusType
			MAX-ACCESS read-only
			STATUS current
			DESCRIPTION
				"The status of user command"
			::= { sleEponProfileVlanControl 2 }

		
--  1.3.6.1.4.1.6296.101.20.5.3.2.3
		-- 1.3.6.1.4.1.6296.101.20.5.3.2.3
		sleEponProfileVlanControlTimer OBJECT-TYPE
			SYNTAX Gauge32
			MAX-ACCESS read-write
			STATUS current
			DESCRIPTION
				"The maximum time for the manager for a long running user command"
			::= { sleEponProfileVlanControl 3 }

		
--  1.3.6.1.4.1.6296.101.20.5.3.2.4
		-- 1.3.6.1.4.1.6296.101.20.5.3.2.4
		sleEponProfileVlanControlTimeStamp OBJECT-TYPE
			SYNTAX TimeTicks
			MAX-ACCESS read-only
			STATUS current
			DESCRIPTION
				"The time stamp of the last command(end of command)"
			::= { sleEponProfileVlanControl 4 }

		
--  1.3.6.1.4.1.6296.101.20.5.3.2.5
		-- 1.3.6.1.4.1.6296.101.20.5.3.2.5
		sleEponProfileVlanControlReqResult OBJECT-TYPE
			SYNTAX SleControlRequestResultType
			MAX-ACCESS read-only
			STATUS current
			DESCRIPTION
				"The result of the last user command"
			::= { sleEponProfileVlanControl 5 }

		
--  1.3.6.1.4.1.6296.101.20.5.3.2.6
		-- 1.3.6.1.4.1.6296.101.20.5.3.2.6
		sleEponProfileVlanControlProfileIndex OBJECT-TYPE
			SYNTAX INTEGER (1..32)
			MAX-ACCESS read-write
			STATUS current
			DESCRIPTION
				"Description."
			::= { sleEponProfileVlanControl 6 }

		
--  1.3.6.1.4.1.6296.101.20.5.3.2.7
		-- 1.3.6.1.4.1.6296.101.20.5.3.2.7
		sleEponProfileVlanControlVlanIndex OBJECT-TYPE
			SYNTAX VlanIndex
			MAX-ACCESS read-write
			STATUS current
			DESCRIPTION
				"The index of ONU VLAN"
			::= { sleEponProfileVlanControl 7 }

		
--  1.3.6.1.4.1.6296.101.20.5.3.2.8
		-- 1.3.6.1.4.1.6296.101.20.5.3.2.8
		sleEponProfileVlanControlVlanEgressPorts OBJECT-TYPE
			SYNTAX PortList
			MAX-ACCESS read-write
			STATUS current
			DESCRIPTION
				"The set of ports which are transmitting traffic for this ONU VLAN as either tagged or untagged frames."
			::= { sleEponProfileVlanControl 8 }

		
--  1.3.6.1.4.1.6296.101.20.5.3.2.9
		-- 1.3.6.1.4.1.6296.101.20.5.3.2.9
		sleEponProfileVlanControlVlanUntaggedPorts OBJECT-TYPE
			SYNTAX PortList
			MAX-ACCESS read-write
			STATUS current
			DESCRIPTION
				"The set of ports which are transmitting traffic for this VLAN as untagged frames"
			::= { sleEponProfileVlanControl 9 }

		
--  1.3.6.1.4.1.6296.101.20.5.3.3
		-- 1.3.6.1.4.1.6296.101.20.5.3.3
		sleEponProfileVlanNotification OBJECT IDENTIFIER ::= { sleEponProfileVlan 3 }

		
--  1.3.6.1.4.1.6296.101.20.5.3.3.1
		-- 1.3.6.1.4.1.6296.101.20.5.3.3.1
		sleEponProfileVlanCreated NOTIFICATION-TYPE
			OBJECTS { sleEponProfileVlanControlRequest, sleEponProfileVlanControlTimeStamp, sleEponProfileVlanControlReqResult, sleEponProfileControlIndex, sleEponProfileControlName, 
				sleEponProfileVlanControlVlanIndex }
			STATUS current
			DESCRIPTION 
				"Description."
			::= { sleEponProfileVlanNotification 1 }

		
--  1.3.6.1.4.1.6296.101.20.5.3.3.2
		-- 1.3.6.1.4.1.6296.101.20.5.3.3.2
		sleEponProfileVlanDestroyed NOTIFICATION-TYPE
			OBJECTS { sleEponProfileVlanControlRequest, sleEponProfileVlanControlTimeStamp, sleEponProfileVlanControlReqResult, sleEponProfileControlIndex, sleEponProfileControlName, 
				sleEponProfileVlanControlVlanIndex }
			STATUS current
			DESCRIPTION 
				"Description."
			::= { sleEponProfileVlanNotification 2 }

		
--  1.3.6.1.4.1.6296.101.20.5.3.3.3
		-- 1.3.6.1.4.1.6296.101.20.5.3.3.3
		sleEponProfileVlanProfileChanged NOTIFICATION-TYPE
			OBJECTS { sleEponProfileVlanControlRequest, sleEponProfileVlanControlTimeStamp, sleEponProfileVlanControlReqResult, sleEponProfileControlIndex, sleEponProfileControlName, 
				sleEponProfileVlanControlVlanIndex, sleEponProfileVlanControlVlanEgressPorts, sleEponProfileVlanControlVlanUntaggedPorts }
			STATUS current
			DESCRIPTION 
				"Description."
			::= { sleEponProfileVlanNotification 3 }

		
--  1.3.6.1.4.1.6296.101.20.5.4
		-- 1.3.6.1.4.1.6296.101.20.5.4
		sleEponProfilePort OBJECT IDENTIFIER ::= { sleEponProfile 4 }

		
--  1.3.6.1.4.1.6296.101.20.5.4.1
		-- 1.3.6.1.4.1.6296.101.20.5.4.1
		sleEponProfilePortTable OBJECT-TYPE
			SYNTAX SEQUENCE OF SleEponProfilePortEntry
			MAX-ACCESS not-accessible
			STATUS current
			DESCRIPTION
				"Description."
			::= { sleEponProfilePort 1 }

		
--  1.3.6.1.4.1.6296.101.20.5.4.1.1
		-- 1.3.6.1.4.1.6296.101.20.5.4.1.1
		sleEponProfilePortEntry OBJECT-TYPE
			SYNTAX SleEponProfilePortEntry
			MAX-ACCESS not-accessible
			STATUS current
			DESCRIPTION
				"Description."
			INDEX { sleEponProfileIndex, sleEponProfilePortIndex }
			::= { sleEponProfilePortTable 1 }

		
		SleEponProfilePortEntry ::=
			SEQUENCE { 
				sleEponProfilePortIndex
					INTEGER,
				sleEponProfilePortAdminStatus
					INTEGER,
				sleEponProfilePortNego
					INTEGER,
				sleEponProfilePortSpeed
					INTEGER,
				sleEponProfilePortduplex
					INTEGER,
				sleEponProfilePortMaxHost
					Integer32,
				sleEponProfilePortPvid
					VlanIndex,
				sleEponProfilePortIngressRateLimitMode
					INTEGER,
				sleEponProfilePortIngressRateLimit
					INTEGER,
				sleEponProfilePortEgressRateLimit
					INTEGER,
				sleEponProfilePortFlowControl
					INTEGER
			 }

--  1.3.6.1.4.1.6296.101.20.5.4.1.1.1
		-- 1.3.6.1.4.1.6296.101.20.5.4.1.1.1
		sleEponProfilePortIndex OBJECT-TYPE
			SYNTAX INTEGER (1..256)
			MAX-ACCESS read-only
			STATUS current
			DESCRIPTION
				"The index of the ONU port"
			::= { sleEponProfilePortEntry 1 }

		
--  1.3.6.1.4.1.6296.101.20.5.4.1.1.2
		-- 1.3.6.1.4.1.6296.101.20.5.4.1.1.2
		sleEponProfilePortAdminStatus OBJECT-TYPE
			SYNTAX INTEGER
				{
				enable(1),
				disable(2)
				}
			MAX-ACCESS read-only
			STATUS current
			DESCRIPTION
				"The desired state of the ONU port"
			::= { sleEponProfilePortEntry 2 }

		
--  1.3.6.1.4.1.6296.101.20.5.4.1.1.3
		-- 1.3.6.1.4.1.6296.101.20.5.4.1.1.3
		sleEponProfilePortNego OBJECT-TYPE
			SYNTAX INTEGER
				{
				on(1),
				off(2)
				}
			MAX-ACCESS read-only
			STATUS current
			DESCRIPTION
				"The current operational state of the ONU port"
			::= { sleEponProfilePortEntry 3 }

		
--  1.3.6.1.4.1.6296.101.20.5.4.1.1.4
		-- 1.3.6.1.4.1.6296.101.20.5.4.1.1.4
		sleEponProfilePortSpeed OBJECT-TYPE
			SYNTAX INTEGER (10 | 100)
			UNITS "Mbits/sec"
			MAX-ACCESS read-only
			STATUS current
			DESCRIPTION
				"It's auto-negotiation for a port, automatically to match the transmission speed and the duplex mode of the attached device"
			::= { sleEponProfilePortEntry 4 }

		
--  1.3.6.1.4.1.6296.101.20.5.4.1.1.5
		-- 1.3.6.1.4.1.6296.101.20.5.4.1.1.5
		sleEponProfilePortduplex OBJECT-TYPE
			SYNTAX INTEGER
				{
				full(1),
				half(2)
				}
			MAX-ACCESS read-only
			STATUS current
			DESCRIPTION
				"It express port speed that configure transmit rate of each port."
			::= { sleEponProfilePortEntry 5 }

		
--  1.3.6.1.4.1.6296.101.20.5.4.1.1.6
		-- 1.3.6.1.4.1.6296.101.20.5.4.1.1.6
		sleEponProfilePortMaxHost OBJECT-TYPE
			SYNTAX Integer32
			MAX-ACCESS read-only
			STATUS current
			DESCRIPTION
				"It express half duplex or full duplex mode. Only unidirectional communication is possible on half duplex mode and bi-directional communication is possible on full duplex mode to transmit packet for two ways."
			::= { sleEponProfilePortEntry 6 }

		
--  1.3.6.1.4.1.6296.101.20.5.4.1.1.7
		-- 1.3.6.1.4.1.6296.101.20.5.4.1.1.7
		sleEponProfilePortPvid OBJECT-TYPE
			SYNTAX VlanIndex
			MAX-ACCESS read-only
			STATUS current
			DESCRIPTION
				"It is PVID that configure in ONU port"
			::= { sleEponProfilePortEntry 7 }

		
--  1.3.6.1.4.1.6296.101.20.5.4.1.1.8
		-- 1.3.6.1.4.1.6296.101.20.5.4.1.1.8
		sleEponProfilePortIngressRateLimitMode OBJECT-TYPE
			SYNTAX INTEGER
				{
				all(0),
				multiBroadUnicast(1),
				multiBroadcast(2),
				broadcast(3)
				}
			MAX-ACCESS read-only
			STATUS current
			DESCRIPTION
				"It is rate limit mode in Ingress
				0  Limit all frames
				 1  Limit multicast, broadcast and flooded unicast frame
				 2  Limit multicast, broadcast frame
				 3  Limit broadcast frame only"
			::= { sleEponProfilePortEntry 8 }

		
--  1.3.6.1.4.1.6296.101.20.5.4.1.1.9
		-- 1.3.6.1.4.1.6296.101.20.5.4.1.1.9
		sleEponProfilePortIngressRateLimit OBJECT-TYPE
			SYNTAX INTEGER (0 | 62..100000)
			MAX-ACCESS read-only
			STATUS current
			DESCRIPTION
				"It is configurable port rate limit in Ingress
				The value of 0 is unlimit
				"
			DEFVAL { 0 }
			::= { sleEponProfilePortEntry 9 }

		
--  1.3.6.1.4.1.6296.101.20.5.4.1.1.10
		-- 1.3.6.1.4.1.6296.101.20.5.4.1.1.10
		sleEponProfilePortEgressRateLimit OBJECT-TYPE
			SYNTAX INTEGER (0 | 62..100000)
			MAX-ACCESS read-only
			STATUS current
			DESCRIPTION
				"It is configurable port rate limit in Egress
				The value of 0 is unlimit
				"
			DEFVAL { 0 }
			::= { sleEponProfilePortEntry 10 }

		
--  1.3.6.1.4.1.6296.101.20.5.4.1.1.11
		-- 1.3.6.1.4.1.6296.101.20.5.4.1.1.11
		sleEponProfilePortFlowControl OBJECT-TYPE
			SYNTAX INTEGER
				{
				on(1),
				off(2)
				}
			MAX-ACCESS read-only
			STATUS current
			DESCRIPTION
				"Description."
			::= { sleEponProfilePortEntry 11 }

		
--  1.3.6.1.4.1.6296.101.20.5.4.2
		-- 1.3.6.1.4.1.6296.101.20.5.4.2
		sleEponProfilePortControl OBJECT IDENTIFIER ::= { sleEponProfilePort 2 }

		
--  1.3.6.1.4.1.6296.101.20.5.4.2.1
		-- 1.3.6.1.4.1.6296.101.20.5.4.2.1
		sleEponProfilePortControlRequest OBJECT-TYPE
			SYNTAX INTEGER
				{
				setPortAdminStatus(1),
				setPortNego(2),
				setPortSpeed(3),
				setPortDuplex(4),
				setPortMaxHost(5),
				setPortPvid(6),
				setPortRateLimit(7),
				setPortFlowControl(8)
				}
			MAX-ACCESS read-write
			STATUS current
			DESCRIPTION
				"The request of a user command"
			::= { sleEponProfilePortControl 1 }

		
--  1.3.6.1.4.1.6296.101.20.5.4.2.2
		-- 1.3.6.1.4.1.6296.101.20.5.4.2.2
		sleEponProfilePortControlStatus OBJECT-TYPE
			SYNTAX SleControlStatusType
			MAX-ACCESS read-only
			STATUS current
			DESCRIPTION
				"The status of user command"
			::= { sleEponProfilePortControl 2 }

		
--  1.3.6.1.4.1.6296.101.20.5.4.2.3
		-- 1.3.6.1.4.1.6296.101.20.5.4.2.3
		sleEponProfilePortControlTimer OBJECT-TYPE
			SYNTAX Gauge32
			MAX-ACCESS read-write
			STATUS current
			DESCRIPTION
				"The maximum time for the manager for a long running user command"
			::= { sleEponProfilePortControl 3 }

		
--  1.3.6.1.4.1.6296.101.20.5.4.2.4
		-- 1.3.6.1.4.1.6296.101.20.5.4.2.4
		sleEponProfilePortControlTimeStamp OBJECT-TYPE
			SYNTAX TimeTicks
			MAX-ACCESS read-only
			STATUS current
			DESCRIPTION
				"The time stamp of the last command(end of command)"
			::= { sleEponProfilePortControl 4 }

		
--  1.3.6.1.4.1.6296.101.20.5.4.2.5
		-- 1.3.6.1.4.1.6296.101.20.5.4.2.5
		sleEponProfilePortControlReqResult OBJECT-TYPE
			SYNTAX SleControlRequestResultType
			MAX-ACCESS read-only
			STATUS current
			DESCRIPTION
				"The result of the last user command"
			::= { sleEponProfilePortControl 5 }

		
--  1.3.6.1.4.1.6296.101.20.5.4.2.6
		-- 1.3.6.1.4.1.6296.101.20.5.4.2.6
		sleEponProfilePortControlProfileIndex OBJECT-TYPE
			SYNTAX INTEGER (1..32)
			MAX-ACCESS read-write
			STATUS current
			DESCRIPTION
				"Description."
			::= { sleEponProfilePortControl 6 }

		
--  1.3.6.1.4.1.6296.101.20.5.4.2.7
		-- 1.3.6.1.4.1.6296.101.20.5.4.2.7
		sleEponProfilePortControlPortIndex OBJECT-TYPE
			SYNTAX INTEGER (1..256)
			MAX-ACCESS read-write
			STATUS current
			DESCRIPTION
				"Description."
			::= { sleEponProfilePortControl 7 }

		
--  1.3.6.1.4.1.6296.101.20.5.4.2.8
		-- 1.3.6.1.4.1.6296.101.20.5.4.2.8
		sleEponProfilePortControlAdminStatus OBJECT-TYPE
			SYNTAX INTEGER
				{
				enable(1),
				disable(2)
				}
			MAX-ACCESS read-write
			STATUS current
			DESCRIPTION
				"Description."
			DEFVAL { 0 }
			::= { sleEponProfilePortControl 8 }

		
--  1.3.6.1.4.1.6296.101.20.5.4.2.9
		-- 1.3.6.1.4.1.6296.101.20.5.4.2.9
		sleEponProfilePortControlNego OBJECT-TYPE
			SYNTAX INTEGER
				{
				on(1),
				off(2)
				}
			MAX-ACCESS read-write
			STATUS current
			DESCRIPTION
				"Description."
			DEFVAL { 1 }
			::= { sleEponProfilePortControl 9 }

		
--  1.3.6.1.4.1.6296.101.20.5.4.2.10
		-- 1.3.6.1.4.1.6296.101.20.5.4.2.10
		sleEponProfilePortControlSpeed OBJECT-TYPE
			SYNTAX INTEGER (10 | 100)
			UNITS "Mbits/sec"
			MAX-ACCESS read-write
			STATUS current
			DESCRIPTION
				"Description."
			::= { sleEponProfilePortControl 10 }

		
--  1.3.6.1.4.1.6296.101.20.5.4.2.11
		-- 1.3.6.1.4.1.6296.101.20.5.4.2.11
		sleEponProfilePortControlDuplex OBJECT-TYPE
			SYNTAX INTEGER
				{
				full(1),
				half(2)
				}
			MAX-ACCESS read-write
			STATUS current
			DESCRIPTION
				"Description."
			DEFVAL { 1 }
			::= { sleEponProfilePortControl 11 }

		
--  1.3.6.1.4.1.6296.101.20.5.4.2.12
		-- 1.3.6.1.4.1.6296.101.20.5.4.2.12
		sleEponProfilePortControlMaxHost OBJECT-TYPE
			SYNTAX Integer32
			MAX-ACCESS read-write
			STATUS current
			DESCRIPTION
				"Description."
			::= { sleEponProfilePortControl 12 }

		
--  1.3.6.1.4.1.6296.101.20.5.4.2.13
		-- 1.3.6.1.4.1.6296.101.20.5.4.2.13
		sleEponProfilePortControlPvid OBJECT-TYPE
			SYNTAX VlanIndex
			MAX-ACCESS read-write
			STATUS current
			DESCRIPTION
				"It is PVID that configure in ONU port"
			DEFVAL { '1'b }
			::= { sleEponProfilePortControl 13 }

		
--  1.3.6.1.4.1.6296.101.20.5.4.2.14
		-- 1.3.6.1.4.1.6296.101.20.5.4.2.14
		sleEponProfilePortControlIngressRateLimitMode OBJECT-TYPE
			SYNTAX INTEGER
				{
				all(0),
				multiBroadUnicast(1),
				multiBroadcast(2),
				broadcast(3)
				}
			MAX-ACCESS read-write
			STATUS current
			DESCRIPTION
				"It is rate limit mode in Ingress 
				0  Limit all frames
				  1  Limit multicast, broadcast and flooded unicast frame
				  2  Limit multicast, broadcast frame
				  3  Limit broadcast frame only"
			DEFVAL { 0 }
			::= { sleEponProfilePortControl 14 }

		
--  1.3.6.1.4.1.6296.101.20.5.4.2.15
		-- 1.3.6.1.4.1.6296.101.20.5.4.2.15
		sleEponProfilePortControlIngressRateLimit OBJECT-TYPE
			SYNTAX INTEGER (62..100000)
			MAX-ACCESS read-write
			STATUS current
			DESCRIPTION
				"It is configurable port rate limit in Ingress
				The value of 0 is unlimit
				"
			DEFVAL { 0 }
			::= { sleEponProfilePortControl 15 }

		
--  1.3.6.1.4.1.6296.101.20.5.4.2.16
		-- 1.3.6.1.4.1.6296.101.20.5.4.2.16
		sleEponProfilePortControlEgressRateLimit OBJECT-TYPE
			SYNTAX INTEGER (62..100000)
			MAX-ACCESS read-write
			STATUS current
			DESCRIPTION
				"It is configurable port rate limit in Egress
				The value of 0 is unlimit
				"
			DEFVAL { 0 }
			::= { sleEponProfilePortControl 16 }

		
--  1.3.6.1.4.1.6296.101.20.5.4.2.17
		-- 1.3.6.1.4.1.6296.101.20.5.4.2.17
		sleEponProfilePortControlFlowControl OBJECT-TYPE
			SYNTAX INTEGER
				{
				on(1),
				off(2)
				}
			MAX-ACCESS read-write
			STATUS current
			DESCRIPTION
				"Description."
			::= { sleEponProfilePortControl 17 }

		
--  1.3.6.1.4.1.6296.101.20.5.4.3
		-- 1.3.6.1.4.1.6296.101.20.5.4.3
		sleEponProfilePortNotification OBJECT IDENTIFIER ::= { sleEponProfilePort 3 }

		
--  1.3.6.1.4.1.6296.101.20.5.4.3.1
		-- 1.3.6.1.4.1.6296.101.20.5.4.3.1
		sleEponProfilePortAdminStatusChanged NOTIFICATION-TYPE
			OBJECTS { sleEponProfilePortControlRequest, sleEponProfilePortControlTimeStamp, sleEponProfilePortControlReqResult, sleEponProfilePortControlProfileIndex, sleEponProfileControlName, 
				sleEponProfilePortControlPortIndex, sleEponProfilePortControlAdminStatus }
			STATUS current
			DESCRIPTION 
				"Description."
			::= { sleEponProfilePortNotification 1 }

		
--  1.3.6.1.4.1.6296.101.20.5.4.3.2
		-- 1.3.6.1.4.1.6296.101.20.5.4.3.2
		sleEponProfilePortNegoChanged NOTIFICATION-TYPE
			OBJECTS { sleEponProfilePortControlRequest, sleEponProfilePortControlTimeStamp, sleEponProfilePortControlReqResult, sleEponProfilePortControlProfileIndex, sleEponProfilePortControlPortIndex, 
				sleEponProfilePortControlNego, sleEponProfileControlName }
			STATUS current
			DESCRIPTION 
				"Description."
			::= { sleEponProfilePortNotification 2 }

		
--  1.3.6.1.4.1.6296.101.20.5.4.3.3
		-- 1.3.6.1.4.1.6296.101.20.5.4.3.3
		sleEponProfilePortSpeedChanged NOTIFICATION-TYPE
			OBJECTS { sleEponProfilePortControlRequest, sleEponProfilePortControlTimeStamp, sleEponProfilePortControlReqResult, sleEponProfilePortControlProfileIndex, sleEponProfileControlName, 
				sleEponProfilePortControlPortIndex, sleEponProfilePortControlSpeed }
			STATUS current
			DESCRIPTION 
				"Description."
			::= { sleEponProfilePortNotification 3 }

		
--  1.3.6.1.4.1.6296.101.20.5.4.3.4
		-- 1.3.6.1.4.1.6296.101.20.5.4.3.4
		sleEponProfilePortDuplexChanged NOTIFICATION-TYPE
			OBJECTS { sleEponProfilePortControlRequest, sleEponProfilePortControlTimeStamp, sleEponProfilePortControlReqResult, sleEponProfilePortControlProfileIndex, sleEponProfileControlName, 
				sleEponProfilePortControlPortIndex, sleEponProfilePortControlDuplex }
			STATUS current
			DESCRIPTION 
				"Description."
			::= { sleEponProfilePortNotification 4 }

		
--  1.3.6.1.4.1.6296.101.20.5.4.3.5
		-- 1.3.6.1.4.1.6296.101.20.5.4.3.5
		sleEponProfilePortMaxHostChanged NOTIFICATION-TYPE
			OBJECTS { sleEponProfilePortControlRequest, sleEponProfilePortControlTimeStamp, sleEponProfilePortControlReqResult, sleEponProfilePortControlProfileIndex, sleEponProfileControlName, 
				sleEponProfilePortControlPortIndex, sleEponProfilePortControlMaxHost }
			STATUS current
			DESCRIPTION 
				"Description."
			::= { sleEponProfilePortNotification 5 }

		
--  1.3.6.1.4.1.6296.101.20.5.4.3.6
		-- 1.3.6.1.4.1.6296.101.20.5.4.3.6
		sleEponProfilePortPvidChanged NOTIFICATION-TYPE
			OBJECTS { sleEponProfilePortControlRequest, sleEponProfilePortControlTimeStamp, sleEponProfilePortControlReqResult, sleEponProfilePortControlProfileIndex, sleEponProfileControlName, 
				sleEponProfilePortControlPortIndex, sleEponProfilePortControlPvid }
			STATUS current
			DESCRIPTION 
				"Description."
			::= { sleEponProfilePortNotification 6 }

		
--  1.3.6.1.4.1.6296.101.20.5.4.3.7
		-- 1.3.6.1.4.1.6296.101.20.5.4.3.7
		sleEponProfilePortRateLimitChanged NOTIFICATION-TYPE
			OBJECTS { sleEponProfilePortControlRequest, sleEponProfilePortControlTimeStamp, sleEponProfilePortControlReqResult, sleEponProfilePortControlProfileIndex, sleEponProfileControlName, 
				sleEponProfilePortControlPortIndex, sleEponProfilePortControlIngressRateLimitMode, sleEponProfilePortControlIngressRateLimit, sleEponProfilePortControlEgressRateLimit }
			STATUS current
			DESCRIPTION 
				"Description."
			::= { sleEponProfilePortNotification 7 }

		
--  1.3.6.1.4.1.6296.101.20.5.4.3.8
		-- 1.3.6.1.4.1.6296.101.20.5.4.3.8
		sleEponProfilePortFlowControlChanged NOTIFICATION-TYPE
			OBJECTS { sleEponProfilePortControlRequest, sleEponProfilePortControlTimeStamp, sleEponProfilePortControlReqResult, sleEponProfilePortControlProfileIndex, sleEponProfileControlName, 
				sleEponProfilePortControlPortIndex, sleEponProfilePortControlFlowControl }
			STATUS current
			DESCRIPTION 
				"Description."
			::= { sleEponProfilePortNotification 8 }

		
--  1.3.6.1.4.1.6296.101.20.5.5
		-- 1.3.6.1.4.1.6296.101.20.5.5
		sleEponProfileClassification OBJECT IDENTIFIER ::= { sleEponProfile 5 }

		
--  1.3.6.1.4.1.6296.101.20.5.5.1
		-- 1.3.6.1.4.1.6296.101.20.5.5.1
		sleEponProfileClassificationTable OBJECT-TYPE
			SYNTAX SEQUENCE OF SleEponProfileClassificationEntry
			MAX-ACCESS not-accessible
			STATUS current
			DESCRIPTION
				"Description."
			::= { sleEponProfileClassification 1 }

		
--  1.3.6.1.4.1.6296.101.20.5.5.1.1
		-- 1.3.6.1.4.1.6296.101.20.5.5.1.1
		sleEponProfileClassificationEntry OBJECT-TYPE
			SYNTAX SleEponProfileClassificationEntry
			MAX-ACCESS not-accessible
			STATUS current
			DESCRIPTION
				"Description."
			INDEX { sleEponProfileIndex, sleEponProfileClassificationIndex }
			::= { sleEponProfileClassificationTable 1 }

		
		SleEponProfileClassificationEntry ::=
			SEQUENCE { 
				sleEponProfileClassificationIndex
					INTEGER,
				sleEponProfileClassificationMatchAction
					INTEGER,
				sleEponProfileClassificationQueue
					INTEGER
			 }

--  1.3.6.1.4.1.6296.101.20.5.5.1.1.1
		-- 1.3.6.1.4.1.6296.101.20.5.5.1.1.1
		sleEponProfileClassificationIndex OBJECT-TYPE
			SYNTAX INTEGER (1..256)
			MAX-ACCESS read-only
			STATUS current
			DESCRIPTION
				"Description."
			::= { sleEponProfileClassificationEntry 1 }

		
--  1.3.6.1.4.1.6296.101.20.5.5.1.1.2
		-- 1.3.6.1.4.1.6296.101.20.5.5.1.1.2
		sleEponProfileClassificationMatchAction OBJECT-TYPE
			SYNTAX INTEGER
				{
				permit(1),
				deny(2),
				notUse(3)
				}
			MAX-ACCESS read-only
			STATUS current
			DESCRIPTION
				"Description."
			::= { sleEponProfileClassificationEntry 2 }

		
--  1.3.6.1.4.1.6296.101.20.5.5.1.1.3
		-- 1.3.6.1.4.1.6296.101.20.5.5.1.1.3
		sleEponProfileClassificationQueue OBJECT-TYPE
			SYNTAX INTEGER (-1 | 0..7)
			MAX-ACCESS read-only
			STATUS current
			DESCRIPTION
				"The value of -1 is all of the queue"
			::= { sleEponProfileClassificationEntry 3 }

		
--  1.3.6.1.4.1.6296.101.20.5.5.2
		-- 1.3.6.1.4.1.6296.101.20.5.5.2
		sleEponProfileClassificationControl OBJECT IDENTIFIER ::= { sleEponProfileClassification 2 }

		
--  1.3.6.1.4.1.6296.101.20.5.5.2.1
		-- 1.3.6.1.4.1.6296.101.20.5.5.2.1
		sleEponProfileClassificationControlRequest OBJECT-TYPE
			SYNTAX INTEGER
				{
				createClassification(1),
				destroyClassification(2)
				}
			MAX-ACCESS read-write
			STATUS current
			DESCRIPTION
				"Description."
			::= { sleEponProfileClassificationControl 1 }

		
--  1.3.6.1.4.1.6296.101.20.5.5.2.2
		-- 1.3.6.1.4.1.6296.101.20.5.5.2.2
		sleEponProfileClassificationControlStatus OBJECT-TYPE
			SYNTAX SleControlStatusType
			MAX-ACCESS read-only
			STATUS current
			DESCRIPTION
				"Description."
			::= { sleEponProfileClassificationControl 2 }

		
--  1.3.6.1.4.1.6296.101.20.5.5.2.3
		-- 1.3.6.1.4.1.6296.101.20.5.5.2.3
		sleEponProfileClassificationControlTimer OBJECT-TYPE
			SYNTAX Gauge32
			MAX-ACCESS read-write
			STATUS current
			DESCRIPTION
				"Description."
			::= { sleEponProfileClassificationControl 3 }

		
--  1.3.6.1.4.1.6296.101.20.5.5.2.4
		-- 1.3.6.1.4.1.6296.101.20.5.5.2.4
		sleEponProfileClassificationControlTimeStamp OBJECT-TYPE
			SYNTAX TimeTicks
			MAX-ACCESS read-only
			STATUS current
			DESCRIPTION
				"Description."
			::= { sleEponProfileClassificationControl 4 }

		
--  1.3.6.1.4.1.6296.101.20.5.5.2.5
		-- 1.3.6.1.4.1.6296.101.20.5.5.2.5
		sleEponProfileClassificationControlReqResult OBJECT-TYPE
			SYNTAX SleControlRequestResultType
			MAX-ACCESS read-only
			STATUS current
			DESCRIPTION
				"Description."
			::= { sleEponProfileClassificationControl 5 }

		
--  1.3.6.1.4.1.6296.101.20.5.5.2.6
		-- 1.3.6.1.4.1.6296.101.20.5.5.2.6
		sleEponProfileClassificationControlProfileIndex OBJECT-TYPE
			SYNTAX INTEGER (1..32)
			MAX-ACCESS read-write
			STATUS current
			DESCRIPTION
				"Description."
			::= { sleEponProfileClassificationControl 6 }

		
--  1.3.6.1.4.1.6296.101.20.5.5.2.7
		-- 1.3.6.1.4.1.6296.101.20.5.5.2.7
		sleEponProfileClassificationControlClassificationIndex OBJECT-TYPE
			SYNTAX INTEGER (1..256)
			MAX-ACCESS read-write
			STATUS current
			DESCRIPTION
				"Description."
			::= { sleEponProfileClassificationControl 7 }

		
--  1.3.6.1.4.1.6296.101.20.5.5.2.8
		-- 1.3.6.1.4.1.6296.101.20.5.5.2.8
		sleEponProfileClassificationControlMatchAction OBJECT-TYPE
			SYNTAX INTEGER
				{
				permit(1),
				deny(2),
				notUse(3)
				}
			MAX-ACCESS read-write
			STATUS current
			DESCRIPTION
				"Description."
			::= { sleEponProfileClassificationControl 8 }

		
--  1.3.6.1.4.1.6296.101.20.5.5.2.9
		-- 1.3.6.1.4.1.6296.101.20.5.5.2.9
		sleEponProfileClassificationControlQueue OBJECT-TYPE
			SYNTAX INTEGER (-1 | 0..7)
			MAX-ACCESS read-write
			STATUS current
			DESCRIPTION
				"Description."
			::= { sleEponProfileClassificationControl 9 }

		
--  1.3.6.1.4.1.6296.101.20.5.5.3
		-- 1.3.6.1.4.1.6296.101.20.5.5.3
		sleEponProfileClassificationNotification OBJECT IDENTIFIER ::= { sleEponProfileClassification 3 }

		
--  1.3.6.1.4.1.6296.101.20.5.5.3.1
		-- 1.3.6.1.4.1.6296.101.20.5.5.3.1
		sleEponProfileClassificationCreated NOTIFICATION-TYPE
			OBJECTS { sleEponProfileClassificationControlRequest, sleEponProfileClassificationControlTimeStamp, sleEponProfileClassificationControlReqResult, sleEponProfileClassificationControlProfileIndex, sleEponProfileControlName, 
				sleEponProfileClassificationControlClassificationIndex, sleEponOnuClassificationControlName }
			STATUS current
			DESCRIPTION 
				"Description."
			::= { sleEponProfileClassificationNotification 1 }

		
--  1.3.6.1.4.1.6296.101.20.5.5.3.2
		-- 1.3.6.1.4.1.6296.101.20.5.5.3.2
		sleEponProfileClassificationDestroyed NOTIFICATION-TYPE
			OBJECTS { sleEponProfileClassificationControlRequest, sleEponProfileClassificationControlTimeStamp, sleEponProfileClassificationControlReqResult, sleEponProfileClassificationControlProfileIndex, sleEponProfileControlName, 
				sleEponProfileClassificationControlClassificationIndex, sleEponOnuClassificationControlName }
			STATUS current
			DESCRIPTION 
				"Description."
			::= { sleEponProfileClassificationNotification 2 }

		
--  1.3.6.1.4.1.6296.101.20.5.6
		-- 1.3.6.1.4.1.6296.101.20.5.6
		sleEponProfileUNIQueue OBJECT IDENTIFIER ::= { sleEponProfile 6 }

		
--  1.3.6.1.4.1.6296.101.20.5.6.1
		-- 1.3.6.1.4.1.6296.101.20.5.6.1
		sleEponProfileUNIQueueTable OBJECT-TYPE
			SYNTAX SEQUENCE OF SleEponProfileUNIQueueEntry
			MAX-ACCESS not-accessible
			STATUS current
			DESCRIPTION
				"Description."
			::= { sleEponProfileUNIQueue 1 }

		
--  1.3.6.1.4.1.6296.101.20.5.6.1.1
		-- 1.3.6.1.4.1.6296.101.20.5.6.1.1
		sleEponProfileUNIQueueEntry OBJECT-TYPE
			SYNTAX SleEponProfileUNIQueueEntry
			MAX-ACCESS not-accessible
			STATUS current
			DESCRIPTION
				"Description."
			INDEX { sleEponProfileIndex }
			::= { sleEponProfileUNIQueueTable 1 }

		
		SleEponProfileUNIQueueEntry ::=
			SEQUENCE { 
				sleEponProfileUNIQueueUpMaxBandwidth
					INTEGER,
				sleEponProfileUNIQueueUpMaxBurstSize
					INTEGER,
				sleEponProfileUNIQueueDownMaxBandwidth
					INTEGER,
				sleEponProfileUNIQueueDownMaxBurstSize
					INTEGER
			 }

--  1.3.6.1.4.1.6296.101.20.5.6.1.1.1
		-- 1.3.6.1.4.1.6296.101.20.5.6.1.1.1
		sleEponProfileUNIQueueUpMaxBandwidth OBJECT-TYPE
			SYNTAX INTEGER (100..1000000)
			UNITS "kbps"
			MAX-ACCESS read-only
			STATUS current
			DESCRIPTION
				"Description."
			::= { sleEponProfileUNIQueueEntry 1 }

		
--  1.3.6.1.4.1.6296.101.20.5.6.1.1.2
		-- 1.3.6.1.4.1.6296.101.20.5.6.1.1.2
		sleEponProfileUNIQueueUpMaxBurstSize OBJECT-TYPE
			SYNTAX INTEGER (128..16777214)
			UNITS "byte"
			MAX-ACCESS read-only
			STATUS current
			DESCRIPTION
				"Description."
			::= { sleEponProfileUNIQueueEntry 2 }

		
--  1.3.6.1.4.1.6296.101.20.5.6.1.1.3
		-- 1.3.6.1.4.1.6296.101.20.5.6.1.1.3
		sleEponProfileUNIQueueDownMaxBandwidth OBJECT-TYPE
			SYNTAX INTEGER (100..1000000)
			UNITS "kbps"
			MAX-ACCESS read-only
			STATUS current
			DESCRIPTION
				"Description."
			::= { sleEponProfileUNIQueueEntry 3 }

		
--  1.3.6.1.4.1.6296.101.20.5.6.1.1.4
		-- 1.3.6.1.4.1.6296.101.20.5.6.1.1.4
		sleEponProfileUNIQueueDownMaxBurstSize OBJECT-TYPE
			SYNTAX INTEGER (128..16777214)
			MAX-ACCESS read-only
			STATUS current
			DESCRIPTION
				"Description."
			::= { sleEponProfileUNIQueueEntry 4 }

		
--  1.3.6.1.4.1.6296.101.20.5.6.2
		-- 1.3.6.1.4.1.6296.101.20.5.6.2
		sleEponProfileUNIQueueControl OBJECT IDENTIFIER ::= { sleEponProfileUNIQueue 2 }

		
--  1.3.6.1.4.1.6296.101.20.5.6.2.1
		-- 1.3.6.1.4.1.6296.101.20.5.6.2.1
		sleEponProfileUNIQueueControlRequest OBJECT-TYPE
			SYNTAX INTEGER
				{
				modifyProfileUNIQuuePolicyUp(1),
				modifyProfileUNIQuuePolicyDown(2)
				}
			MAX-ACCESS read-write
			STATUS current
			DESCRIPTION
				"Description."
			::= { sleEponProfileUNIQueueControl 1 }

		
--  1.3.6.1.4.1.6296.101.20.5.6.2.2
		-- 1.3.6.1.4.1.6296.101.20.5.6.2.2
		sleEponProfileUNIQueueControlStatus OBJECT-TYPE
			SYNTAX SleControlStatusType
			MAX-ACCESS read-only
			STATUS current
			DESCRIPTION
				"Description."
			::= { sleEponProfileUNIQueueControl 2 }

		
--  1.3.6.1.4.1.6296.101.20.5.6.2.3
		-- 1.3.6.1.4.1.6296.101.20.5.6.2.3
		sleEponProfileUNIQueueControlTimer OBJECT-TYPE
			SYNTAX Gauge32
			MAX-ACCESS read-write
			STATUS current
			DESCRIPTION
				"Description."
			::= { sleEponProfileUNIQueueControl 3 }

		
--  1.3.6.1.4.1.6296.101.20.5.6.2.4
		-- 1.3.6.1.4.1.6296.101.20.5.6.2.4
		sleEponProfileUNIQueueControlTimeStamp OBJECT-TYPE
			SYNTAX TimeTicks
			MAX-ACCESS read-only
			STATUS current
			DESCRIPTION
				"Description."
			::= { sleEponProfileUNIQueueControl 4 }

		
--  1.3.6.1.4.1.6296.101.20.5.6.2.5
		-- 1.3.6.1.4.1.6296.101.20.5.6.2.5
		sleEponProfileUNIQueueControlReqResult OBJECT-TYPE
			SYNTAX SleControlRequestResultType
			MAX-ACCESS read-only
			STATUS current
			DESCRIPTION
				"Description."
			::= { sleEponProfileUNIQueueControl 5 }

		
--  1.3.6.1.4.1.6296.101.20.5.6.2.6
		-- 1.3.6.1.4.1.6296.101.20.5.6.2.6
		sleEponProfileUNIQueueControlProfileIndex OBJECT-TYPE
			SYNTAX INTEGER (1..32)
			MAX-ACCESS read-write
			STATUS current
			DESCRIPTION
				"Description."
			::= { sleEponProfileUNIQueueControl 6 }

		
--  1.3.6.1.4.1.6296.101.20.5.6.2.7
		-- 1.3.6.1.4.1.6296.101.20.5.6.2.7
		sleEponProfileUNIQueueControlUpMaxBandwidth OBJECT-TYPE
			SYNTAX INTEGER (0 | 100..1000000)
			UNITS "kbps"
			MAX-ACCESS read-write
			STATUS current
			DESCRIPTION
				"Description."
			::= { sleEponProfileUNIQueueControl 7 }

		
--  1.3.6.1.4.1.6296.101.20.5.6.2.8
		-- 1.3.6.1.4.1.6296.101.20.5.6.2.8
		sleEponProfileUNIQueueControlUpMaxBurstSize OBJECT-TYPE
			SYNTAX INTEGER (0 | 128..16777214)
			UNITS "byte"
			MAX-ACCESS read-write
			STATUS current
			DESCRIPTION
				"Description."
			::= { sleEponProfileUNIQueueControl 8 }

		
--  1.3.6.1.4.1.6296.101.20.5.6.2.9
		-- 1.3.6.1.4.1.6296.101.20.5.6.2.9
		sleEponProfileUNIQueueControlDownMaxBandwidth OBJECT-TYPE
			SYNTAX INTEGER (0 | 100..1000000)
			UNITS "kbps"
			MAX-ACCESS read-write
			STATUS current
			DESCRIPTION
				"Description."
			::= { sleEponProfileUNIQueueControl 9 }

		
--  1.3.6.1.4.1.6296.101.20.5.6.2.10
		-- 1.3.6.1.4.1.6296.101.20.5.6.2.10
		sleEponProfileUNIQueueControlDownMaxBurstSize OBJECT-TYPE
			SYNTAX INTEGER (0 | 128..16777214)
			UNITS "byte"
			MAX-ACCESS read-write
			STATUS current
			DESCRIPTION
				"Description."
			::= { sleEponProfileUNIQueueControl 10 }

		
--  1.3.6.1.4.1.6296.101.20.5.6.3
		-- 1.3.6.1.4.1.6296.101.20.5.6.3
		sleEponProfileUNIQueueNotification OBJECT IDENTIFIER ::= { sleEponProfileUNIQueue 3 }

		
--  1.3.6.1.4.1.6296.101.20.5.6.3.1
		-- 1.3.6.1.4.1.6296.101.20.5.6.3.1
		sleEponProfileUNIQueueModifyQueuePolicy NOTIFICATION-TYPE
			OBJECTS { sleEponProfileUNIQueueControlRequest, sleEponProfileUNIQueueControlTimeStamp, sleEponProfileUNIQueueControlReqResult, sleEponProfileUNIQueueControlProfileIndex }
			STATUS current
			DESCRIPTION 
				"Description."
			::= { sleEponProfileUNIQueueNotification 1 }

		
--  1.3.6.1.4.1.6296.101.20.6
		-- 1.3.6.1.4.1.6296.101.20.6
		sleEponAlarm OBJECT IDENTIFIER ::= { sleEpon 6 }

		
--  1.3.6.1.4.1.6296.101.20.6.1
		-- 1.3.6.1.4.1.6296.101.20.6.1
		sleEponAlarmTable OBJECT-TYPE
			SYNTAX SEQUENCE OF SleEponAlarmEntry
			MAX-ACCESS not-accessible
			STATUS current
			DESCRIPTION
				"Description."
			::= { sleEponAlarm 1 }

		
--  1.3.6.1.4.1.6296.101.20.7.1.1
		-- 1.3.6.1.4.1.6296.101.20.6.1.1
		sleEponAlarmEntry OBJECT-TYPE
			SYNTAX SleEponAlarmEntry
			MAX-ACCESS not-accessible
			STATUS current
			DESCRIPTION
				"Description."
			INDEX { sleEponOltIndex }
			::= { sleEponAlarmTable 1 }

		
		SleEponAlarmEntry ::=
			SEQUENCE { 
				sleEponAlarmBadEncryption
					EnableFlag,
				sleEponAlarmDyingGasp
					EnableFlag,
				sleEponAlarmLlidMismatch
					EnableFlag,
				sleEponAlarmOnuRegistrationError
					EnableFlag,
				sleEponAlarmTooManyOnuRegistration
					EnableFlag
			 }

--  1.3.6.1.4.1.6296.101.20.7.1.1.1
		-- 1.3.6.1.4.1.6296.101.20.6.1.1.1
		sleEponAlarmBadEncryption OBJECT-TYPE
			SYNTAX EnableFlag
			MAX-ACCESS read-only
			STATUS current
			DESCRIPTION
				"alarm type: Bad encryption"
			DEFVAL { enable }
			::= { sleEponAlarmEntry 1 }

		
--  1.3.6.1.4.1.6296.101.20.7.1.1.2
		-- 1.3.6.1.4.1.6296.101.20.6.1.1.2
		sleEponAlarmDyingGasp OBJECT-TYPE
			SYNTAX EnableFlag
			MAX-ACCESS read-only
			STATUS current
			DESCRIPTION
				"alarm type: Dying gasp"
			DEFVAL { enable }
			::= { sleEponAlarmEntry 2 }

		
--  1.3.6.1.4.1.6296.101.20.7.1.1.3
		-- 1.3.6.1.4.1.6296.101.20.6.1.1.3
		sleEponAlarmLlidMismatch OBJECT-TYPE
			SYNTAX EnableFlag
			MAX-ACCESS read-only
			STATUS current
			DESCRIPTION
				"alarm type: llid mismatch"
			DEFVAL { enable }
			::= { sleEponAlarmEntry 3 }

		
--  1.3.6.1.4.1.6296.101.20.7.1.1.4
		-- 1.3.6.1.4.1.6296.101.20.6.1.1.4
		sleEponAlarmOnuRegistrationError OBJECT-TYPE
			SYNTAX EnableFlag
			MAX-ACCESS read-only
			STATUS current
			DESCRIPTION
				"alarm type: onu registration error"
			DEFVAL { enable }
			::= { sleEponAlarmEntry 4 }

		
--  1.3.6.1.4.1.6296.101.20.7.1.1.5
		-- 1.3.6.1.4.1.6296.101.20.6.1.1.5
		sleEponAlarmTooManyOnuRegistration OBJECT-TYPE
			SYNTAX EnableFlag
			MAX-ACCESS read-only
			STATUS current
			DESCRIPTION
				"alarm type: too many onu registration"
			DEFVAL { enable }
			::= { sleEponAlarmEntry 5 }

		
--  1.3.6.1.4.1.6296.101.20.6.2
		-- 1.3.6.1.4.1.6296.101.20.6.2
		sleEponAlarmControl OBJECT IDENTIFIER ::= { sleEponAlarm 2 }

		
--  1.3.6.1.4.1.6296.101.20.6.2.1
		-- 1.3.6.1.4.1.6296.101.20.6.2.1
		sleEponAlarmControlRequest OBJECT-TYPE
			SYNTAX INTEGER { setEponAlarmProfile(1) }
			MAX-ACCESS read-write
			STATUS current
			DESCRIPTION
				"The request of a user command"
			::= { sleEponAlarmControl 1 }

		
--  1.3.6.1.4.1.6296.101.20.6.2.2
		-- 1.3.6.1.4.1.6296.101.20.6.2.2
		sleEponAlarmControlStatus OBJECT-TYPE
			SYNTAX SleControlStatusType
			MAX-ACCESS read-only
			STATUS current
			DESCRIPTION
				"The status of user command"
			::= { sleEponAlarmControl 2 }

		
--  1.3.6.1.4.1.6296.101.20.6.2.3
		-- 1.3.6.1.4.1.6296.101.20.6.2.3
		sleEponAlarmControlTimer OBJECT-TYPE
			SYNTAX Gauge32
			MAX-ACCESS read-write
			STATUS current
			DESCRIPTION
				"The maximum time for the manager for a long running user command"
			::= { sleEponAlarmControl 3 }

		
--  1.3.6.1.4.1.6296.101.20.6.2.4
		-- 1.3.6.1.4.1.6296.101.20.6.2.4
		sleEponAlarmControlTimeStamp OBJECT-TYPE
			SYNTAX TimeTicks
			MAX-ACCESS read-only
			STATUS current
			DESCRIPTION
				"The time stamp of the last command(end of command)"
			::= { sleEponAlarmControl 4 }

		
--  1.3.6.1.4.1.6296.101.20.6.2.5
		-- 1.3.6.1.4.1.6296.101.20.6.2.5
		sleEponAlarmControlReqResult OBJECT-TYPE
			SYNTAX SleControlRequestResultType
			MAX-ACCESS read-only
			STATUS current
			DESCRIPTION
				"The result of the last user command"
			::= { sleEponAlarmControl 5 }

		
--  1.3.6.1.4.1.6296.101.20.6.2.6
		-- 1.3.6.1.4.1.6296.101.20.6.2.6
		sleEponAlarmControlOltIndex OBJECT-TYPE
			SYNTAX Integer32
			MAX-ACCESS read-write
			STATUS current
			DESCRIPTION
				"OLT index"
			::= { sleEponAlarmControl 6 }

		
--  1.3.6.1.4.1.6296.101.20.6.2.7
		-- 1.3.6.1.4.1.6296.101.20.6.2.7
		sleEponAlarmControlBadEncryption OBJECT-TYPE
			SYNTAX EnableFlag
			MAX-ACCESS read-write
			STATUS current
			DESCRIPTION
				"disable(1), enable(2)"
			DEFVAL { enable }
			::= { sleEponAlarmControl 7 }

		
--  1.3.6.1.4.1.6296.101.20.6.2.8
		-- 1.3.6.1.4.1.6296.101.20.6.2.8
		sleEponAlarmControlDyingGasp OBJECT-TYPE
			SYNTAX EnableFlag
			MAX-ACCESS read-write
			STATUS current
			DESCRIPTION
				"disable(1), enable(2)"
			DEFVAL { enable }
			::= { sleEponAlarmControl 8 }

		
--  1.3.6.1.4.1.6296.101.20.6.2.9
		-- 1.3.6.1.4.1.6296.101.20.6.2.9
		sleEponAlarmControlLlidMismatch OBJECT-TYPE
			SYNTAX EnableFlag
			MAX-ACCESS read-write
			STATUS current
			DESCRIPTION
				"disable(1), enable(2)"
			DEFVAL { enable }
			::= { sleEponAlarmControl 9 }

		
--  1.3.6.1.4.1.6296.101.20.6.2.10
		-- 1.3.6.1.4.1.6296.101.20.6.2.10
		sleEponAlarmControlOnuRegistrationError OBJECT-TYPE
			SYNTAX EnableFlag
			MAX-ACCESS read-write
			STATUS current
			DESCRIPTION
				"disable(1), enable(2)"
			DEFVAL { enable }
			::= { sleEponAlarmControl 10 }

		
--  1.3.6.1.4.1.6296.101.20.6.2.11
		-- 1.3.6.1.4.1.6296.101.20.6.2.11
		sleEponAlarmControlTooManyOnuRegistration OBJECT-TYPE
			SYNTAX EnableFlag
			MAX-ACCESS read-write
			STATUS current
			DESCRIPTION
				"disable(1), enable(2)"
			DEFVAL { enable }
			::= { sleEponAlarmControl 11 }

		
--  1.3.6.1.4.1.6296.101.20.6.3
		-- 1.3.6.1.4.1.6296.101.20.6.3
		sleEponAlarmNotification OBJECT IDENTIFIER ::= { sleEponAlarm 3 }

		
--  1.3.6.1.4.1.6296.101.20.6.3.1
		-- 1.3.6.1.4.1.6296.101.20.6.3.1
		sleEponAlarmProfileChanged NOTIFICATION-TYPE
			OBJECTS { sleEponAlarmControlRequest, sleEponAlarmControlTimeStamp, sleEponAlarmControlReqResult, sleEponAlarmControlOltIndex }
			STATUS current
			DESCRIPTION 
				"Description."
			::= { sleEponAlarmNotification 1 }

		
--  1.3.6.1.4.1.6296.101.20.7
		-- 1.3.6.1.4.1.6296.101.20.7
		sleEponStatistics OBJECT IDENTIFIER ::= { sleEpon 7 }

		
--  1.3.6.1.4.1.6296.101.20.7.1
		-- 1.3.6.1.4.1.6296.101.20.7.1
		sleEponOltStatistics OBJECT IDENTIFIER ::= { sleEponStatistics 1 }

		
--  1.3.6.1.4.1.6296.101.20.7.1.1
		-- 1.3.6.1.4.1.6296.101.20.7.1.1
		sleEponStatsOltTable OBJECT-TYPE
			SYNTAX SEQUENCE OF SleEponStatsOltEntry
			MAX-ACCESS not-accessible
			STATUS current
			DESCRIPTION
				"Description."
			::= { sleEponOltStatistics 1 }

		
--  1.3.6.1.4.1.6296.101.20.8.1.1.1
		-- 1.3.6.1.4.1.6296.101.20.7.1.1.1
		sleEponStatsOltEntry OBJECT-TYPE
			SYNTAX SleEponStatsOltEntry
			MAX-ACCESS not-accessible
			STATUS current
			DESCRIPTION
				"Description."
			INDEX { sleEponOltIndex }
			::= { sleEponStatsOltTable 1 }

		
		SleEponStatsOltEntry ::=
			SEQUENCE { 
				sleEponStatsOltInOctets
					Counter64,
				sleEponStatsOltInPkts
					Counter32,
				sleEponStatsOltInPause
					Counter32,
				sleEponStatsOltInErroredFrame
					Counter32,
				sleEponStatsOltInUnicastPkts
					Counter32,
				sleEponstatsOltInBroadcastPkts
					Counter32,
				sleEponStatsOltInMulticastPkts
					Counter32,
				sleEponStatsOltOutOctets
					Counter64,
				sleEponStatsOltOutPkts
					Counter32,
				sleEponStatsOltOutPause
					Counter32,
				sleEponStatsOltOutDropped
					Counter32,
				sleEponStatsOltOutUnicastPkts
					Counter32,
				sleEponstatsOltOutBroadcastPkts
					Counter32,
				sleEponStatsOltOutMulticastPkts
					Counter32
			 }

--  1.3.6.1.4.1.6296.101.20.8.1.1.1.1
		-- 1.3.6.1.4.1.6296.101.20.7.1.1.1.1
		sleEponStatsOltInOctets OBJECT-TYPE
			SYNTAX Counter64
			MAX-ACCESS read-only
			STATUS current
			DESCRIPTION
				"The total number of octets received on the switch side"
			::= { sleEponStatsOltEntry 1 }

		
--  1.3.6.1.4.1.6296.101.20.8.1.1.1.2
		-- 1.3.6.1.4.1.6296.101.20.7.1.1.1.2
		sleEponStatsOltInPkts OBJECT-TYPE
			SYNTAX Counter32
			MAX-ACCESS read-only
			STATUS current
			DESCRIPTION
				"The total number of packets received on the switch side"
			::= { sleEponStatsOltEntry 2 }

		
--  1.3.6.1.4.1.6296.101.20.8.1.1.1.3
		-- 1.3.6.1.4.1.6296.101.20.7.1.1.1.3
		sleEponStatsOltInPause OBJECT-TYPE
			SYNTAX Counter32
			MAX-ACCESS read-only
			STATUS current
			DESCRIPTION
				"The total number of paused packet received on the switch side"
			::= { sleEponStatsOltEntry 3 }

		
--  1.3.6.1.4.1.6296.101.20.8.1.1.1.4
		-- 1.3.6.1.4.1.6296.101.20.7.1.1.1.4
		sleEponStatsOltInErroredFrame OBJECT-TYPE
			SYNTAX Counter32
			MAX-ACCESS read-only
			STATUS current
			DESCRIPTION
				"The total number of errored frame received on the switch side"
			::= { sleEponStatsOltEntry 4 }

		
--  1.3.6.1.4.1.6296.101.20.8.1.1.1.5
		-- 1.3.6.1.4.1.6296.101.20.7.1.1.1.5
		sleEponStatsOltInUnicastPkts OBJECT-TYPE
			SYNTAX Counter32
			MAX-ACCESS read-only
			STATUS current
			DESCRIPTION
				"The total number of unicast packets received on the switch side"
			::= { sleEponStatsOltEntry 5 }

		
--  1.3.6.1.4.1.6296.101.20.8.1.1.1.6
		-- 1.3.6.1.4.1.6296.101.20.7.1.1.1.6
		sleEponstatsOltInBroadcastPkts OBJECT-TYPE
			SYNTAX Counter32
			MAX-ACCESS read-only
			STATUS current
			DESCRIPTION
				"The total number of broadcast packets received on the switch side"
			::= { sleEponStatsOltEntry 6 }

		
--  1.3.6.1.4.1.6296.101.20.8.1.1.1.7
		-- 1.3.6.1.4.1.6296.101.20.7.1.1.1.7
		sleEponStatsOltInMulticastPkts OBJECT-TYPE
			SYNTAX Counter32
			MAX-ACCESS read-only
			STATUS current
			DESCRIPTION
				"The total number of multicast packets received on the switch side"
			::= { sleEponStatsOltEntry 7 }

		
--  1.3.6.1.4.1.6296.101.20.8.1.1.1.8
		-- 1.3.6.1.4.1.6296.101.20.7.1.1.1.8
		sleEponStatsOltOutOctets OBJECT-TYPE
			SYNTAX Counter64
			MAX-ACCESS read-only
			STATUS current
			DESCRIPTION
				"The total number of octets transmitted out of the switch side"
			::= { sleEponStatsOltEntry 8 }

		
--  1.3.6.1.4.1.6296.101.20.8.1.1.1.9
		-- 1.3.6.1.4.1.6296.101.20.7.1.1.1.9
		sleEponStatsOltOutPkts OBJECT-TYPE
			SYNTAX Counter32
			MAX-ACCESS read-only
			STATUS current
			DESCRIPTION
				"The total number of packets transmitted out of the switch side"
			::= { sleEponStatsOltEntry 9 }

		
--  1.3.6.1.4.1.6296.101.20.8.1.1.1.10
		-- 1.3.6.1.4.1.6296.101.20.7.1.1.1.10
		sleEponStatsOltOutPause OBJECT-TYPE
			SYNTAX Counter32
			MAX-ACCESS read-only
			STATUS current
			DESCRIPTION
				"The total number of paused packets transmitted out of the switch side"
			::= { sleEponStatsOltEntry 10 }

		
--  1.3.6.1.4.1.6296.101.20.8.1.1.1.11
		-- 1.3.6.1.4.1.6296.101.20.7.1.1.1.11
		sleEponStatsOltOutDropped OBJECT-TYPE
			SYNTAX Counter32
			MAX-ACCESS read-only
			STATUS current
			DESCRIPTION
				"The total number of droped packets transmitted out of the switch side"
			::= { sleEponStatsOltEntry 11 }

		
--  1.3.6.1.4.1.6296.101.20.8.1.1.1.12
		-- 1.3.6.1.4.1.6296.101.20.7.1.1.1.12
		sleEponStatsOltOutUnicastPkts OBJECT-TYPE
			SYNTAX Counter32
			MAX-ACCESS read-only
			STATUS current
			DESCRIPTION
				"The total number of unicast packets transmitted out of the switch side"
			::= { sleEponStatsOltEntry 12 }

		
--  1.3.6.1.4.1.6296.101.20.8.1.1.1.13
		-- 1.3.6.1.4.1.6296.101.20.7.1.1.1.13
		sleEponstatsOltOutBroadcastPkts OBJECT-TYPE
			SYNTAX Counter32
			MAX-ACCESS read-only
			STATUS current
			DESCRIPTION
				"The total number of broadcast packets transmitted out of the switch side"
			::= { sleEponStatsOltEntry 13 }

		
--  1.3.6.1.4.1.6296.101.20.8.1.1.1.14
		-- 1.3.6.1.4.1.6296.101.20.7.1.1.1.14
		sleEponStatsOltOutMulticastPkts OBJECT-TYPE
			SYNTAX Counter32
			MAX-ACCESS read-only
			STATUS current
			DESCRIPTION
				"The total number of multicast packets transmitted out of the switch side"
			::= { sleEponStatsOltEntry 14 }

		
--  1.3.6.1.4.1.6296.101.20.7.1.2
		-- 1.3.6.1.4.1.6296.101.20.7.1.2
		sleEponStatsOltPonTable OBJECT-TYPE
			SYNTAX SEQUENCE OF SleEponStatsOltPonEntry
			MAX-ACCESS not-accessible
			STATUS current
			DESCRIPTION
				"Description."
			::= { sleEponOltStatistics 2 }

		
--  1.3.6.1.4.1.6296.101.20.8.1.2.1
		-- 1.3.6.1.4.1.6296.101.20.7.1.2.1
		sleEponStatsOltPonEntry OBJECT-TYPE
			SYNTAX SleEponStatsOltPonEntry
			MAX-ACCESS not-accessible
			STATUS current
			DESCRIPTION
				"Description."
			INDEX { sleEponOltIndex }
			::= { sleEponStatsOltPonTable 1 }

		
		SleEponStatsOltPonEntry ::=
			SEQUENCE { 
				sleEponStatsOltPonInOctets
					Counter64,
				sleEponStatsOltPonInPkts
					Counter32,
				sleEponStatsOltPonInPause
					Counter32,
				sleEponStatsOltPonInErroredFrame
					Counter32,
				sleEponStatsOltPonInUnicastPkts
					Counter32,
				sleEponstatsOltPonInBroadcastPkts
					Counter32,
				sleEponStatsOltPonInMulticastPkts
					Counter32,
				sleEponStatsOltPonOutOctets
					Counter64,
				sleEponStatsOltPonOutPkts
					Counter32,
				sleEponStatsOltPonOutPause
					Counter32,
				sleEponStatsOltPonOutDropped
					Counter32,
				sleEponStatsOltPonOutUnicastPkts
					Counter32,
				sleEponstatsOltPonOutBroadcastPkts
					Counter32,
				sleEponStatsOltPonOutMulticastPkts
					Counter32
			 }

--  1.3.6.1.4.1.6296.101.20.8.1.2.1.1
		-- 1.3.6.1.4.1.6296.101.20.7.1.2.1.1
		sleEponStatsOltPonInOctets OBJECT-TYPE
			SYNTAX Counter64
			MAX-ACCESS read-only
			STATUS current
			DESCRIPTION
				"The total number of octets received on the OLT side"
			::= { sleEponStatsOltPonEntry 1 }

		
--  1.3.6.1.4.1.6296.101.20.8.1.2.1.2
		-- 1.3.6.1.4.1.6296.101.20.7.1.2.1.2
		sleEponStatsOltPonInPkts OBJECT-TYPE
			SYNTAX Counter32
			MAX-ACCESS read-only
			STATUS current
			DESCRIPTION
				"The total number of packets received on the OLT side"
			::= { sleEponStatsOltPonEntry 2 }

		
--  1.3.6.1.4.1.6296.101.20.8.1.2.1.3
		-- 1.3.6.1.4.1.6296.101.20.7.1.2.1.3
		sleEponStatsOltPonInPause OBJECT-TYPE
			SYNTAX Counter32
			MAX-ACCESS read-only
			STATUS current
			DESCRIPTION
				"The total number of paused packet received on the OLT side"
			::= { sleEponStatsOltPonEntry 3 }

		
--  1.3.6.1.4.1.6296.101.20.8.1.2.1.4
		-- 1.3.6.1.4.1.6296.101.20.7.1.2.1.4
		sleEponStatsOltPonInErroredFrame OBJECT-TYPE
			SYNTAX Counter32
			MAX-ACCESS read-only
			STATUS current
			DESCRIPTION
				"The total number of errored frame received on the OLT side"
			::= { sleEponStatsOltPonEntry 4 }

		
--  1.3.6.1.4.1.6296.101.20.8.1.2.1.5
		-- 1.3.6.1.4.1.6296.101.20.7.1.2.1.5
		sleEponStatsOltPonInUnicastPkts OBJECT-TYPE
			SYNTAX Counter32
			MAX-ACCESS read-only
			STATUS current
			DESCRIPTION
				"The total number of unicast packets received on the OLT side"
			::= { sleEponStatsOltPonEntry 5 }

		
--  1.3.6.1.4.1.6296.101.20.8.1.2.1.6
		-- 1.3.6.1.4.1.6296.101.20.7.1.2.1.6
		sleEponstatsOltPonInBroadcastPkts OBJECT-TYPE
			SYNTAX Counter32
			MAX-ACCESS read-only
			STATUS current
			DESCRIPTION
				"The total number of broadcast packets received on the OLT side"
			::= { sleEponStatsOltPonEntry 6 }

		
--  1.3.6.1.4.1.6296.101.20.8.1.2.1.7
		-- 1.3.6.1.4.1.6296.101.20.7.1.2.1.7
		sleEponStatsOltPonInMulticastPkts OBJECT-TYPE
			SYNTAX Counter32
			MAX-ACCESS read-only
			STATUS current
			DESCRIPTION
				"The total number of multicast packets received on the OLT side"
			::= { sleEponStatsOltPonEntry 7 }

		
--  1.3.6.1.4.1.6296.101.20.8.1.2.1.8
		-- 1.3.6.1.4.1.6296.101.20.7.1.2.1.8
		sleEponStatsOltPonOutOctets OBJECT-TYPE
			SYNTAX Counter64
			MAX-ACCESS read-only
			STATUS current
			DESCRIPTION
				"The total number of octets transmitted out of the OLT side"
			::= { sleEponStatsOltPonEntry 8 }

		
--  1.3.6.1.4.1.6296.101.20.8.1.2.1.9
		-- 1.3.6.1.4.1.6296.101.20.7.1.2.1.9
		sleEponStatsOltPonOutPkts OBJECT-TYPE
			SYNTAX Counter32
			MAX-ACCESS read-only
			STATUS current
			DESCRIPTION
				"The total number of packets transmitted out of the OLT side"
			::= { sleEponStatsOltPonEntry 9 }

		
--  1.3.6.1.4.1.6296.101.20.8.1.2.1.10
		-- 1.3.6.1.4.1.6296.101.20.7.1.2.1.10
		sleEponStatsOltPonOutPause OBJECT-TYPE
			SYNTAX Counter32
			MAX-ACCESS read-only
			STATUS current
			DESCRIPTION
				"The total number of paused packets transmitted out of the OLT side"
			::= { sleEponStatsOltPonEntry 10 }

		
--  1.3.6.1.4.1.6296.101.20.8.1.2.1.11
		-- 1.3.6.1.4.1.6296.101.20.7.1.2.1.11
		sleEponStatsOltPonOutDropped OBJECT-TYPE
			SYNTAX Counter32
			MAX-ACCESS read-only
			STATUS current
			DESCRIPTION
				"The total number of droped packets transmitted out of the OLT side"
			::= { sleEponStatsOltPonEntry 11 }

		
--  1.3.6.1.4.1.6296.101.20.8.1.2.1.12
		-- 1.3.6.1.4.1.6296.101.20.7.1.2.1.12
		sleEponStatsOltPonOutUnicastPkts OBJECT-TYPE
			SYNTAX Counter32
			MAX-ACCESS read-only
			STATUS current
			DESCRIPTION
				"The total number of unicast packets transmitted out of the OLT side"
			::= { sleEponStatsOltPonEntry 12 }

		
--  1.3.6.1.4.1.6296.101.20.8.1.2.1.13
		-- 1.3.6.1.4.1.6296.101.20.7.1.2.1.13
		sleEponstatsOltPonOutBroadcastPkts OBJECT-TYPE
			SYNTAX Counter32
			MAX-ACCESS read-only
			STATUS current
			DESCRIPTION
				"The total number of broadcast packets transmitted out of the OLT side"
			::= { sleEponStatsOltPonEntry 13 }

		
--  1.3.6.1.4.1.6296.101.20.8.1.2.1.14
		-- 1.3.6.1.4.1.6296.101.20.7.1.2.1.14
		sleEponStatsOltPonOutMulticastPkts OBJECT-TYPE
			SYNTAX Counter32
			MAX-ACCESS read-only
			STATUS current
			DESCRIPTION
				"The total number of multicast packets transmitted out of the OLT side"
			::= { sleEponStatsOltPonEntry 14 }

		
--  1.3.6.1.4.1.6296.101.20.7.1.3
		-- 1.3.6.1.4.1.6296.101.20.7.1.3
		sleEponStatsOltChannelTable OBJECT-TYPE
			SYNTAX SEQUENCE OF SleEponStatsOltChannelEntry
			MAX-ACCESS not-accessible
			STATUS current
			DESCRIPTION
				"Description."
			::= { sleEponOltStatistics 3 }

		
--  1.3.6.1.4.1.6296.101.20.8.1.3.1
		-- 1.3.6.1.4.1.6296.101.20.7.1.3.1
		sleEponStatsOltChannelEntry OBJECT-TYPE
			SYNTAX SleEponStatsOltChannelEntry
			MAX-ACCESS not-accessible
			STATUS current
			DESCRIPTION
				"Description."
			INDEX { sleEponOltIndex, sleEponOnuIndex }
			::= { sleEponStatsOltChannelTable 1 }

		
		SleEponStatsOltChannelEntry ::=
			SEQUENCE { 
				sleEponStatsOltChannelInOctets
					Counter64,
				sleEponStatsOltChannelInDataOctets
					Counter64,
				sleEponStatsOltChannelInPkts
					Counter32,
				sleEponStatsOltChannelInMulticastPkts
					Counter32,
				sleEponStatsOltChannelInBroadcastPkts
					Counter32,
				sleEponStatsOltChannelInErrorOctets
					Counter32,
				sleEponStatsOltChannelInErrorPkts
					Counter32,
				sleEponStatsOltChannelOutOctets
					Counter64,
				sleEponStatsOltChannelOutPkts
					Counter32,
				sleEponStatsOltChannelOutPolicerDroppedPkts
					Counter32,
				sleEponStatsOltChannelOutMismatchDroppedPkts
					Counter32,
				sleEponStatsOltChannelOutMulticastPkts
					Counter32,
				sleEponStatsOltChannelOutBroadcastPkts
					Counter32,
				sleEponStatsOltChannelFCS
					Counter32,
				sleEponStatsOltChannelInRangeLengthErrors
					Counter32,
				sleEponStatsOltChannelFrameTooLongErrors
					Counter32,
				sleEponStatsOltChannelInUnicastPkts
					Counter32,
				sleEponStatsOltChannelOutUnicastPkts
					Counter32
			 }

--  1.3.6.1.4.1.6296.101.20.8.1.3.1.1
		-- 1.3.6.1.4.1.6296.101.20.7.1.3.1.1
		sleEponStatsOltChannelInOctets OBJECT-TYPE
			SYNTAX Counter64
			MAX-ACCESS read-only
			STATUS current
			DESCRIPTION
				"The total number of octets received on the ONU side"
			::= { sleEponStatsOltChannelEntry 1 }

		
--  1.3.6.1.4.1.6296.101.20.8.1.3.1.2
		-- 1.3.6.1.4.1.6296.101.20.7.1.3.1.2
		sleEponStatsOltChannelInDataOctets OBJECT-TYPE
			SYNTAX Counter64
			MAX-ACCESS read-only
			STATUS current
			DESCRIPTION
				"The total number of  data octets received on the ONU side"
			::= { sleEponStatsOltChannelEntry 2 }

		
--  1.3.6.1.4.1.6296.101.20.8.1.3.1.3
		-- 1.3.6.1.4.1.6296.101.20.7.1.3.1.3
		sleEponStatsOltChannelInPkts OBJECT-TYPE
			SYNTAX Counter32
			MAX-ACCESS read-only
			STATUS current
			DESCRIPTION
				"The total number of packets transmitted out of the ONU side"
			::= { sleEponStatsOltChannelEntry 3 }

		
--  1.3.6.1.4.1.6296.101.20.8.1.3.1.4
		-- 1.3.6.1.4.1.6296.101.20.7.1.3.1.4
		sleEponStatsOltChannelInMulticastPkts OBJECT-TYPE
			SYNTAX Counter32
			MAX-ACCESS read-only
			STATUS current
			DESCRIPTION
				"The total number of multicast packets received on the ONU side"
			::= { sleEponStatsOltChannelEntry 4 }

		
--  1.3.6.1.4.1.6296.101.20.8.1.3.1.5
		-- 1.3.6.1.4.1.6296.101.20.7.1.3.1.5
		sleEponStatsOltChannelInBroadcastPkts OBJECT-TYPE
			SYNTAX Counter32
			MAX-ACCESS read-only
			STATUS current
			DESCRIPTION
				"The total number of broadcast packets received on the ONU side"
			::= { sleEponStatsOltChannelEntry 5 }

		
--  1.3.6.1.4.1.6296.101.20.8.1.3.1.6
		-- 1.3.6.1.4.1.6296.101.20.7.1.3.1.6
		sleEponStatsOltChannelInErrorOctets OBJECT-TYPE
			SYNTAX Counter32
			MAX-ACCESS read-only
			STATUS current
			DESCRIPTION
				"The total number of errored octets received on the ONU side"
			::= { sleEponStatsOltChannelEntry 6 }

		
--  1.3.6.1.4.1.6296.101.20.8.1.3.1.7
		-- 1.3.6.1.4.1.6296.101.20.7.1.3.1.7
		sleEponStatsOltChannelInErrorPkts OBJECT-TYPE
			SYNTAX Counter32
			MAX-ACCESS read-only
			STATUS current
			DESCRIPTION
				"The total number of errored packets received on the ONU side"
			::= { sleEponStatsOltChannelEntry 7 }

		
--  1.3.6.1.4.1.6296.101.20.8.1.3.1.8
		-- 1.3.6.1.4.1.6296.101.20.7.1.3.1.8
		sleEponStatsOltChannelOutOctets OBJECT-TYPE
			SYNTAX Counter64
			MAX-ACCESS read-only
			STATUS current
			DESCRIPTION
				"The total number of octets transmitted out of the ONU side"
			::= { sleEponStatsOltChannelEntry 8 }

		
--  1.3.6.1.4.1.6296.101.20.8.1.3.1.9
		-- 1.3.6.1.4.1.6296.101.20.7.1.3.1.9
		sleEponStatsOltChannelOutPkts OBJECT-TYPE
			SYNTAX Counter32
			MAX-ACCESS read-only
			STATUS current
			DESCRIPTION
				"The total number of packets transmitted out of the ONU side"
			::= { sleEponStatsOltChannelEntry 9 }

		
--  1.3.6.1.4.1.6296.101.20.8.1.3.1.10
		-- 1.3.6.1.4.1.6296.101.20.7.1.3.1.10
		sleEponStatsOltChannelOutPolicerDroppedPkts OBJECT-TYPE
			SYNTAX Counter32
			MAX-ACCESS read-only
			STATUS current
			DESCRIPTION
				"The total number of policer dropped transmitted out of the ONU side"
			::= { sleEponStatsOltChannelEntry 10 }

		
--  1.3.6.1.4.1.6296.101.20.8.1.3.1.11
		-- 1.3.6.1.4.1.6296.101.20.7.1.3.1.11
		sleEponStatsOltChannelOutMismatchDroppedPkts OBJECT-TYPE
			SYNTAX Counter32
			MAX-ACCESS read-only
			STATUS current
			DESCRIPTION
				"The total number of mismatch dropped packets transmitted out of the ONU side"
			::= { sleEponStatsOltChannelEntry 11 }

		
--  1.3.6.1.4.1.6296.101.20.8.1.3.1.12
		-- 1.3.6.1.4.1.6296.101.20.7.1.3.1.12
		sleEponStatsOltChannelOutMulticastPkts OBJECT-TYPE
			SYNTAX Counter32
			MAX-ACCESS read-only
			STATUS current
			DESCRIPTION
				"The total number of multicast packets transmitted out of the ONU side"
			::= { sleEponStatsOltChannelEntry 12 }

		
--  1.3.6.1.4.1.6296.101.20.8.1.3.1.13
		-- 1.3.6.1.4.1.6296.101.20.7.1.3.1.13
		sleEponStatsOltChannelOutBroadcastPkts OBJECT-TYPE
			SYNTAX Counter32
			MAX-ACCESS read-only
			STATUS current
			DESCRIPTION
				"The total number of broadcast packets transmitted out of the ONU side"
			::= { sleEponStatsOltChannelEntry 13 }

		
--  1.3.6.1.4.1.6296.101.20.8.1.3.1.14
		-- 1.3.6.1.4.1.6296.101.20.7.1.3.1.14
		sleEponStatsOltChannelFCS OBJECT-TYPE
			SYNTAX Counter32
			MAX-ACCESS read-only
			STATUS current
			DESCRIPTION
				"The total number of FCS transmitted out of the ONU side"
			::= { sleEponStatsOltChannelEntry 14 }

		
--  1.3.6.1.4.1.6296.101.20.8.1.3.1.15
		-- 1.3.6.1.4.1.6296.101.20.7.1.3.1.15
		sleEponStatsOltChannelInRangeLengthErrors OBJECT-TYPE
			SYNTAX Counter32
			MAX-ACCESS read-only
			STATUS current
			DESCRIPTION
				"The total number of range length errors received on th ONU side"
			::= { sleEponStatsOltChannelEntry 15 }

		
--  1.3.6.1.4.1.6296.101.20.8.1.3.1.16
		-- 1.3.6.1.4.1.6296.101.20.7.1.3.1.16
		sleEponStatsOltChannelFrameTooLongErrors OBJECT-TYPE
			SYNTAX Counter32
			MAX-ACCESS read-only
			STATUS current
			DESCRIPTION
				"The total number of frame to long errors on the ONU side"
			::= { sleEponStatsOltChannelEntry 16 }

		
--  1.3.6.1.4.1.6296.101.20.8.1.3.1.17
		-- 1.3.6.1.4.1.6296.101.20.7.1.3.1.17
		sleEponStatsOltChannelInUnicastPkts OBJECT-TYPE
			SYNTAX Counter32
			MAX-ACCESS read-only
			STATUS current
			DESCRIPTION
				"The total number of unicast packets received on the ONU side"
			::= { sleEponStatsOltChannelEntry 17 }

		
--  1.3.6.1.4.1.6296.101.20.8.1.3.1.18
		-- 1.3.6.1.4.1.6296.101.20.7.1.3.1.18
		sleEponStatsOltChannelOutUnicastPkts OBJECT-TYPE
			SYNTAX Counter32
			MAX-ACCESS read-only
			STATUS current
			DESCRIPTION
				"The total number of unicast packets transmitted out of the ONU side"
			::= { sleEponStatsOltChannelEntry 18 }

		
--  1.3.6.1.4.1.6296.101.20.7.1.4
		-- 1.3.6.1.4.1.6296.101.20.7.1.4
		sleEponStatsOltControl OBJECT IDENTIFIER ::= { sleEponOltStatistics 4 }

		
--  1.3.6.1.4.1.6296.101.20.7.1.4.1
		-- 1.3.6.1.4.1.6296.101.20.7.1.4.1
		sleEponStatsOltControlRequest OBJECT-TYPE
			SYNTAX INTEGER
				{
				clearEponStatsOlt(1),
				clearEponStatsOltChannel(2),
				clearEponStatsAll(3)
				}
			MAX-ACCESS read-write
			STATUS current
			DESCRIPTION
				"The request of a user command"
			::= { sleEponStatsOltControl 1 }

		
--  1.3.6.1.4.1.6296.101.20.7.1.4.2
		-- 1.3.6.1.4.1.6296.101.20.7.1.4.2
		sleEponStatsOltControlStatus OBJECT-TYPE
			SYNTAX SleControlStatusType
			MAX-ACCESS read-only
			STATUS current
			DESCRIPTION
				"The status of user command"
			::= { sleEponStatsOltControl 2 }

		
--  1.3.6.1.4.1.6296.101.20.7.1.4.3
		-- 1.3.6.1.4.1.6296.101.20.7.1.4.3
		sleEponStatsOltControlTimer OBJECT-TYPE
			SYNTAX Gauge32
			MAX-ACCESS read-write
			STATUS current
			DESCRIPTION
				"The maximum time for the manager for a long running user command"
			::= { sleEponStatsOltControl 3 }

		
--  1.3.6.1.4.1.6296.101.20.7.1.4.4
		-- 1.3.6.1.4.1.6296.101.20.7.1.4.4
		sleEponStatsOltControlTimeStamp OBJECT-TYPE
			SYNTAX TimeTicks
			MAX-ACCESS read-only
			STATUS current
			DESCRIPTION
				"The time stamp of the last command(end of command)"
			::= { sleEponStatsOltControl 4 }

		
--  1.3.6.1.4.1.6296.101.20.7.1.4.5
		-- 1.3.6.1.4.1.6296.101.20.7.1.4.5
		sleEponStatsOltControlReqResult OBJECT-TYPE
			SYNTAX SleControlRequestResultType
			MAX-ACCESS read-only
			STATUS current
			DESCRIPTION
				"The result of the last user command"
			::= { sleEponStatsOltControl 5 }

		
--  1.3.6.1.4.1.6296.101.20.7.1.4.6
		-- 1.3.6.1.4.1.6296.101.20.7.1.4.6
		sleEponStatsOltControlOltIndex OBJECT-TYPE
			SYNTAX INTEGER (1..512)
			MAX-ACCESS read-write
			STATUS current
			DESCRIPTION
				"OLT index"
			::= { sleEponStatsOltControl 6 }

		
--  1.3.6.1.4.1.6296.101.20.7.1.4.7
		-- 1.3.6.1.4.1.6296.101.20.7.1.4.7
		sleEponStatsOltControlChannelIndex OBJECT-TYPE
			SYNTAX INTEGER (1..32)
			MAX-ACCESS read-write
			STATUS current
			DESCRIPTION
				"ONU index"
			::= { sleEponStatsOltControl 7 }

		
--  1.3.6.1.4.1.6296.101.20.7.1.5
		-- 1.3.6.1.4.1.6296.101.20.7.1.5
		sleEponStatsOltNotification OBJECT IDENTIFIER ::= { sleEponOltStatistics 5 }

		
--  1.3.6.1.4.1.6296.101.20.7.1.5.1
		-- 1.3.6.1.4.1.6296.101.20.7.1.5.1
		sleEponstatsOltCleared NOTIFICATION-TYPE
			OBJECTS { sleEponStatsOltControlRequest, sleEponStatsOltControlTimeStamp, sleEponStatsOltControlReqResult, sleEponStatsOltControlOltIndex }
			STATUS current
			DESCRIPTION 
				"Description."
			::= { sleEponStatsOltNotification 1 }

		
--  1.3.6.1.4.1.6296.101.20.7.1.5.2
		-- 1.3.6.1.4.1.6296.101.20.7.1.5.2
		sleEponStatsOltChannelCleared NOTIFICATION-TYPE
			OBJECTS { sleEponStatsOltControlRequest, sleEponStatsOltControlTimeStamp, sleEponStatsOltControlReqResult, sleEponStatsOltControlOltIndex, sleEponStatsOltControlChannelIndex
				 }
			STATUS current
			DESCRIPTION 
				"Description."
			::= { sleEponStatsOltNotification 2 }

		
--  1.3.6.1.4.1.6296.101.20.7.1.5.3
		-- 1.3.6.1.4.1.6296.101.20.7.1.5.3
		sleEponStatsAllCleared NOTIFICATION-TYPE
			OBJECTS { sleEponStatsOltControlRequest, sleEponStatsOltControlTimeStamp, sleEponStatsOltControlReqResult, sleEponStatsOltControlOltIndex, sleEponStatsOltControlChannelIndex
				 }
			STATUS current
			DESCRIPTION 
				"Description."
			::= { sleEponStatsOltNotification 3 }

		
--  1.3.6.1.4.1.6296.101.20.7.2
		-- 1.3.6.1.4.1.6296.101.20.7.2
		sleEponOnuStatistics OBJECT IDENTIFIER ::= { sleEponStatistics 2 }

		
--  1.3.6.1.4.1.6296.101.20.7.2.1
		-- 1.3.6.1.4.1.6296.101.20.7.2.1
		sleEponStatsOnuPortTable OBJECT-TYPE
			SYNTAX SEQUENCE OF SleEponStatsOnuPortEntry
			MAX-ACCESS not-accessible
			STATUS current
			DESCRIPTION
				"Description."
			::= { sleEponOnuStatistics 1 }

		
--  1.3.6.1.4.1.6296.101.20.7.2.1.1
		-- 1.3.6.1.4.1.6296.101.20.7.2.1.1
		sleEponStatsOnuPortEntry OBJECT-TYPE
			SYNTAX SleEponStatsOnuPortEntry
			MAX-ACCESS not-accessible
			STATUS current
			DESCRIPTION
				"Description."
			INDEX { sleEponOltIndex, sleEponOnuIndex, sleEponOnuPortIndex }
			::= { sleEponStatsOnuPortTable 1 }

		
		SleEponStatsOnuPortEntry ::=
			SEQUENCE { 
				sleEponStatsOnuPortInOctets
					Counter64,
				sleEponStatsOnuPortInPkts
					Counter32,
				sleEponStatsOnuPortInUcastPkts
					Counter32,
				sleEponStatsOnuPortInBcastPkts
					Counter32,
				sleEponStatsOnuPortInMcastPkts
					Counter32,
				sleEponStatsOnuPortOutOctets
					Counter64,
				sleEponStatsOnuPortOutPkts
					Counter32,
				sleEponStatsOnuPortOutUcastPkts
					Counter32,
				sleEponStatsOnuPortOutBcastPkts
					Counter32,
				sleEponStatsOnuPortOutMcastPkts
					Counter32
			 }

--  1.3.6.1.4.1.6296.101.20.7.2.1.1.1
		-- 1.3.6.1.4.1.6296.101.20.7.2.1.1.1
		sleEponStatsOnuPortInOctets OBJECT-TYPE
			SYNTAX Counter64
			MAX-ACCESS read-only
			STATUS current
			DESCRIPTION
				"Description."
			::= { sleEponStatsOnuPortEntry 1 }

		
--  1.3.6.1.4.1.6296.101.20.7.2.1.1.2
		-- 1.3.6.1.4.1.6296.101.20.7.2.1.1.2
		sleEponStatsOnuPortInPkts OBJECT-TYPE
			SYNTAX Counter32
			MAX-ACCESS read-only
			STATUS current
			DESCRIPTION
				"Description."
			::= { sleEponStatsOnuPortEntry 2 }

		
--  1.3.6.1.4.1.6296.101.20.7.2.1.1.3
		-- 1.3.6.1.4.1.6296.101.20.7.2.1.1.3
		sleEponStatsOnuPortInUcastPkts OBJECT-TYPE
			SYNTAX Counter32
			MAX-ACCESS read-only
			STATUS current
			DESCRIPTION
				"Description."
			::= { sleEponStatsOnuPortEntry 3 }

		
--  1.3.6.1.4.1.6296.101.20.7.2.1.1.4
		-- 1.3.6.1.4.1.6296.101.20.7.2.1.1.4
		sleEponStatsOnuPortInBcastPkts OBJECT-TYPE
			SYNTAX Counter32
			MAX-ACCESS read-only
			STATUS current
			DESCRIPTION
				"Description."
			::= { sleEponStatsOnuPortEntry 4 }

		
--  1.3.6.1.4.1.6296.101.20.7.2.1.1.5
		-- 1.3.6.1.4.1.6296.101.20.7.2.1.1.5
		sleEponStatsOnuPortInMcastPkts OBJECT-TYPE
			SYNTAX Counter32
			MAX-ACCESS read-only
			STATUS current
			DESCRIPTION
				"Description."
			::= { sleEponStatsOnuPortEntry 5 }

		
--  1.3.6.1.4.1.6296.101.20.7.2.1.1.6
		-- 1.3.6.1.4.1.6296.101.20.7.2.1.1.6
		sleEponStatsOnuPortOutOctets OBJECT-TYPE
			SYNTAX Counter64
			MAX-ACCESS read-only
			STATUS current
			DESCRIPTION
				"Description."
			::= { sleEponStatsOnuPortEntry 6 }

		
--  1.3.6.1.4.1.6296.101.20.7.2.1.1.7
		-- 1.3.6.1.4.1.6296.101.20.7.2.1.1.7
		sleEponStatsOnuPortOutPkts OBJECT-TYPE
			SYNTAX Counter32
			MAX-ACCESS read-only
			STATUS current
			DESCRIPTION
				"Description."
			::= { sleEponStatsOnuPortEntry 7 }

		
--  1.3.6.1.4.1.6296.101.20.7.2.1.1.8
		-- 1.3.6.1.4.1.6296.101.20.7.2.1.1.8
		sleEponStatsOnuPortOutUcastPkts OBJECT-TYPE
			SYNTAX Counter32
			MAX-ACCESS read-only
			STATUS current
			DESCRIPTION
				"Description."
			::= { sleEponStatsOnuPortEntry 8 }

		
--  1.3.6.1.4.1.6296.101.20.7.2.1.1.9
		-- 1.3.6.1.4.1.6296.101.20.7.2.1.1.9
		sleEponStatsOnuPortOutBcastPkts OBJECT-TYPE
			SYNTAX Counter32
			MAX-ACCESS read-only
			STATUS current
			DESCRIPTION
				"Description."
			::= { sleEponStatsOnuPortEntry 9 }

		
--  1.3.6.1.4.1.6296.101.20.7.2.1.1.10
		-- 1.3.6.1.4.1.6296.101.20.7.2.1.1.10
		sleEponStatsOnuPortOutMcastPkts OBJECT-TYPE
			SYNTAX Counter32
			MAX-ACCESS read-only
			STATUS current
			DESCRIPTION
				"Description."
			::= { sleEponStatsOnuPortEntry 10 }

		
--  1.3.6.1.4.1.6296.101.20.7.3
		-- 1.3.6.1.4.1.6296.101.20.7.3
		sleEponPerTimeStatistics OBJECT IDENTIFIER ::= { sleEponStatistics 3 }

		
--  1.3.6.1.4.1.6296.101.20.7.3.1
		-- 1.3.6.1.4.1.6296.101.20.7.3.1
		sleEponPTimeStatsPortTable OBJECT-TYPE
			SYNTAX SEQUENCE OF SleEponPTimeStatsPortEntry
			MAX-ACCESS not-accessible
			STATUS current
			DESCRIPTION
				"Description."
			::= { sleEponPerTimeStatistics 1 }

		
--  1.3.6.1.4.1.6296.101.20.7.3.1.1
		-- 1.3.6.1.4.1.6296.101.20.7.3.1.1
		sleEponPTimeStatsPortEntry OBJECT-TYPE
			SYNTAX SleEponPTimeStatsPortEntry
			MAX-ACCESS not-accessible
			STATUS current
			DESCRIPTION
				"Description."
			INDEX { ifIndex }
			::= { sleEponPTimeStatsPortTable 1 }

		
		SleEponPTimeStatsPortEntry ::=
			SEQUENCE { 
				sleEponPTimeStatsPortSaveTime
					Gauge32,
				sleEponPTimeStatsPortHourInOctets
					Counter64,
				sleEponPTimeStatsPortHourOutOctets
					Counter64,
				sleEponPTimeStatsPortDayInOctets
					Counter64,
				sleEponPTimeStatsPortDayOutOctets
					Counter64
			 }

--  1.3.6.1.4.1.6296.101.20.7.3.1.1.1
		-- 1.3.6.1.4.1.6296.101.20.7.3.1.1.1
		sleEponPTimeStatsPortSaveTime OBJECT-TYPE
			SYNTAX Gauge32
			MAX-ACCESS read-only
			STATUS current
			DESCRIPTION
				"Description."
			::= { sleEponPTimeStatsPortEntry 1 }

		
--  1.3.6.1.4.1.6296.101.20.7.3.1.1.2
		-- 1.3.6.1.4.1.6296.101.20.7.3.1.1.2
		sleEponPTimeStatsPortHourInOctets OBJECT-TYPE
			SYNTAX Counter64
			MAX-ACCESS read-only
			STATUS current
			DESCRIPTION
				"Description."
			::= { sleEponPTimeStatsPortEntry 2 }

		
--  1.3.6.1.4.1.6296.101.20.7.3.1.1.3
		-- 1.3.6.1.4.1.6296.101.20.7.3.1.1.3
		sleEponPTimeStatsPortHourOutOctets OBJECT-TYPE
			SYNTAX Counter64
			MAX-ACCESS read-only
			STATUS current
			DESCRIPTION
				"Description."
			::= { sleEponPTimeStatsPortEntry 3 }

		
--  1.3.6.1.4.1.6296.101.20.7.3.1.1.4
		-- 1.3.6.1.4.1.6296.101.20.7.3.1.1.4
		sleEponPTimeStatsPortDayInOctets OBJECT-TYPE
			SYNTAX Counter64
			MAX-ACCESS read-only
			STATUS current
			DESCRIPTION
				"Description."
			::= { sleEponPTimeStatsPortEntry 4 }

		
--  1.3.6.1.4.1.6296.101.20.7.3.1.1.5
		-- 1.3.6.1.4.1.6296.101.20.7.3.1.1.5
		sleEponPTimeStatsPortDayOutOctets OBJECT-TYPE
			SYNTAX Counter64
			MAX-ACCESS read-only
			STATUS current
			DESCRIPTION
				"Description."
			::= { sleEponPTimeStatsPortEntry 5 }

		
--  1.3.6.1.4.1.6296.101.20.7.3.2
		-- 1.3.6.1.4.1.6296.101.20.7.3.2
		sleEponPTimeStatsOltTable OBJECT-TYPE
			SYNTAX SEQUENCE OF SleEponPTimeStatsOltEntry
			MAX-ACCESS not-accessible
			STATUS current
			DESCRIPTION
				"Description."
			::= { sleEponPerTimeStatistics 2 }

		
--  1.3.6.1.4.1.6296.101.20.7.3.2.1
		-- 1.3.6.1.4.1.6296.101.20.7.3.2.1
		sleEponPTimeStatsOltEntry OBJECT-TYPE
			SYNTAX SleEponPTimeStatsOltEntry
			MAX-ACCESS not-accessible
			STATUS current
			DESCRIPTION
				"Description."
			INDEX { sleEponOltIndex }
			::= { sleEponPTimeStatsOltTable 1 }

		
		SleEponPTimeStatsOltEntry ::=
			SEQUENCE { 
				sleEponPTimeStatsOltSaveTime
					Gauge32,
				sleEponPTimeStatsOltHourInOctets
					Counter64,
				sleEponPTimeStatsOltHourOutOctets
					Counter64,
				sleEponPTimeStatsOltDayInOctets
					Counter64,
				sleEponPTimeStatsOltDayOutOctets
					Counter64
			 }

--  1.3.6.1.4.1.6296.101.20.7.3.2.1.1
		-- 1.3.6.1.4.1.6296.101.20.7.3.2.1.1
		sleEponPTimeStatsOltSaveTime OBJECT-TYPE
			SYNTAX Gauge32
			MAX-ACCESS read-only
			STATUS current
			DESCRIPTION
				"Description."
			::= { sleEponPTimeStatsOltEntry 1 }

		
--  1.3.6.1.4.1.6296.101.20.7.3.2.1.2
		-- 1.3.6.1.4.1.6296.101.20.7.3.2.1.2
		sleEponPTimeStatsOltHourInOctets OBJECT-TYPE
			SYNTAX Counter64
			MAX-ACCESS read-only
			STATUS current
			DESCRIPTION
				"Description."
			::= { sleEponPTimeStatsOltEntry 2 }

		
--  1.3.6.1.4.1.6296.101.20.7.3.2.1.3
		-- 1.3.6.1.4.1.6296.101.20.7.3.2.1.3
		sleEponPTimeStatsOltHourOutOctets OBJECT-TYPE
			SYNTAX Counter64
			MAX-ACCESS read-only
			STATUS current
			DESCRIPTION
				"Description."
			::= { sleEponPTimeStatsOltEntry 3 }

		
--  1.3.6.1.4.1.6296.101.20.7.3.2.1.4
		-- 1.3.6.1.4.1.6296.101.20.7.3.2.1.4
		sleEponPTimeStatsOltDayInOctets OBJECT-TYPE
			SYNTAX Counter64
			MAX-ACCESS read-only
			STATUS current
			DESCRIPTION
				"Description."
			::= { sleEponPTimeStatsOltEntry 4 }

		
--  1.3.6.1.4.1.6296.101.20.7.3.2.1.5
		-- 1.3.6.1.4.1.6296.101.20.7.3.2.1.5
		sleEponPTimeStatsOltDayOutOctets OBJECT-TYPE
			SYNTAX Counter64
			MAX-ACCESS read-only
			STATUS current
			DESCRIPTION
				"Description."
			::= { sleEponPTimeStatsOltEntry 5 }

		
--  1.3.6.1.4.1.6296.101.20.7.3.3
		-- 1.3.6.1.4.1.6296.101.20.7.3.3
		sleEponPTimeStatsOnuTable OBJECT-TYPE
			SYNTAX SEQUENCE OF SleEponPTimeStatsOnuEntry
			MAX-ACCESS not-accessible
			STATUS current
			DESCRIPTION
				"Description."
			::= { sleEponPerTimeStatistics 3 }

		
--  1.3.6.1.4.1.6296.101.20.7.3.3.1
		-- 1.3.6.1.4.1.6296.101.20.7.3.3.1
		sleEponPTimeStatsOnuEntry OBJECT-TYPE
			SYNTAX SleEponPTimeStatsOnuEntry
			MAX-ACCESS not-accessible
			STATUS current
			DESCRIPTION
				"Description."
			INDEX { sleEponOltIndex, sleEponOnuIndex }
			::= { sleEponPTimeStatsOnuTable 1 }

		
		SleEponPTimeStatsOnuEntry ::=
			SEQUENCE { 
				sleEponPTimeStatsOnuSaveTime
					Gauge32,
				sleEponPTimeStatsOnuHourInOctets
					Counter64,
				sleEponPTimeStatsOnuHourOutOctets
					Counter64,
				sleEponPTimeStatsOnuDayInOctets
					Counter64,
				sleEponPTimeStatsOnuDayOutOctets
					Counter64
			 }

--  1.3.6.1.4.1.6296.101.20.7.3.3.1.1
		-- 1.3.6.1.4.1.6296.101.20.7.3.3.1.1
		sleEponPTimeStatsOnuSaveTime OBJECT-TYPE
			SYNTAX Gauge32
			MAX-ACCESS read-only
			STATUS current
			DESCRIPTION
				"Description."
			::= { sleEponPTimeStatsOnuEntry 1 }

		
--  1.3.6.1.4.1.6296.101.20.7.3.3.1.2
		-- 1.3.6.1.4.1.6296.101.20.7.3.3.1.2
		sleEponPTimeStatsOnuHourInOctets OBJECT-TYPE
			SYNTAX Counter64
			MAX-ACCESS read-only
			STATUS current
			DESCRIPTION
				"Description."
			::= { sleEponPTimeStatsOnuEntry 2 }

		
--  1.3.6.1.4.1.6296.101.20.7.3.3.1.3
		-- 1.3.6.1.4.1.6296.101.20.7.3.3.1.3
		sleEponPTimeStatsOnuHourOutOctets OBJECT-TYPE
			SYNTAX Counter64
			MAX-ACCESS read-only
			STATUS current
			DESCRIPTION
				"Description."
			::= { sleEponPTimeStatsOnuEntry 3 }

		
--  1.3.6.1.4.1.6296.101.20.7.3.3.1.4
		-- 1.3.6.1.4.1.6296.101.20.7.3.3.1.4
		sleEponPTimeStatsOnuDayInOctets OBJECT-TYPE
			SYNTAX Counter64
			MAX-ACCESS read-only
			STATUS current
			DESCRIPTION
				"Description."
			::= { sleEponPTimeStatsOnuEntry 4 }

		
--  1.3.6.1.4.1.6296.101.20.7.3.3.1.5
		-- 1.3.6.1.4.1.6296.101.20.7.3.3.1.5
		sleEponPTimeStatsOnuDayOutOctets OBJECT-TYPE
			SYNTAX Counter64
			MAX-ACCESS read-only
			STATUS current
			DESCRIPTION
				"Description."
			::= { sleEponPTimeStatsOnuEntry 5 }

		
--  1.3.6.1.4.1.6296.101.20.7.3.4
		-- 1.3.6.1.4.1.6296.101.20.7.3.4
		sleEponPTimeStatsInfo OBJECT IDENTIFIER ::= { sleEponPerTimeStatistics 4 }

		
--  1.3.6.1.4.1.6296.101.20.7.3.4.1
		-- 1.3.6.1.4.1.6296.101.20.7.3.4.1
		sleEponPTimeStatsBase OBJECT IDENTIFIER ::= { sleEponPTimeStatsInfo 1 }

		
--  1.3.6.1.4.1.6296.101.20.7.3.4.1.1
		-- 1.3.6.1.4.1.6296.101.20.7.3.4.1.1
		sleEponPTimeStatsServiceActivity OBJECT-TYPE
			SYNTAX EnableFlag
			MAX-ACCESS read-only
			STATUS current
			DESCRIPTION
				"Description."
			::= { sleEponPTimeStatsBase 1 }

		
--  1.3.6.1.4.1.6296.101.20.7.3.4.2
		-- 1.3.6.1.4.1.6296.101.20.7.3.4.2
		sleEponPTimeStatsControl OBJECT IDENTIFIER ::= { sleEponPTimeStatsInfo 2 }

		
--  1.3.6.1.4.1.6296.101.20.7.3.4.2.1
		-- 1.3.6.1.4.1.6296.101.20.7.3.4.2.1
		sleEponPTimeStatsControlRequest OBJECT-TYPE
			SYNTAX INTEGER
				{
				setEponPerTimeStatisticsServiceActivity(1),
				clearEponPerTimeStatistics(2)
				}
			MAX-ACCESS read-write
			STATUS current
			DESCRIPTION
				"Description."
			::= { sleEponPTimeStatsControl 1 }

		
--  1.3.6.1.4.1.6296.101.20.7.3.4.2.2
		-- 1.3.6.1.4.1.6296.101.20.7.3.4.2.2
		sleEponPTimeStatsControlStatus OBJECT-TYPE
			SYNTAX SleControlStatusType
			MAX-ACCESS read-only
			STATUS current
			DESCRIPTION
				"Description."
			::= { sleEponPTimeStatsControl 2 }

		
--  1.3.6.1.4.1.6296.101.20.7.3.4.2.3
		-- 1.3.6.1.4.1.6296.101.20.7.3.4.2.3
		sleEponPTimeStatsControlTimer OBJECT-TYPE
			SYNTAX Gauge32
			MAX-ACCESS read-write
			STATUS current
			DESCRIPTION
				"Description."
			::= { sleEponPTimeStatsControl 3 }

		
--  1.3.6.1.4.1.6296.101.20.7.3.4.2.4
		-- 1.3.6.1.4.1.6296.101.20.7.3.4.2.4
		sleEponPTimeStatsControlTimeStamp OBJECT-TYPE
			SYNTAX TimeTicks
			MAX-ACCESS read-only
			STATUS current
			DESCRIPTION
				"Description."
			::= { sleEponPTimeStatsControl 4 }

		
--  1.3.6.1.4.1.6296.101.20.7.3.4.2.5
		-- 1.3.6.1.4.1.6296.101.20.7.3.4.2.5
		sleEponPTimeStatsControlReqResult OBJECT-TYPE
			SYNTAX SleControlRequestResultType
			MAX-ACCESS read-only
			STATUS current
			DESCRIPTION
				"Description."
			::= { sleEponPTimeStatsControl 5 }

		
--  1.3.6.1.4.1.6296.101.20.7.3.4.2.6
		-- 1.3.6.1.4.1.6296.101.20.7.3.4.2.6
		sleEponPTimeStatsControlServiceActivity OBJECT-TYPE
			SYNTAX EnableFlag
			MAX-ACCESS read-write
			STATUS current
			DESCRIPTION
				"Description."
			::= { sleEponPTimeStatsControl 6 }

		
--  1.3.6.1.4.1.6296.101.20.7.3.4.3
		-- 1.3.6.1.4.1.6296.101.20.7.3.4.3
		sleEponPTimeStatsNotification OBJECT IDENTIFIER ::= { sleEponPTimeStatsInfo 3 }

		
--  1.3.6.1.4.1.6296.101.20.7.3.4.3.1
		-- 1.3.6.1.4.1.6296.101.20.7.3.4.3.1
		sleEponPTimeStatsServiceActivityChanged NOTIFICATION-TYPE
			OBJECTS { sleEponPTimeStatsControlRequest, sleEponPTimeStatsControlTimeStamp, sleEponPTimeStatsControlReqResult, sleEponPTimeStatsControlServiceActivity }
			STATUS current
			DESCRIPTION 
				"Description."
			::= { sleEponPTimeStatsNotification 1 }

		
--  1.3.6.1.4.1.6296.101.20.7.3.4.3.2
		-- 1.3.6.1.4.1.6296.101.20.7.3.4.3.2
		sleEponPTimeStatsCleared NOTIFICATION-TYPE
			OBJECTS { sleEponPTimeStatsControlRequest, sleEponPTimeStatsControlTimeStamp, sleEponPTimeStatsControlReqResult }
			STATUS current
			DESCRIPTION 
				"Description."
			::= { sleEponPTimeStatsNotification 2 }

		
--  1.3.6.1.4.1.6296.101.20.8
		-- 1.3.6.1.4.1.6296.101.20.8
		sleEponOnuClassification OBJECT IDENTIFIER ::= { sleEpon 8 }

		
--  1.3.6.1.4.1.6296.101.20.8.1
		-- 1.3.6.1.4.1.6296.101.20.8.1
		sleEponOnuClassificationTable OBJECT-TYPE
			SYNTAX SEQUENCE OF SleEponOnuClassificationEntry
			MAX-ACCESS not-accessible
			STATUS current
			DESCRIPTION
				"Description."
			::= { sleEponOnuClassification 1 }

		
--  1.3.6.1.4.1.6296.101.20.8.1.1
		-- 1.3.6.1.4.1.6296.101.20.8.1.1
		sleEponOnuClassificationEntry OBJECT-TYPE
			SYNTAX SleEponOnuClassificationEntry
			MAX-ACCESS not-accessible
			STATUS current
			DESCRIPTION
				"Description."
			INDEX { sleEponOnuClassificationIndex }
			::= { sleEponOnuClassificationTable 1 }

		
		SleEponOnuClassificationEntry ::=
			SEQUENCE { 
				sleEponOnuClassificationIndex
					INTEGER,
				sleEponOnuClassificationName
					OCTET STRING,
				sleEponOnuClassificationTrafficDirection
					INTEGER,
				sleEponOnuClassificationLayer
					INTEGER,
				sleEponOnuClassificationEtherType
					Integer32,
				sleEponOnuClassificationProtoTypeNum
					INTEGER,
				sleEponOnuClassificationL3Addr
					IpAddress,
				sleEponOnuClassificationL4Num
					Integer32
			 }

--  1.3.6.1.4.1.6296.101.20.8.1.1.1
		-- 1.3.6.1.4.1.6296.101.20.8.1.1.1
		sleEponOnuClassificationIndex OBJECT-TYPE
			SYNTAX INTEGER (1..256)
			MAX-ACCESS read-only
			STATUS current
			DESCRIPTION
				"Description."
			::= { sleEponOnuClassificationEntry 1 }

		
--  1.3.6.1.4.1.6296.101.20.8.1.1.2
		-- 1.3.6.1.4.1.6296.101.20.8.1.1.2
		sleEponOnuClassificationName OBJECT-TYPE
			SYNTAX OCTET STRING (SIZE (1..32))
			MAX-ACCESS read-only
			STATUS current
			DESCRIPTION
				"Description."
			::= { sleEponOnuClassificationEntry 2 }

		
--  1.3.6.1.4.1.6296.101.20.8.1.1.3
		-- 1.3.6.1.4.1.6296.101.20.8.1.1.3
		sleEponOnuClassificationTrafficDirection OBJECT-TYPE
			SYNTAX INTEGER
				{
				downstream(1),
				upstream(2)
				}
			MAX-ACCESS read-only
			STATUS current
			DESCRIPTION
				"Description."
			::= { sleEponOnuClassificationEntry 3 }

		
--  1.3.6.1.4.1.6296.101.20.8.1.1.4
		-- 1.3.6.1.4.1.6296.101.20.8.1.1.4
		sleEponOnuClassificationLayer OBJECT-TYPE
			SYNTAX INTEGER
				{
				etherType(1),
				protoType(2),
				layer3Destination(3),
				layer3Source(4),
				layer4Tcp(5),
				layer4Udp(6),
				layer2Cos(7),
				layer2vid(8)
				}
			MAX-ACCESS read-only
			STATUS current
			DESCRIPTION
				"Description."
			::= { sleEponOnuClassificationEntry 4 }

		
--  1.3.6.1.4.1.6296.101.20.8.1.1.5
		-- 1.3.6.1.4.1.6296.101.20.8.1.1.5
		sleEponOnuClassificationEtherType OBJECT-TYPE
			SYNTAX Integer32
			MAX-ACCESS read-only
			STATUS current
			DESCRIPTION
				"Description."
			::= { sleEponOnuClassificationEntry 5 }

		
--  1.3.6.1.4.1.6296.101.20.8.1.1.6
		-- 1.3.6.1.4.1.6296.101.20.8.1.1.6
		sleEponOnuClassificationProtoTypeNum OBJECT-TYPE
			SYNTAX INTEGER (0 | 1..255)
			MAX-ACCESS read-only
			STATUS current
			DESCRIPTION
				"Description."
			::= { sleEponOnuClassificationEntry 6 }

		
--  1.3.6.1.4.1.6296.101.20.8.1.1.7
		-- 1.3.6.1.4.1.6296.101.20.8.1.1.7
		sleEponOnuClassificationL3Addr OBJECT-TYPE
			SYNTAX IpAddress
			MAX-ACCESS read-only
			STATUS current
			DESCRIPTION
				"Description."
			::= { sleEponOnuClassificationEntry 7 }

		
--  1.3.6.1.4.1.6296.101.20.8.1.1.8
		-- 1.3.6.1.4.1.6296.101.20.8.1.1.8
		sleEponOnuClassificationL4Num OBJECT-TYPE
			SYNTAX Integer32
			MAX-ACCESS read-only
			STATUS current
			DESCRIPTION
				"Description."
			::= { sleEponOnuClassificationEntry 8 }

		
--  1.3.6.1.4.1.6296.101.20.8.2
		-- 1.3.6.1.4.1.6296.101.20.8.2
		sleEponOnuClassificationControl OBJECT IDENTIFIER ::= { sleEponOnuClassification 2 }

		
--  1.3.6.1.4.1.6296.101.20.8.2.1
		-- 1.3.6.1.4.1.6296.101.20.8.2.1
		sleEponOnuClassificationControlRequest OBJECT-TYPE
			SYNTAX INTEGER
				{
				createOnuClassification(1),
				destroyOnuClassification(2)
				}
			MAX-ACCESS read-write
			STATUS current
			DESCRIPTION
				"The request of a user command"
			::= { sleEponOnuClassificationControl 1 }

		
--  1.3.6.1.4.1.6296.101.20.8.2.2
		-- 1.3.6.1.4.1.6296.101.20.8.2.2
		sleEponOnuClassificationControlStatus OBJECT-TYPE
			SYNTAX SleControlStatusType
			MAX-ACCESS read-only
			STATUS current
			DESCRIPTION
				"The status of user command"
			::= { sleEponOnuClassificationControl 2 }

		
--  1.3.6.1.4.1.6296.101.20.8.2.3
		-- 1.3.6.1.4.1.6296.101.20.8.2.3
		sleEponOnuClassificationControlTimer OBJECT-TYPE
			SYNTAX Gauge32
			MAX-ACCESS read-write
			STATUS current
			DESCRIPTION
				"The maximum time for the manager for a long running user command"
			::= { sleEponOnuClassificationControl 3 }

		
--  1.3.6.1.4.1.6296.101.20.8.2.4
		-- 1.3.6.1.4.1.6296.101.20.8.2.4
		sleEponOnuClassificationControlTimeStamp OBJECT-TYPE
			SYNTAX TimeTicks
			MAX-ACCESS read-only
			STATUS current
			DESCRIPTION
				"The time stamp of the last command(end of command)"
			::= { sleEponOnuClassificationControl 4 }

		
--  1.3.6.1.4.1.6296.101.20.8.2.5
		-- 1.3.6.1.4.1.6296.101.20.8.2.5
		sleEponOnuClassificationControlReqResult OBJECT-TYPE
			SYNTAX SleControlRequestResultType
			MAX-ACCESS read-only
			STATUS current
			DESCRIPTION
				"The result of the last user command"
			::= { sleEponOnuClassificationControl 5 }

		
--  1.3.6.1.4.1.6296.101.20.8.2.6
		-- 1.3.6.1.4.1.6296.101.20.8.2.6
		sleEponOnuClassificationControlName OBJECT-TYPE
			SYNTAX OCTET STRING (SIZE (1..32))
			MAX-ACCESS read-write
			STATUS current
			DESCRIPTION
				"Description."
			::= { sleEponOnuClassificationControl 6 }

		
--  1.3.6.1.4.1.6296.101.20.8.2.7
		-- 1.3.6.1.4.1.6296.101.20.8.2.7
		sleEponOnuClassificationControlTrafficDirection OBJECT-TYPE
			SYNTAX INTEGER
				{
				downstream(1),
				upstream(2)
				}
			MAX-ACCESS read-write
			STATUS current
			DESCRIPTION
				"Description."
			::= { sleEponOnuClassificationControl 7 }

		
--  1.3.6.1.4.1.6296.101.20.8.2.8
		-- 1.3.6.1.4.1.6296.101.20.8.2.8
		sleEponOnuClassificationControlLayer OBJECT-TYPE
			SYNTAX INTEGER
				{
				etherType(1),
				protoType(2),
				layer3Destination(3),
				layer3Source(4),
				layer4Tcp(5),
				layer4Udp(6),
				layer2Cos(7),
				layer2Vid(8)
				}
			MAX-ACCESS read-write
			STATUS current
			DESCRIPTION
				"Description."
			::= { sleEponOnuClassificationControl 8 }

		
--  1.3.6.1.4.1.6296.101.20.8.2.9
		-- 1.3.6.1.4.1.6296.101.20.8.2.9
		sleEponOnuClassificationControlEtherType OBJECT-TYPE
			SYNTAX Integer32
			MAX-ACCESS read-write
			STATUS current
			DESCRIPTION
				"Description."
			::= { sleEponOnuClassificationControl 9 }

		
--  1.3.6.1.4.1.6296.101.20.8.2.10
		-- 1.3.6.1.4.1.6296.101.20.8.2.10
		sleEponOnuClassificationControlProtoTypeNum OBJECT-TYPE
			SYNTAX INTEGER (0 | 1..255)
			MAX-ACCESS read-write
			STATUS current
			DESCRIPTION
				"Description."
			::= { sleEponOnuClassificationControl 10 }

		
--  1.3.6.1.4.1.6296.101.20.8.2.11
		-- 1.3.6.1.4.1.6296.101.20.8.2.11
		sleEponOnuClassificationControlL3Addr OBJECT-TYPE
			SYNTAX IpAddress
			MAX-ACCESS read-write
			STATUS current
			DESCRIPTION
				"Description."
			::= { sleEponOnuClassificationControl 11 }

		
--  1.3.6.1.4.1.6296.101.20.8.2.12
		-- 1.3.6.1.4.1.6296.101.20.8.2.12
		sleEponOnuClassificationControlL4Num OBJECT-TYPE
			SYNTAX Integer32
			MAX-ACCESS read-write
			STATUS current
			DESCRIPTION
				"Description."
			::= { sleEponOnuClassificationControl 12 }

		
--  1.3.6.1.4.1.6296.101.20.8.3
		-- 1.3.6.1.4.1.6296.101.20.8.3
		sleEponOnuClassificationNotification OBJECT IDENTIFIER ::= { sleEponOnuClassification 3 }

		
--  1.3.6.1.4.1.6296.101.20.8.3.1
		-- 1.3.6.1.4.1.6296.101.20.8.3.1
		sleEponOnuClassificationCreated NOTIFICATION-TYPE
			OBJECTS { sleEponOnuClassificationControlName }
			STATUS current
			DESCRIPTION 
				"Description."
			::= { sleEponOnuClassificationNotification 1 }

		
--  1.3.6.1.4.1.6296.101.20.8.3.2
		-- 1.3.6.1.4.1.6296.101.20.8.3.2
		sleEponOnuClassificationDestroyed NOTIFICATION-TYPE
			OBJECTS { sleEponOnuClassificationControlName }
			STATUS current
			DESCRIPTION 
				"Description."
			::= { sleEponOnuClassificationNotification 2 }

		
--  1.3.6.1.4.1.6296.101.20.9
		-- 1.3.6.1.4.1.6296.101.20.9
		sleEponVlan OBJECT IDENTIFIER ::= { sleEpon 9 }

		
--  1.3.6.1.4.1.6296.101.20.9.1
		-- 1.3.6.1.4.1.6296.101.20.9.1
		sleEponVlanOltVlan OBJECT IDENTIFIER ::= { sleEponVlan 1 }

		
--  1.3.6.1.4.1.6296.101.20.9.1.1
		-- 1.3.6.1.4.1.6296.101.20.9.1.1
		sleEponVlanOltVlanTable OBJECT-TYPE
			SYNTAX SEQUENCE OF SleEponVlanOltVlanEntry
			MAX-ACCESS not-accessible
			STATUS current
			DESCRIPTION
				"Description."
			::= { sleEponVlanOltVlan 1 }

		
--  1.3.6.1.4.1.6296.101.20.9.1.1.1
		-- 1.3.6.1.4.1.6296.101.20.9.1.1.1
		sleEponVlanOltVlanEntry OBJECT-TYPE
			SYNTAX SleEponVlanOltVlanEntry
			MAX-ACCESS not-accessible
			STATUS current
			DESCRIPTION
				"Description."
			INDEX { sleEponOltIndex, sleEponOnuIndex }
			::= { sleEponVlanOltVlanTable 1 }

		
		SleEponVlanOltVlanEntry ::=
			SEQUENCE { 
				sleEponVlanOltVlanMode
					INTEGER,
				sleEponVlanOltVlanNestedStack
					EnableFlag,
				sleEponVlanOltVlanPrefix
					INTEGER,
				sleEponVlanOltVlanSuffix
					INTEGER,
				sleEponVlanOltVlanTag
					INTEGER,
				sleEponVlanOltVlanEtherType
					INTEGER
			 }

--  1.3.6.1.4.1.6296.101.20.9.1.1.1.1
		-- 1.3.6.1.4.1.6296.101.20.9.1.1.1.1
		sleEponVlanOltVlanMode OBJECT-TYPE
			SYNTAX INTEGER
				{
				none(0),
				exchange(1),
				stack(2)
				}
			MAX-ACCESS read-only
			STATUS current
			DESCRIPTION
				"Description."
			::= { sleEponVlanOltVlanEntry 1 }

		
--  1.3.6.1.4.1.6296.101.20.9.1.1.1.2
		-- 1.3.6.1.4.1.6296.101.20.9.1.1.1.2
		sleEponVlanOltVlanNestedStack OBJECT-TYPE
			SYNTAX EnableFlag
			MAX-ACCESS read-only
			STATUS current
			DESCRIPTION
				"Description."
			::= { sleEponVlanOltVlanEntry 2 }

		
--  1.3.6.1.4.1.6296.101.20.9.1.1.1.3
		-- 1.3.6.1.4.1.6296.101.20.9.1.1.1.3
		sleEponVlanOltVlanPrefix OBJECT-TYPE
			SYNTAX INTEGER (-1 | 0..255)
			MAX-ACCESS read-only
			STATUS current
			DESCRIPTION
				"Description."
			::= { sleEponVlanOltVlanEntry 3 }

		
--  1.3.6.1.4.1.6296.101.20.9.1.1.1.4
		-- 1.3.6.1.4.1.6296.101.20.9.1.1.1.4
		sleEponVlanOltVlanSuffix OBJECT-TYPE
			SYNTAX INTEGER (-1 | 0..15)
			MAX-ACCESS read-only
			STATUS current
			DESCRIPTION
				"Description."
			::= { sleEponVlanOltVlanEntry 4 }

		
--  1.3.6.1.4.1.6296.101.20.9.1.1.1.5
		-- 1.3.6.1.4.1.6296.101.20.9.1.1.1.5
		sleEponVlanOltVlanTag OBJECT-TYPE
			SYNTAX INTEGER (-1 | 1..4096)
			MAX-ACCESS read-only
			STATUS current
			DESCRIPTION
				"Description."
			::= { sleEponVlanOltVlanEntry 5 }

		
--  1.3.6.1.4.1.6296.101.20.9.1.1.1.6
		-- 1.3.6.1.4.1.6296.101.20.9.1.1.1.6
		sleEponVlanOltVlanEtherType OBJECT-TYPE
			SYNTAX INTEGER
				{
				none(0),
				etherType0x8100(1),
				etherType0x9100(2)
				}
			MAX-ACCESS read-only
			STATUS current
			DESCRIPTION
				"Description."
			::= { sleEponVlanOltVlanEntry 6 }

		
--  1.3.6.1.4.1.6296.101.20.9.1.2
		-- 1.3.6.1.4.1.6296.101.20.9.1.2
		sleEponVlanOltVlanControl OBJECT IDENTIFIER ::= { sleEponVlanOltVlan 2 }

		
--  1.3.6.1.4.1.6296.101.20.9.1.2.1
		-- 1.3.6.1.4.1.6296.101.20.9.1.2.1
		sleEponVlanOltVlanControlRequest OBJECT-TYPE
			SYNTAX INTEGER
				{
				setEponVlanOltVlanPrefix(1),
				setEponVlanOltVlanProfile(2)
				}
			MAX-ACCESS read-write
			STATUS current
			DESCRIPTION
				"Description."
			::= { sleEponVlanOltVlanControl 1 }

		
--  1.3.6.1.4.1.6296.101.20.9.1.2.2
		-- 1.3.6.1.4.1.6296.101.20.9.1.2.2
		sleEponVlanOltVlanControlStatus OBJECT-TYPE
			SYNTAX SleControlStatusType
			MAX-ACCESS read-only
			STATUS current
			DESCRIPTION
				"Description."
			::= { sleEponVlanOltVlanControl 2 }

		
--  1.3.6.1.4.1.6296.101.20.9.1.2.3
		-- 1.3.6.1.4.1.6296.101.20.9.1.2.3
		sleEponVlanOltVlanControlTimer OBJECT-TYPE
			SYNTAX Gauge32
			MAX-ACCESS read-write
			STATUS current
			DESCRIPTION
				"Description."
			::= { sleEponVlanOltVlanControl 3 }

		
--  1.3.6.1.4.1.6296.101.20.9.1.2.4
		-- 1.3.6.1.4.1.6296.101.20.9.1.2.4
		sleEponVlanOltVlanControlTimeStamp OBJECT-TYPE
			SYNTAX TimeTicks
			MAX-ACCESS read-only
			STATUS current
			DESCRIPTION
				"Description."
			::= { sleEponVlanOltVlanControl 4 }

		
--  1.3.6.1.4.1.6296.101.20.9.1.2.5
		-- 1.3.6.1.4.1.6296.101.20.9.1.2.5
		sleEponVlanOltVlanControlReqResult OBJECT-TYPE
			SYNTAX SleControlRequestResultType
			MAX-ACCESS read-only
			STATUS current
			DESCRIPTION
				"Description."
			::= { sleEponVlanOltVlanControl 5 }

		
--  1.3.6.1.4.1.6296.101.20.9.1.2.6
		-- 1.3.6.1.4.1.6296.101.20.9.1.2.6
		sleEponVlanOltVlanControlOltIndex OBJECT-TYPE
			SYNTAX INTEGER (1..512)
			MAX-ACCESS read-write
			STATUS current
			DESCRIPTION
				"Description."
			::= { sleEponVlanOltVlanControl 6 }

		
--  1.3.6.1.4.1.6296.101.20.9.1.2.7
		-- 1.3.6.1.4.1.6296.101.20.9.1.2.7
		sleEponVlanOltVlanControlOnuIndex OBJECT-TYPE
			SYNTAX INTEGER (1..32)
			MAX-ACCESS read-write
			STATUS current
			DESCRIPTION
				"Description."
			::= { sleEponVlanOltVlanControl 7 }

		
--  1.3.6.1.4.1.6296.101.20.9.1.2.8
		-- 1.3.6.1.4.1.6296.101.20.9.1.2.8
		sleEponVlanOltVlanControlMode OBJECT-TYPE
			SYNTAX INTEGER
				{
				none(0),
				exchange(1),
				stack(2)
				}
			MAX-ACCESS read-write
			STATUS current
			DESCRIPTION
				"Description."
			::= { sleEponVlanOltVlanControl 8 }

		
--  1.3.6.1.4.1.6296.101.20.9.1.2.9
		-- 1.3.6.1.4.1.6296.101.20.9.1.2.9
		sleEponVlanOltVlanControlNestedStack OBJECT-TYPE
			SYNTAX EnableFlag
			MAX-ACCESS read-write
			STATUS current
			DESCRIPTION
				"Description."
			::= { sleEponVlanOltVlanControl 9 }

		
--  1.3.6.1.4.1.6296.101.20.9.1.2.10
		-- 1.3.6.1.4.1.6296.101.20.9.1.2.10
		sleEponVlanOltVlanControlPrefix OBJECT-TYPE
			SYNTAX INTEGER (-1 | 0..255)
			MAX-ACCESS read-write
			STATUS current
			DESCRIPTION
				"Description."
			::= { sleEponVlanOltVlanControl 10 }

		
--  1.3.6.1.4.1.6296.101.20.9.1.2.11
		-- 1.3.6.1.4.1.6296.101.20.9.1.2.11
		sleEponVlanOltVlanControlSuffix OBJECT-TYPE
			SYNTAX INTEGER (-1 | 0..15)
			MAX-ACCESS read-write
			STATUS current
			DESCRIPTION
				"Description."
			::= { sleEponVlanOltVlanControl 11 }

		
--  1.3.6.1.4.1.6296.101.20.9.1.2.12
		-- 1.3.6.1.4.1.6296.101.20.9.1.2.12
		sleEponVlanOltVlanControlVlanTag OBJECT-TYPE
			SYNTAX INTEGER (-1 | 1..4094)
			MAX-ACCESS read-write
			STATUS current
			DESCRIPTION
				"Description."
			::= { sleEponVlanOltVlanControl 12 }

		
--  1.3.6.1.4.1.6296.101.20.9.1.2.13
		-- 1.3.6.1.4.1.6296.101.20.9.1.2.13
		sleEponVlanOltVlanControlEtherType OBJECT-TYPE
			SYNTAX INTEGER
				{
				none(0),
				etherType0x8100(1),
				etherType0x9100(2)
				}
			MAX-ACCESS read-write
			STATUS current
			DESCRIPTION
				"Description."
			::= { sleEponVlanOltVlanControl 13 }

		
--  1.3.6.1.4.1.6296.101.20.9.1.3
		-- 1.3.6.1.4.1.6296.101.20.9.1.3
		sleEponVlanOltVlanNotification OBJECT IDENTIFIER ::= { sleEponVlanOltVlan 3 }

		
--  1.3.6.1.4.1.6296.101.20.9.1.3.1
		-- 1.3.6.1.4.1.6296.101.20.9.1.3.1
		sleEponVlanOltVlanPrefixChanged NOTIFICATION-TYPE
			OBJECTS { sleEponVlanOltVlanControlRequest, sleEponVlanOltVlanControlTimeStamp, sleEponVlanOltVlanControlReqResult, sleEponVlanOltVlanControlOltIndex, sleEponVlanOltVlanControlPrefix
				 }
			STATUS current
			DESCRIPTION 
				"Description."
			::= { sleEponVlanOltVlanNotification 1 }

		
--  1.3.6.1.4.1.6296.101.20.9.1.3.2
		-- 1.3.6.1.4.1.6296.101.20.9.1.3.2
		sleEponVlanOltVlanProfileChanged NOTIFICATION-TYPE
			OBJECTS { sleEponVlanOltVlanControlRequest, sleEponVlanOltVlanControlTimeStamp, sleEponVlanOltVlanControlReqResult, sleEponVlanOltVlanControlOltIndex, sleEponVlanOltVlanControlOnuIndex, 
				sleEponVlanOltVlanControlMode, sleEponVlanOltVlanControlNestedStack, sleEponVlanOltVlanControlSuffix, sleEponVlanOltVlanControlVlanTag, sleEponVlanOltVlanControlEtherType
				 }
			STATUS current
			DESCRIPTION 
				"Description."
			::= { sleEponVlanOltVlanNotification 2 }

		
--  1.3.6.1.4.1.6296.101.20.9.2
		-- 1.3.6.1.4.1.6296.101.20.9.2
		sleEponVlanOnuVlan OBJECT IDENTIFIER ::= { sleEponVlan 2 }

		
--  1.3.6.1.4.1.6296.101.20.9.2.1
		-- 1.3.6.1.4.1.6296.101.20.9.2.1
		sleEponVlanOnuVlanTable OBJECT-TYPE
			SYNTAX SEQUENCE OF SleEponVlanOnuVlanEntry
			MAX-ACCESS not-accessible
			STATUS current
			DESCRIPTION
				"Description."
			::= { sleEponVlanOnuVlan 1 }

		
--  1.3.6.1.4.1.6296.101.20.9.2.1.1
		-- 1.3.6.1.4.1.6296.101.20.9.2.1.1
		sleEponVlanOnuVlanEntry OBJECT-TYPE
			SYNTAX SleEponVlanOnuVlanEntry
			MAX-ACCESS not-accessible
			STATUS current
			DESCRIPTION
				"Description."
			INDEX { sleEponOltIndex, sleEponOnuIndex }
			::= { sleEponVlanOnuVlanTable 1 }

		
		SleEponVlanOnuVlanEntry ::=
			SEQUENCE { 
				sleEponVlanOnuVlanUpMode
					INTEGER,
				sleEponVlanOnuVlanUpVlanTag
					INTEGER,
				sleEponVlanOnuVlanUpEtherType
					INTEGER,
				sleEponVlanOnuVlanUpPriority
					Integer32,
				sleEponVlanOnuVlanDownMode
					INTEGER,
				sleEponVlanOnuVlanDownVlanTag
					INTEGER,
				sleEponVlanOnuVlanDownPriority
					Integer32
			 }

--  1.3.6.1.4.1.6296.101.20.9.2.1.1.1
		-- 1.3.6.1.4.1.6296.101.20.9.2.1.1.1
		sleEponVlanOnuVlanUpMode OBJECT-TYPE
			SYNTAX INTEGER
				{
				none(0),
				exchange(1),
				stack(2)
				}
			MAX-ACCESS read-only
			STATUS current
			DESCRIPTION
				"Description."
			::= { sleEponVlanOnuVlanEntry 1 }

		
--  1.3.6.1.4.1.6296.101.20.9.2.1.1.2
		-- 1.3.6.1.4.1.6296.101.20.9.2.1.1.2
		sleEponVlanOnuVlanUpVlanTag OBJECT-TYPE
			SYNTAX INTEGER (-1 | 1..4094)
			MAX-ACCESS read-only
			STATUS current
			DESCRIPTION
				"Description."
			::= { sleEponVlanOnuVlanEntry 2 }

		
--  1.3.6.1.4.1.6296.101.20.9.2.1.1.3
		-- 1.3.6.1.4.1.6296.101.20.9.2.1.1.3
		sleEponVlanOnuVlanUpEtherType OBJECT-TYPE
			SYNTAX INTEGER
				{
				none(0),
				etherType0x8100(1),
				etherType0x9100(2)
				}
			MAX-ACCESS read-only
			STATUS current
			DESCRIPTION
				"Description."
			::= { sleEponVlanOnuVlanEntry 3 }

		
--  1.3.6.1.4.1.6296.101.20.9.2.1.1.4
		-- 1.3.6.1.4.1.6296.101.20.9.2.1.1.4
		sleEponVlanOnuVlanUpPriority OBJECT-TYPE
			SYNTAX Integer32
			MAX-ACCESS read-only
			STATUS current
			DESCRIPTION
				"Description."
			::= { sleEponVlanOnuVlanEntry 4 }

		
--  1.3.6.1.4.1.6296.101.20.9.2.1.1.5
		-- 1.3.6.1.4.1.6296.101.20.9.2.1.1.5
		sleEponVlanOnuVlanDownMode OBJECT-TYPE
			SYNTAX INTEGER
				{
				none(0),
				exchange(1),
				stack(2)
				}
			MAX-ACCESS read-only
			STATUS current
			DESCRIPTION
				"Description."
			::= { sleEponVlanOnuVlanEntry 5 }

		
--  1.3.6.1.4.1.6296.101.20.9.2.1.1.6
		-- 1.3.6.1.4.1.6296.101.20.9.2.1.1.6
		sleEponVlanOnuVlanDownVlanTag OBJECT-TYPE
			SYNTAX INTEGER (-1 | 1..4094)
			MAX-ACCESS read-only
			STATUS current
			DESCRIPTION
				"Description."
			::= { sleEponVlanOnuVlanEntry 6 }

		
--  1.3.6.1.4.1.6296.101.20.9.2.1.1.7
		-- 1.3.6.1.4.1.6296.101.20.9.2.1.1.7
		sleEponVlanOnuVlanDownPriority OBJECT-TYPE
			SYNTAX Integer32
			MAX-ACCESS read-write
			STATUS current
			DESCRIPTION
				"Description."
			::= { sleEponVlanOnuVlanEntry 7 }

		
--  1.3.6.1.4.1.6296.101.20.9.2.2
		-- 1.3.6.1.4.1.6296.101.20.9.2.2
		sleEponVlanOnuVlanControl OBJECT IDENTIFIER ::= { sleEponVlanOnuVlan 2 }

		
--  1.3.6.1.4.1.6296.101.20.9.2.2.1
		-- 1.3.6.1.4.1.6296.101.20.9.2.2.1
		sleEponVlanOnuVlanControlRequest OBJECT-TYPE
			SYNTAX INTEGER { setEponVlanOnuVlanProfile(1) }
			MAX-ACCESS read-write
			STATUS current
			DESCRIPTION
				"Description."
			::= { sleEponVlanOnuVlanControl 1 }

		
--  1.3.6.1.4.1.6296.101.20.9.2.2.2
		-- 1.3.6.1.4.1.6296.101.20.9.2.2.2
		sleEponVlanOnuVlanControlStatus OBJECT-TYPE
			SYNTAX SleControlStatusType
			MAX-ACCESS read-only
			STATUS current
			DESCRIPTION
				"Description."
			::= { sleEponVlanOnuVlanControl 2 }

		
--  1.3.6.1.4.1.6296.101.20.9.2.2.3
		-- 1.3.6.1.4.1.6296.101.20.9.2.2.3
		sleEponVlanOnuVlanControlTimer OBJECT-TYPE
			SYNTAX Gauge32
			MAX-ACCESS read-write
			STATUS current
			DESCRIPTION
				"Description."
			::= { sleEponVlanOnuVlanControl 3 }

		
--  1.3.6.1.4.1.6296.101.20.9.2.2.4
		-- 1.3.6.1.4.1.6296.101.20.9.2.2.4
		sleEponVlanOnuVlanControlTimeStamp OBJECT-TYPE
			SYNTAX TimeTicks
			MAX-ACCESS read-only
			STATUS current
			DESCRIPTION
				"Description."
			::= { sleEponVlanOnuVlanControl 4 }

		
--  1.3.6.1.4.1.6296.101.20.9.2.2.5
		-- 1.3.6.1.4.1.6296.101.20.9.2.2.5
		sleEponVlanOnuVlanControlReqResult OBJECT-TYPE
			SYNTAX SleControlRequestResultType
			MAX-ACCESS read-only
			STATUS current
			DESCRIPTION
				"Description."
			::= { sleEponVlanOnuVlanControl 5 }

		
--  1.3.6.1.4.1.6296.101.20.9.2.2.6
		-- 1.3.6.1.4.1.6296.101.20.9.2.2.6
		sleEponVlanOnuVlanControlOltIndex OBJECT-TYPE
			SYNTAX INTEGER (1..512)
			MAX-ACCESS read-write
			STATUS current
			DESCRIPTION
				"Description."
			::= { sleEponVlanOnuVlanControl 6 }

		
--  1.3.6.1.4.1.6296.101.20.9.2.2.7
		-- 1.3.6.1.4.1.6296.101.20.9.2.2.7
		sleEponVlanOnuVlanControlOnuIndex OBJECT-TYPE
			SYNTAX INTEGER (1..32)
			MAX-ACCESS read-write
			STATUS current
			DESCRIPTION
				"Description."
			::= { sleEponVlanOnuVlanControl 7 }

		
--  1.3.6.1.4.1.6296.101.20.9.2.2.8
		-- 1.3.6.1.4.1.6296.101.20.9.2.2.8
		sleEponVlanOnuVlanControlUpMode OBJECT-TYPE
			SYNTAX INTEGER
				{
				none(0),
				exchange(1),
				stack(2)
				}
			MAX-ACCESS read-write
			STATUS current
			DESCRIPTION
				"Description."
			::= { sleEponVlanOnuVlanControl 8 }

		
--  1.3.6.1.4.1.6296.101.20.9.2.2.9
		-- 1.3.6.1.4.1.6296.101.20.9.2.2.9
		sleEponVlanOnuVlanControlUpVlanTag OBJECT-TYPE
			SYNTAX INTEGER (-1 | 1..4094)
			MAX-ACCESS read-write
			STATUS current
			DESCRIPTION
				"Description."
			::= { sleEponVlanOnuVlanControl 9 }

		
--  1.3.6.1.4.1.6296.101.20.9.2.2.10
		-- 1.3.6.1.4.1.6296.101.20.9.2.2.10
		sleEponVlanOnuVlanControlUpEtherType OBJECT-TYPE
			SYNTAX INTEGER
				{
				none(0),
				etherType0x8100(1),
				etherType0x9100(2)
				}
			MAX-ACCESS read-write
			STATUS current
			DESCRIPTION
				"Description."
			::= { sleEponVlanOnuVlanControl 10 }

		
--  1.3.6.1.4.1.6296.101.20.9.2.2.11
		-- 1.3.6.1.4.1.6296.101.20.9.2.2.11
		sleEponVlanOnuVlanControlUpPriority OBJECT-TYPE
			SYNTAX Integer32
			MAX-ACCESS read-write
			STATUS current
			DESCRIPTION
				"Description."
			::= { sleEponVlanOnuVlanControl 11 }

		
--  1.3.6.1.4.1.6296.101.20.9.2.2.12
		-- 1.3.6.1.4.1.6296.101.20.9.2.2.12
		sleEponVlanOnuVlanControlDownMode OBJECT-TYPE
			SYNTAX INTEGER
				{
				none(0),
				exchange(1),
				stack(2)
				}
			MAX-ACCESS read-write
			STATUS current
			DESCRIPTION
				"Description."
			::= { sleEponVlanOnuVlanControl 12 }

		
--  1.3.6.1.4.1.6296.101.20.9.2.2.13
		-- 1.3.6.1.4.1.6296.101.20.9.2.2.13
		sleEponVlanOnuVlanControlDownVlanTag OBJECT-TYPE
			SYNTAX INTEGER (-1 | 1..4094)
			MAX-ACCESS read-write
			STATUS current
			DESCRIPTION
				"Description."
			::= { sleEponVlanOnuVlanControl 13 }

		
--  1.3.6.1.4.1.6296.101.20.9.2.2.14
		-- 1.3.6.1.4.1.6296.101.20.9.2.2.14
		sleEponVlanOnuVlanControlDownPriority OBJECT-TYPE
			SYNTAX Integer32
			MAX-ACCESS read-write
			STATUS current
			DESCRIPTION
				"Description."
			::= { sleEponVlanOnuVlanControl 14 }

		
--  1.3.6.1.4.1.6296.101.20.9.2.3
		-- 1.3.6.1.4.1.6296.101.20.9.2.3
		sleEponVlanOnuVlanNotification OBJECT IDENTIFIER ::= { sleEponVlanOnuVlan 3 }

		
--  1.3.6.1.4.1.6296.101.20.9.2.3.1
		-- 1.3.6.1.4.1.6296.101.20.9.2.3.1
		sleEponVlanOnuVlanProfileChanged NOTIFICATION-TYPE
			OBJECTS { sleEponVlanOnuVlanControlRequest, sleEponVlanOnuVlanControlTimeStamp, sleEponVlanOnuVlanControlReqResult, sleEponVlanOnuVlanControlOltIndex, sleEponVlanOnuVlanControlOnuIndex, 
				sleEponVlanOnuVlanControlUpMode, sleEponVlanOnuVlanControlUpVlanTag, sleEponVlanOnuVlanControlUpEtherType, sleEponVlanOnuVlanControlDownMode, sleEponVlanOnuVlanControlDownVlanTag
				 }
			STATUS current
			DESCRIPTION 
				"Description."
			::= { sleEponVlanOnuVlanNotification 1 }

		
		-- 1.3.6.1.4.1.6296.101.20.10
		sleEponFirmwareMgmt OBJECT IDENTIFIER ::= { sleEpon 10 }

		
		-- 1.3.6.1.4.1.6296.101.20.10.1
		sleEponFirmwareTable OBJECT-TYPE
			SYNTAX SEQUENCE OF SleEponFirmwareEntry
			MAX-ACCESS not-accessible
			STATUS current
			DESCRIPTION
				"Description."
			::= { sleEponFirmwareMgmt 1 }

		
		-- 1.3.6.1.4.1.6296.101.20.10.1.1
		sleEponFirmwareEntry OBJECT-TYPE
			SYNTAX SleEponFirmwareEntry
			MAX-ACCESS not-accessible
			STATUS current
			DESCRIPTION
				"Description."
			INDEX { sleEponFirmwareType, sleEponFirmwareName }
			::= { sleEponFirmwareTable 1 }

		
		SleEponFirmwareEntry ::=
			SEQUENCE { 
				sleEponFirmwareType
					INTEGER,
				sleEponFirmwareName
					OCTET STRING
			 }

		-- 1.3.6.1.4.1.6296.101.20.10.1.1.1
		sleEponFirmwareType OBJECT-TYPE
			SYNTAX INTEGER
				{
				olt(1),
				onu(2)
				}
			MAX-ACCESS read-only
			STATUS current
			DESCRIPTION
				"Description."
			::= { sleEponFirmwareEntry 1 }

		
		-- 1.3.6.1.4.1.6296.101.20.10.1.1.2
		sleEponFirmwareName OBJECT-TYPE
			SYNTAX OCTET STRING (SIZE (1..128))
			MAX-ACCESS read-only
			STATUS current
			DESCRIPTION
				"Description."
			::= { sleEponFirmwareEntry 2 }

		
		-- 1.3.6.1.4.1.6296.101.20.10.2
		sleEponFirmwareControl OBJECT IDENTIFIER ::= { sleEponFirmwareMgmt 2 }

		
		-- 1.3.6.1.4.1.6296.101.20.10.2.1
		sleEponFirmwareControlRequest OBJECT-TYPE
			SYNTAX INTEGER
				{
				setEponFirmwareUpgradeProfile(1),
				deleteEponFirmware(2)
				}
			MAX-ACCESS read-write
			STATUS current
			DESCRIPTION
				"Description."
			::= { sleEponFirmwareControl 1 }

		
		-- 1.3.6.1.4.1.6296.101.20.10.2.2
		sleEponFirmwareControlStatus OBJECT-TYPE
			SYNTAX SleControlStatusType
			MAX-ACCESS read-only
			STATUS current
			DESCRIPTION
				"Description."
			::= { sleEponFirmwareControl 2 }

		
		-- 1.3.6.1.4.1.6296.101.20.10.2.3
		sleEponFirmwareControlTimer OBJECT-TYPE
			SYNTAX Gauge32
			MAX-ACCESS read-write
			STATUS current
			DESCRIPTION
				"Description."
			::= { sleEponFirmwareControl 3 }

		
		-- 1.3.6.1.4.1.6296.101.20.10.2.4
		sleEponFirmwareControlTimeStamp OBJECT-TYPE
			SYNTAX TimeTicks
			MAX-ACCESS read-only
			STATUS current
			DESCRIPTION
				"Description."
			::= { sleEponFirmwareControl 4 }

		
		-- 1.3.6.1.4.1.6296.101.20.10.2.5
		sleEponFirmwareControlReqResult OBJECT-TYPE
			SYNTAX SleControlRequestResultType
			MAX-ACCESS read-only
			STATUS current
			DESCRIPTION
				"Description."
			::= { sleEponFirmwareControl 5 }

		
		-- 1.3.6.1.4.1.6296.101.20.10.2.6
		sleEponFirmwareControlName OBJECT-TYPE
			SYNTAX OCTET STRING (SIZE (1..128))
			MAX-ACCESS read-write
			STATUS current
			DESCRIPTION
				"Description."
			::= { sleEponFirmwareControl 6 }

		
		-- 1.3.6.1.4.1.6296.101.20.10.2.7
		sleEponFirmwareControlUpgradeMethod OBJECT-TYPE
			SYNTAX INTEGER
				{
				ftp(1),
				tftp(2)
				}
			MAX-ACCESS read-write
			STATUS current
			DESCRIPTION
				"Description."
			::= { sleEponFirmwareControl 7 }

		
		-- 1.3.6.1.4.1.6296.101.20.10.2.8
		sleEponFirmwareControlUpgradeMode OBJECT-TYPE
			SYNTAX INTEGER
				{
				upload(1),
				download(2)
				}
			MAX-ACCESS read-write
			STATUS current
			DESCRIPTION
				"Description."
			::= { sleEponFirmwareControl 8 }

		
		-- 1.3.6.1.4.1.6296.101.20.10.2.9
		sleEponFirmwareControlServerAddress OBJECT-TYPE
			SYNTAX IpAddress
			MAX-ACCESS read-write
			STATUS current
			DESCRIPTION
				"Description."
			::= { sleEponFirmwareControl 9 }

		
		-- 1.3.6.1.4.1.6296.101.20.10.2.10
		sleEponFirmwareControlUser OBJECT-TYPE
			SYNTAX OCTET STRING
			MAX-ACCESS read-write
			STATUS current
			DESCRIPTION
				"Description."
			::= { sleEponFirmwareControl 10 }

		
		-- 1.3.6.1.4.1.6296.101.20.10.2.11
		sleEponFirmwareControlPasswd OBJECT-TYPE
			SYNTAX OCTET STRING
			MAX-ACCESS read-write
			STATUS current
			DESCRIPTION
				"Description."
			::= { sleEponFirmwareControl 11 }

		
		-- 1.3.6.1.4.1.6296.101.20.10.3
		sleEponFirmwareNotification OBJECT IDENTIFIER ::= { sleEponFirmwareMgmt 3 }

		
		-- 1.3.6.1.4.1.6296.101.20.10.3.1
		sleEponFirmwareUpgradeProfileChanged NOTIFICATION-TYPE
			OBJECTS { sleEponFirmwareControlRequest, sleEponFirmwareControlTimeStamp, sleEponFirmwareControlReqResult, sleEponFirmwareControlName, sleEponFirmwareControlUpgradeMethod, 
				sleEponFirmwareControlUpgradeMode, sleEponFirmwareControlServerAddress, sleEponFirmwareControlUser, sleEponFirmwareControlPasswd }
			STATUS current
			DESCRIPTION 
				"Description."
			::= { sleEponFirmwareNotification 1 }

		
		-- 1.3.6.1.4.1.6296.101.20.10.3.2
		sleEponFirmwareDeleted NOTIFICATION-TYPE
			OBJECTS { sleEponFirmwareControlRequest, sleEponFirmwareControlTimeStamp, sleEponFirmwareControlReqResult, sleEponFirmwareControlName }
			STATUS current
			DESCRIPTION 
				"Description."
			::= { sleEponFirmwareNotification 2 }

		
--  1.3.6.1.4.1.6296.101.20.11
		-- 1.3.6.1.4.1.6296.101.20.11
		sleEponGroup OBJECT-GROUP
			OBJECTS { sleEponOltControlRequest, sleEponOltControlStatus, sleEponOltControlTimer, sleEponOltControlTimeStamp, sleEponOltControlReqResult, 
				sleEponOltControlOltIndex, sleEponOltControlRegMode, sleEponOltControlEncryptionPolicy, sleEponOltControlP2pAccessControl, sleEponOltControlDbaInternal, 
				sleEponOltControlDbaCycle, sleEponOltControlDbaDiscoveryFrequency, sleEponOltControlDbaDiscoveryLength, sleEponOnuControlRequest, sleEponOnuControlStatus, 
				sleEponOnuControlTimer, sleEponOnuControlTimeStamp, sleEponOnuControlReqResult, sleEponOnuControlOltIndex, sleEponOnuControlMacAddress, 
				sleEponOnuControlRegMode, sleEponOnuControlDescription, sleEponOnuControlProfile, sleEponProfileControlRequest, sleEponProfileControlStatus, 
				sleEponProfileControlTimer, sleEponProfileControlTimeStamp, sleEponProfileControlReqResult, sleEponProfileControlName, sleEponProfileControlDPDownMaxBandwidth, 
				sleEponProfileControlDPDownMaxBurstSize, sleEponProfileControlDPP2pMaxBandwidth, sleEponProfileControlDPP2pMaxBurstSize, sleEponProfileControlSlaGuaranteedBandwidth, sleEponProfileControlSlaPlatoClass, 
				sleEponProfileControlSlaPlatoGuaranteedBandwidth1m, sleEponProfileControlSlaPlatoGuaranteedBandwdith64k, sleEponProfileControlSlaPlatoBestEffortBandwidth1m, sleEponProfileControlSlaPlatoBestEffortBandwidth64k, sleEponProfileControlSlaPlatoDelayLevel, 
				sleEponAlarmControlRequest, sleEponAlarmControlStatus, sleEponAlarmControlTimer, sleEponAlarmControlTimeStamp, sleEponAlarmControlReqResult, 
				sleEponAlarmControlOltIndex, sleEponAlarmControlBadEncryption, sleEponAlarmControlDyingGasp, sleEponAlarmControlLlidMismatch, sleEponAlarmControlOnuRegistrationError, 
				sleEponOnuControlOnuIndex, sleEponOnuControlOnuStatus, sleEponStatsOltControlRequest, sleEponStatsOltControlStatus, sleEponStatsOltControlTimer, 
				sleEponStatsOltControlTimeStamp, sleEponStatsOltControlReqResult, sleEponStatsOltControlOltIndex, sleEponStatsOltControlChannelIndex, sleEponOnuControlLoopbackProvision, 
				sleEponOltControlOltStatus, sleEponAlarmControlTooManyOnuRegistration, sleEponProfileQueueControlRequest, sleEponProfileQueueControlStatus, sleEponProfileQueueControlTimer, 
				sleEponProfileQueueControlTimeStamp, sleEponProfileQueueControlReqResult, sleEponProfileQueueControlProfileIndex, sleEponProfileQueueControlQueueIndex, sleEponProfileQueueControlQPUpQueue, 
				sleEponProfileQueueControlQPUpMaxBandwidth, sleEponProfileQueueControlQPUpMAxBurstSize, sleEponProfileQueueControlQPDownQueue, sleEponProfileQueueControlQPDownMaxBandwidth, sleEponProfileQueueControlQPDownMAxBurstSize, 
				sleEponOltControlProfile, sleEponProfilePortControlRequest, sleEponProfilePortControlStatus, sleEponProfilePortControlTimer, sleEponProfilePortControlTimeStamp, 
				sleEponProfilePortControlReqResult, sleEponProfilePortControlAdminStatus, sleEponProfilePortControlNego, sleEponProfilePortControlSpeed, sleEponProfilePortControlMaxHost, 
				sleEponProfileVlanControlRequest, sleEponProfileVlanControlStatus, sleEponProfileVlanControlTimer, sleEponProfileVlanControlTimeStamp, sleEponProfileVlanControlReqResult, 
				sleEponProfileVlanControlVlanIndex, sleEponProfileVlanControlVlanEgressPorts, sleEponProfileVlanControlVlanUntaggedPorts, sleEponProfilePortControlPvid, sleEponProfilePortControlEgressRateLimit, 
				sleEponProfilePortControlIngressRateLimit, sleEponProfilePortControlIngressRateLimitMode, sleEponOnuPortControlReqResult, sleEponOnuPortControlOltIndex, sleEponOnuPortControlOnuIndex, 
				sleEponOnuPortControlPortIndex, sleEponOnuPortControlRequest, sleEponOnuPortControlStatus, sleEponOnuPortControlTimer, sleEponOnuPortControlTimeStamp, 
				sleEponOnuClassificationControlRequest, sleEponOnuClassificationControlStatus, sleEponOnuClassificationControlTimer, sleEponOnuClassificationControlTimeStamp, sleEponOnuClassificationControlProtoTypeNum, 
				sleEponOnuClassificationControlL3Addr, sleEponOnuClassificationControlReqResult, sleEponOnuClassificationControlName, sleEponOnuClassificationControlTrafficDirection, sleEponOnuClassificationControlLayer, 
				sleEponOnuClassificationControlEtherType, sleEponProfileVlanControlProfileIndex, sleEponProfileClassificationControlQueue, sleEponProfileClassificationControlReqResult, sleEponProfileClassificationControlProfileIndex, 
				sleEponProfileClassificationControlClassificationIndex, sleEponProfileClassificationControlMatchAction, sleEponProfileClassificationControlRequest, sleEponProfileClassificationControlStatus, sleEponProfileClassificationControlTimer, 
				sleEponProfileClassificationControlTimeStamp, sleEponOltIndex, sleEponOltRegMode, sleEponOltStatus, sleEponOltEncryptionPolicy, 
				sleEponOltP2pAccessControl, sleEponOltDbaInternal, sleEponOltDbaCycle, sleEponOltDbaDiscoveryFrequency, sleEponOltDbaDiscoveryLength, 
				sleEponOltProfile, sleEponOltTxFault, sleEponOltLossOfSignal, sleEponOltAdminRegMode, sleEponOltSC, 
				sleEponOltSCAutoOnuBlock, sleEponOltControlSC, sleEponOltControlSCAutoOnuBlock, sleEponOltControlUpgradeFilename, sleEponOnuIndex, 
				sleEponOnuLlid, sleEponOnuRegMode, sleEponOnuStatus, sleEponOnuMacAddress, sleEponOnuRtt, 
				sleEponOnuDescription, sleEponOnuProfile, sleEponOnuLoopbackProvision, sleEponOnuVendor, sleEponOnuFirmwareRev, 
				sleEponOnuControlTxPowerOffTimer, sleEponOnuVlanIndex, sleEponOnuVlanEgressPorts, sleEponOnuVlanUntaggedPorts, sleEponOnuPortIndex, 
				sleEponOnuPortAdminStatus, sleEponOnuPortOperStatus, sleEponOnuPortNego, sleEponOnuPortSpeed, sleEponOnuPortDuplex, 
				sleEponOnuPortMaxHost, sleEponOnuPortPvid, sleEponOnuPortIngressRateLimitMode, sleEponOnuPortIngressRateLimit, sleEponOnuPortEgressRateLimit, 
				sleEponOnuPortFlowControl, sleEponOnuFdbMacAddress, sleEponOnuFdbType, sleEponOnuFdbPermission, sleEponOnuFdbControlRequest, 
				sleEponOnuFdbControlStatus, sleEponOnuFdbControlTimer, sleEponOnuFdbControlTimeStamp, sleEponOnuFdbControlReqResult, sleEponOnuFdbControlOltIndex, 
				sleEponOnuFdbControlOnuIndex, sleEponOnuFdbControlType, sleEponOnuUserMacIndex, sleEponOnuUserMacMacAddress, sleEponOnuUserMacUsedTime, 
				sleEponProfileIndex, sleEponProfileName, sleEponProfileDPDownMaxBandwidth, sleEponProfileDPDownMaxBurstSize, sleEponProfileDPP2pMaxBandwidth, 
				sleEponProfileDPP2pMaxBurstSize, sleEponProfileSlaGuaranteedBandwidth, sleEponProfileSlaBestEffortBandwidth, sleEponProfileSlaPlatoClass, sleEponProfileSlaPlatoMinBandwidth1m, 
				sleEponProfileSlaPlatoMinBandwdith64k, sleEponProfileSlaPlatoMaxBandwidth1m, sleEponProfileSlaPlatoMaxBandwidth64k, sleEponProfileSlaPlatoDelayLevel, sleEponProfileIgmpFilter, 
				sleEponProfileIgmpSnooping, sleEponProfileSTPenable, sleEponProfileControlExtendMtu, sleEponProfileControlIgmpFilter, sleEponProfileControlSnooping, 
				sleEponProfileControlSTPenable, sleEponProfileQueueIndex, sleEponProfileQueueQPUpQueue, sleEponProfileQueueQPUpMaxBandwidth, sleEponProfileQueueQPUpMAxBurstSize, 
				sleEponProfileQueueQPDownQueue, sleEponProfileQueueQPDownMaxBandwidth, sleEponProfileQueueQPDownMAxBurstSize, sleEponProfileQueueQLimitUpBlockSize, sleEponProfileQueueQLimitDownBlockSize, 
				sleEponProfileQueueControlLimitFlag, sleEponProfileQueueControlBlockSize0, sleEponProfileQueueControlBlockSize1, sleEponProfileQueueControlBlockSize2, sleEponProfileQueueControlBlockSize3, 
				sleEponProfileVlanIndex, sleEponProfileVlanEgressPorts, sleEponProfileVlanUntaggedPorts, sleEponProfilePortIndex, sleEponProfilePortAdminStatus, 
				sleEponProfilePortNego, sleEponProfilePortSpeed, sleEponProfilePortduplex, sleEponProfilePortMaxHost, sleEponProfilePortPvid, 
				sleEponProfilePortIngressRateLimitMode, sleEponProfilePortIngressRateLimit, sleEponProfilePortEgressRateLimit, sleEponProfilePortFlowControl, sleEponProfilePortControlFlowControl, 
				sleEponProfileClassificationIndex, sleEponProfileClassificationMatchAction, sleEponProfileClassificationQueue, sleEponAlarmBadEncryption, sleEponAlarmDyingGasp, 
				sleEponAlarmLlidMismatch, sleEponAlarmOnuRegistrationError, sleEponAlarmTooManyOnuRegistration, sleEponStatsOltInOctets, sleEponStatsOltInPkts, 
				sleEponStatsOltInPause, sleEponStatsOltInErroredFrame, sleEponStatsOltInUnicastPkts, sleEponstatsOltInBroadcastPkts, sleEponStatsOltInMulticastPkts, 
				sleEponStatsOltOutOctets, sleEponStatsOltOutPkts, sleEponStatsOltOutPause, sleEponStatsOltOutDropped, sleEponStatsOltOutUnicastPkts, 
				sleEponstatsOltOutBroadcastPkts, sleEponStatsOltOutMulticastPkts, sleEponStatsOltPonInOctets, sleEponStatsOltPonInPkts, sleEponStatsOltPonInPause, 
				sleEponStatsOltPonInErroredFrame, sleEponStatsOltPonInUnicastPkts, sleEponstatsOltPonInBroadcastPkts, sleEponStatsOltPonInMulticastPkts, sleEponStatsOltPonOutOctets, 
				sleEponStatsOltPonOutPkts, sleEponStatsOltPonOutPause, sleEponStatsOltPonOutDropped, sleEponStatsOltPonOutUnicastPkts, sleEponstatsOltPonOutBroadcastPkts, 
				sleEponStatsOltPonOutMulticastPkts, sleEponStatsOltChannelInOctets, sleEponStatsOltChannelInDataOctets, sleEponStatsOltChannelInPkts, sleEponStatsOltChannelInMulticastPkts, 
				sleEponStatsOltChannelInBroadcastPkts, sleEponStatsOltChannelInErrorOctets, sleEponStatsOltChannelInErrorPkts, sleEponStatsOltChannelOutOctets, sleEponStatsOltChannelOutPkts, 
				sleEponStatsOltChannelOutPolicerDroppedPkts, sleEponStatsOltChannelOutMismatchDroppedPkts, sleEponStatsOltChannelOutMulticastPkts, sleEponStatsOltChannelOutBroadcastPkts, sleEponStatsOltChannelFCS, 
				sleEponStatsOltChannelInRangeLengthErrors, sleEponStatsOltChannelFrameTooLongErrors, sleEponStatsOltChannelInUnicastPkts, sleEponStatsOltChannelOutUnicastPkts, sleEponStatsOnuPortInOctets, 
				sleEponStatsOnuPortInPkts, sleEponStatsOnuPortInUcastPkts, sleEponStatsOnuPortInBcastPkts, sleEponStatsOnuPortInMcastPkts, sleEponStatsOnuPortOutOctets, 
				sleEponStatsOnuPortOutPkts, sleEponStatsOnuPortOutUcastPkts, sleEponStatsOnuPortOutBcastPkts, sleEponStatsOnuPortOutMcastPkts, sleEponOnuClassificationIndex, 
				sleEponOnuClassificationName, sleEponOnuClassificationTrafficDirection, sleEponOnuClassificationLayer, sleEponOnuClassificationEtherType, sleEponOnuClassificationProtoTypeNum, 
				sleEponOnuClassificationL3Addr, sleEponOnuClassificationL4Num, sleEponVlanOltVlanMode, sleEponVlanOltVlanNestedStack, sleEponVlanOltVlanPrefix, 
				sleEponVlanOltVlanSuffix, sleEponVlanOltVlanTag, sleEponVlanOltVlanEtherType, sleEponVlanOltVlanControlRequest, sleEponVlanOltVlanControlStatus, 
				sleEponVlanOltVlanControlTimer, sleEponVlanOltVlanControlTimeStamp, sleEponVlanOltVlanControlReqResult, sleEponVlanOltVlanControlOltIndex, sleEponVlanOltVlanControlOnuIndex, 
				sleEponVlanOltVlanControlMode, sleEponVlanOltVlanControlNestedStack, sleEponVlanOltVlanControlPrefix, sleEponVlanOltVlanControlSuffix, sleEponVlanOltVlanControlVlanTag, 
				sleEponVlanOltVlanControlEtherType, sleEponVlanOnuVlanUpVlanTag, sleEponVlanOnuVlanUpEtherType, sleEponVlanOnuVlanUpPriority, sleEponVlanOnuVlanDownVlanTag, 
				sleEponVlanOnuVlanDownPriority, sleEponVlanOnuVlanControlRequest, sleEponVlanOnuVlanControlStatus, sleEponVlanOnuVlanControlTimer, sleEponVlanOnuVlanControlTimeStamp, 
				sleEponVlanOnuVlanControlReqResult, sleEponVlanOnuVlanControlOltIndex, sleEponVlanOnuVlanControlOnuIndex, sleEponVlanOnuVlanControlUpVlanTag, sleEponVlanOnuVlanControlUpEtherType, 
				sleEponVlanOnuVlanControlUpPriority, sleEponVlanOnuVlanControlDownPriority, sleEponProfileControlIndex, sleEponOnuControlUpgradePath, sleEponProfileControlSlaBestEffortBandwidth, 
				sleEponProfilePortControlProfileIndex, sleEponProfilePortControlPortIndex, sleEponProfilePortControlDuplex, sleEponOnuClassificationControlL4Num, sleEponVlanOnuVlanControlDownVlanTag, 
				sleEponVlanOnuVlanUpMode, sleEponVlanOnuVlanDownMode, sleEponVlanOnuVlanControlUpMode, sleEponProfileQueueControlBlockSize4, sleEponProfileQueueControlBlockSize5, 
				sleEponProfileQueueControlBlockSize6, sleEponProfileQueueControlBlockSize7, sleEponVlanOnuVlanControlDownMode, sleEponProfileUNIQueueUpMaxBandwidth, sleEponProfileUNIQueueUpMaxBurstSize, 
				sleEponProfileUNIQueueDownMaxBandwidth, sleEponProfileUNIQueueDownMaxBurstSize, sleEponProfileUNIQueueControlRequest, sleEponProfileUNIQueueControlStatus, sleEponProfileUNIQueueControlTimer, 
				sleEponProfileUNIQueueControlTimeStamp, sleEponProfileUNIQueueControlReqResult, sleEponProfileUNIQueueControlProfileIndex, sleEponProfileUNIQueueControlUpMaxBandwidth, sleEponProfileUNIQueueControlUpMaxBurstSize, 
				sleEponProfileUNIQueueControlDownMaxBandwidth, sleEponProfileUNIQueueControlDownMaxBurstSize, sleEponPTimeStatsPortSaveTime, sleEponPTimeStatsPortHourInOctets, sleEponPTimeStatsPortHourOutOctets, 
				sleEponPTimeStatsPortDayInOctets, sleEponPTimeStatsPortDayOutOctets, sleEponPTimeStatsOltSaveTime, sleEponPTimeStatsOltHourInOctets, sleEponPTimeStatsOltHourOutOctets, 
				sleEponPTimeStatsOltDayInOctets, sleEponPTimeStatsOltDayOutOctets, sleEponPTimeStatsOnuSaveTime, sleEponPTimeStatsOnuHourInOctets, sleEponPTimeStatsOnuHourOutOctets, 
				sleEponPTimeStatsOnuDayInOctets, sleEponPTimeStatsOnuDayOutOctets, sleEponPTimeStatsControlRequest, sleEponPTimeStatsControlStatus, sleEponPTimeStatsControlTimer, 
				sleEponPTimeStatsControlTimeStamp, sleEponPTimeStatsControlReqResult, sleEponPTimeStatsServiceActivity, sleEponPTimeStatsControlServiceActivity, sleEponOnuSubscriberCurrentIpAddress, 
				sleEponOnuSubscriberCurrentMacAddress, sleEponOnuSubscriberControlRequest, sleEponOnuSubscriberControlStatus, sleEponOnuSubscriberControlTimer, sleEponOnuSubscriberControlTimeStamp, 
				sleEponOnuSubscriberControlReqResult, sleEponOnuSubscriberControlOltIndex, sleEponOnuSubscriberControlOnuIndex, sleEponOnuSubscriberCurrentPort, sleEponOnuSubscriberHistoryTime, 
				sleEponOnuSubscriberHistoryIpAddress, sleEponOnuSubscriberHistoryMacAddress, sleEponOnuSubscriberHistoryPort, sleEponProfileSubscriberInfoCollection, sleEponProfileControlSubscriberInfoCollection, 
				sleEponOnuSubscriberCurrentTime, sleEponOltOperStatus, sleEponProfileLoopDetectStatus, sleEponProfileLoopDetectBlockTimer, sleEponProfileLoopDetectSendingpacket, 
				sleEponProfileControlLoopDetectStatus, sleEponProfileControlLoopDetectBlockTimer, sleEponProfileControlLoopDetectSendingpacket, sleEponBaseSlaPlatoMaxBandwdith, sleEponBaseDPShapingMaxBandwidth, 
				sleEponBasePortMaxHost, sleEponBaseControlRequest, sleEponBaseControlStatus, sleEponBaseControlTimer, sleEponBaseControlTimeStamp, 
				sleEponBaseControlReqResult, sleEponBaseControlSlaPlatoMaxBandwdith, sleEponBaseControlDPShapingMaxBandwidth, sleEponBaseControlPortMaxHost, sleEponBaseOnuAutoUpgrade, 
				sleEponBaseOnuAutoUpgradeRebootTime, sleEponBaseControlOnuAutoUpgrade, sleEponBaseControlOnuAutoUpgradeRebootTime, sleEponOltFirmwareRev, sleEponFirmwareType, 
				sleEponFirmwareName, sleEponFirmwareControlRequest, sleEponFirmwareControlStatus, sleEponFirmwareControlTimer, sleEponFirmwareControlTimeStamp, 
				sleEponFirmwareControlReqResult, sleEponFirmwareControlName, sleEponFirmwareControlUpgradeMethod, sleEponFirmwareControlUpgradeMode, sleEponFirmwareControlServerAddress, 
				sleEponFirmwareControlUser, sleEponFirmwareControlPasswd, sleEponProfileExtendMtu, sleEponOnuTxPowerOffTimer }
			STATUS current
			DESCRIPTION 
				"Description."
			::= { sleEpon 11 }

		
--  1.3.6.1.4.1.6296.101.20.12
		-- 1.3.6.1.4.1.6296.101.20.12
		sleEponNotificationGroup NOTIFICATION-GROUP
			NOTIFICATIONS { sleEponOltRegModeChanged, sleEponOltStatusChanged, sleEponOnuRegModeChanged, sleEponOnuStatusChanged, sleEponOnuRegistered, 
				sleEponOnuUpgraded, sleEponProfileCreated, sleEponProfileDestroyed, sleEponstatsOltCleared, sleEponStatsOltChannelCleared, 
				sleEponAlarmProfileChanged, sleEponOnuDeregistered, sleEponOnuProfileChanged, sleEponOnuLoopbackProvisioned, sleEponOltProfileChanged, 
				sleEponStatsAllCleared, sleEponProfileVlanCreated, sleEponProfileVlanDestroyed, sleEponProfileVlanProfileChanged, sleEponProfilePortAdminStatusChanged, 
				sleEponProfilePortNegoChanged, sleEponProfilePortSpeedChanged, sleEponProfilePortMaxHostChanged, sleEponProfilePortPvidChanged, sleEponProfilePortRateLimitChanged, 
				sleEponOnuPortReset, sleEponOnuClassificationCreated, sleEponOnuClassificationDestroyed, sleEponProfileClassificationCreated, sleEponProfileClassificationDestroyed, 
				sleEponOltSCChanged, sleEponOltUpgraded, sleEponOltReset, sleEponOnuTxPowerOffChanged, sleEponOnuFdbMacCleared, 
				sleEponProfileExtendMtuChanged, sleEponProfileIgmpChanged, sleEponProfileSTPChanged, sleEponProfileQueueModifyQueueLimit, sleEponProfilePortFlowControlChanged, 
				sleEponVlanOltVlanPrefixChanged, sleEponVlanOltVlanProfileChanged, sleEponProfileDefaultProfileCreated, sleEponProfileUNIQueueModifyQueuePolicy, sleEponPTimeStatsCleared, 
				sleEponPTimeStatsServiceActivityChanged, sleEponOnuSubscriberHistoryOltCleared, sleEponOnuSubscriberHistroyOnuCleared, sleEponProfileQueueModifyQueuePolicy, sleEponOltAttributesChanged, 
				sleEponOnuAttibutesChanged, sleEponProfileModified, sleEponProfilePortDuplexChanged, sleEponProfileLoopDetectChanged, sleEponBaseDefaultBandwidthChanged, 
				sleEponBaseDefaultMaxHost, sleEponVlanOnuVlanProfileChanged, sleEponFirmwareUpgradeProfileChanged, sleEponFirmwareDeleted, sleEponProfileSubscriberChanged, 
				sleEponBaseOnuAutoUpgradeChanged }
			STATUS current
			DESCRIPTION 
				"Description."
			::= { sleEpon 12 }

		
	
	END

--
-- SLE-EPON-MIB.my
--
