-- *****************************************************************************
-- Juniper-DS1-MIB
--
-- Juniper Networks Enterprise MIB
--   IDP MIB
--
-- Copyright (c) 2006 Juniper Networks, Inc.
--   All Rights Reserved.
-- *****************************************************************************
JUNIPER-IDP-MIB DEFINITIONS ::= BEGIN

IMPORTS
    OBJECT-TYPE, MODULE-IDENTITY FROM SNMPv2-SMI
    jnxMibs,jnxTraps FROM JUNIPER-SMI;

-- the Juniper IDP group

jnxIdpMIB MODULE-IDENTITY
    LAST-UPDATED "200605180000Z"
    ORGANIZATION "Juniper Networks, Inc."
    CONTACT-INFO
            "        Juniper Technical Assistance Center
                     Juniper Networks, Inc.
                     1195 N. Mathilda Avenue
                     Sunnyvale, CA 94089
                     E-mail: support@juniper.net"
    DESCRIPTION
            "The Structure of IDP MIBS for Juniper Networks."
    ::= { jnxMibs 9 }

jnxIdpSensor OBJECT IDENTIFIER ::= { jnxIdpMIB 1 }

-- Juniper IDP Objects

jnxIdpSensorCpuUsage OBJECT-TYPE
        SYNTAX  Gauge32 (0..100)
        ACCESS  read-only
        STATUS  current
        DESCRIPTION
             "CPU utilization as a percentage."
        ::= { jnxIdpSensor 1 }

jnxIdpSensorMemUsage OBJECT-TYPE
        SYNTAX  Gauge32  (0..100)
        ACCESS  read-only
        STATUS  mandatory
        DESCRIPTION
             "Memory utilization as a percentage."
        ::= { jnxIdpSensor 2 }

jnxIdpSensorSessAllocated OBJECT-TYPE
        SYNTAX  Gauge32
        ACCESS  read-only
        STATUS  mandatory
        DESCRIPTION
             "Number of sessions currently allocated for this IDP."
        ::= { jnxIdpSensor 3 }

jnxIdpSensorSessMaximum OBJECT-TYPE
        SYNTAX  INTEGER
        ACCESS  read-only
        STATUS  mandatory
        DESCRIPTION
             "Maximum number of sessions supported by this IDP."
        ::= { jnxIdpSensor 4 }

jnxIdpSensorFreeDiskSpace OBJECT-TYPE
        SYNTAX  Gauge32
        UNITS "Megabytes"
        ACCESS  read-only
        STATUS  mandatory
        DESCRIPTION
             "Free disk space available on this IDP."
        ::= { jnxIdpSensor 5 }

jnxIdpSensorCpuThreshold OBJECT-TYPE
        SYNTAX  INTEGER (0..100)
        ACCESS  read-only
        STATUS  current
        DESCRIPTION
             "CPU alert threshold as a percentage."
        ::= { jnxIdpSensor 6 }

jnxIdpSensorMemThreshold OBJECT-TYPE
        SYNTAX  INTEGER  (0..100)
        ACCESS  read-only
        STATUS  mandatory
        DESCRIPTION
             "Memory alert threshold as a percentage."
        ::= { jnxIdpSensor 7 }

jnxIdpSensorSessThreshold OBJECT-TYPE
        SYNTAX  INTEGER (0..100)
        ACCESS  read-only
        STATUS  mandatory
        DESCRIPTION
             "Session alert threshold as a percentage."
        ::= { jnxIdpSensor 8 }

jnxIdpSensorDiskSpaceThreshold OBJECT-TYPE
        SYNTAX  INTEGER (0..100)
        ACCESS  read-only
        STATUS  mandatory
        DESCRIPTION
             "Disk space alert threshold as a percentage."
        ::= { jnxIdpSensor 9 }

jnxIdpTrap           OBJECT IDENTIFIER ::= { jnxTraps 12 }
jnxIdpTrapsPrefix    OBJECT IDENTIFIER ::= { jnxIdpTrap 0 }

jnxIdpSessionCountNotify NOTIFICATION-TYPE
    OBJECTS { jnxIdpSensorSessAllocated,
                           jnxIdpSensorSessThreshold     
    }
    STATUS        current
    DESCRIPTION
            "Session count has exceeded threshold."
    ::= { jnxIdpTrapsPrefix 1 }
    
jnxIdpSessionCountLimitRestored NOTIFICATION-TYPE
    OBJECTS { jnxIdpSensorSessAllocated }
    STATUS        current
    DESCRIPTION
            "Session count has returned to normal."
    ::= { jnxIdpTrapsPrefix 2 }
                          
jnxIdpCPUUtilizationNotify NOTIFICATION-TYPE
    OBJECTS { jnxIdpSensorCpuUsage,
                   jnxIdpSensorCpuThreshold
    }
    STATUS        current
    DESCRIPTION
            "CPU utilization has exceeded threshold."
    ::= { jnxIdpTrapsPrefix 3 }
    
jnxIdpCPUUtilizationLimitRestored NOTIFICATION-TYPE
    OBJECTS { jnxIdpSensorCpuUsage }
    STATUS        current
    DESCRIPTION
            "CPU utilization has returned to normal."
    ::= { jnxIdpTrapsPrefix 4 }

jnxIdpMemoryNotify NOTIFICATION-TYPE
    OBJECTS { jnxIdpSensorMemUsage,
                  jnxIdpSensorMemThreshold
    }
    STATUS        current
    DESCRIPTION
            "RAM memory utilization has exceeded threshold."
    ::= { jnxIdpTrapsPrefix 5 }
    
jnxIdpMemoryLimitRestored NOTIFICATION-TYPE
    OBJECTS { jnxIdpSensorMemUsage }
    STATUS        current
    DESCRIPTION
            "RAM memory utilization has returned to normal."
    ::= { jnxIdpTrapsPrefix 6 }

jnxIdpDiskUtilizationNotify NOTIFICATION-TYPE
    OBJECTS { jnxIdpSensorFreeDiskSpace,
                  jnxIdpSensorDiskSpaceThreshold
    }
    STATUS        current
    DESCRIPTION
            "Hard disk space utilization has exceeded threshold."
    ::= { jnxIdpTrapsPrefix 7 }
    
jnxIdpDiskUtilizationLimitRestored NOTIFICATION-TYPE
    OBJECTS { jnxIdpSensorFreeDiskSpace }
    STATUS        current
    DESCRIPTION
            "Hard disk space utilization has returned to normal."
    ::= { jnxIdpTrapsPrefix 8 }

END
