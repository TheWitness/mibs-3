--
-- SLEV2-Security-MIB.my
-- MIB generated by MG-SOFT Visual MIB Builder Version 3.0 Build 285
-- Friday, February 23, 2007 at 14:19:58
--

	SLEV2-Security-MIB DEFINITIONS ::= BEGIN
 
		IMPORTS
			sleV2Mgmt			
				FROM DASAN-SMI			
			SleControlStatusType, SleControlRequestResultType			
				FROM SLE-TC-MIB			
			OBJECT-GROUP, NOTIFICATION-GROUP			
				FROM SNMPv2-CONF			
			TimeTicks, IpAddress, Integer32, Gauge32, Counter32, 
			Counter64, BITS, OBJECT-TYPE, MODULE-IDENTITY, NOTIFICATION-TYPE			
				FROM SNMPv2-SMI			
			TimeStamp, TEXTUAL-CONVENTION			
				FROM SNMPv2-TC;
	
	
		-- 1.3.6.1.4.1.6296.102.7
		sleV2Security MODULE-IDENTITY 
			LAST-UPDATED "200605051406Z"		-- May 05, 2006 at 14:06 GMT
			ORGANIZATION 
				"Organization."
			CONTACT-INFO 
				"Contact-info."
			DESCRIPTION 
				"Description."
			::= { sleV2Mgmt 7 }

		
	
--
-- Type definitions
--
	
		IntFlowIndex ::= INTEGER (1..1024)

		IntClassIndex ::= INTEGER (1..1024)

		IntPolicyIndex ::= INTEGER (1..1024)

		OctetName ::= OCTET STRING (SIZE (1..64))

		IntIpAddrMask ::= INTEGER (0..32)

		IntProtocolType ::= INTEGER (-1 | 0..255)

		IntL4Port ::= INTEGER (-1 | 0..65535)

		IntIcmpType ::= INTEGER (-1 | 0..255)

		IntIcmpCode ::= INTEGER (-1 | 0..255)

		IntInternetProtocolFlag ::= INTEGER
			{
			nothing(-1),
			tcp(1),
			ucp(2),
			icmp(3)
			}

		IntRulePriority ::= INTEGER
			{
			nothing(-1),
			low(1),
			medium(2),
			high(3),
			highest(4)
			}

		IntFlowClass ::= INTEGER
			{
			nothing(-1),
			flow(1),
			class(2),
			both(4)
			}

		IntInterfaceIndex ::= INTEGER (-1 | 1..512)

		IntFlowOrClass ::= INTEGER
			{
			flow(1),
			class(2)
			}

		IntPermit ::= INTEGER
			{
			deny(1),
			permit(2)
			}

	
--
-- Textual conventions
--
	
		MacAddressMask ::= TEXTUAL-CONVENTION
			STATUS current
			DESCRIPTION 
				"Represents Mac address Mask.
				"
			SYNTAX OCTET STRING (SIZE (6))

	
--
-- Node definitions
--
	
		-- 1.3.6.1.4.1.6296.102.7.1
		sleV2SecurityBase OBJECT IDENTIFIER::= { sleV2Security 1 }

		
		-- 1.3.6.1.4.1.6296.102.7.2
		sleVSecurity4 OBJECT IDENTIFIER::= { sleV2Security 2 }

		
		-- 1.3.6.1.4.1.6296.102.7.2.5
		sleV2SecurityACL OBJECT IDENTIFIER::= { sleVSecurity4 5 }

		
		-- 1.3.6.1.4.1.6296.102.7.2.5.1
		sleV2Security4ACLBase OBJECT IDENTIFIER::= { sleV2SecurityACL 1 }

		
		-- 1.3.6.1.4.1.6296.102.7.2.5.2
		sleV2Security4ACLFlow OBJECT IDENTIFIER::= { sleV2SecurityACL 2 }

		
		-- 1.3.6.1.4.1.6296.102.7.2.5.2.1
		sleV2Security4ACLFlowInfo OBJECT IDENTIFIER::= { sleV2Security4ACLFlow 1 }

		
		-- 1.3.6.1.4.1.6296.102.7.2.5.2.1.1
		sleV2Security4ACLFlowTable OBJECT-TYPE
			SYNTAX SEQUENCE OF SleV2Security4ACLFlowEntry
			MAX-ACCESS not-accessible
			STATUS current
			DESCRIPTION
				"Description."
			::= { sleV2Security4ACLFlowInfo 1 }

		
		-- 1.3.6.1.4.1.6296.102.7.2.5.2.1.1.1
		sleV2Security4ACLFlowEntry OBJECT-TYPE
			SYNTAX SleV2Security4ACLFlowEntry
			MAX-ACCESS not-accessible
			STATUS current
			DESCRIPTION
				"Description."
			INDEX { sleV2Security4ACLFlowIndex }
			::= { sleV2Security4ACLFlowTable 1 }

		
		SleV2Security4ACLFlowEntry ::=
			SEQUENCE { 
				sleV2Security4ACLFlowIndex
					INTEGER,
				sleV2Security4ACLFlowName
					OctetName,
				sleV2Security4ACLFlowSrcIpAddr
					IpAddress,
				sleV2Security4ACLFlowSrcIpAddrMask
					IntIpAddrMask,
				sleV2Security4ACLFlowDstIpAddr
					IpAddress,
				sleV2Security4ACLFlowDstIpAddrMask
					IntIpAddrMask,
				sleV2Security4ACLFlowProtocolType
					IntProtocolType,
				sleV2Security4ACLFlowTcpSrcStartPort
					IntL4Port,
				sleV2Security4ACLFlowTcpSrcEndPort
					IntL4Port,
				sleV2Security4ACLFlowTcpDstStartPort
					IntL4Port,
				sleV2Security4ACLFlowTcpDstEndPort
					IntL4Port,
				sleV2Security4ACLFlowTcpFlag
					BITS,
				sleV2Security4ACLFlowUdpSrcStartPort
					IntL4Port,
				sleV2Security4ACLFlowUdpSrcEndPort
					IntL4Port,
				sleV2Security4ACLFlowUdpDstStartPort
					IntL4Port,
				sleV2Security4ACLFlowUdpDstEndPort
					IntL4Port,
				sleV2Security4ACLFlowIcmpType
					IntIcmpType,
				sleV2Security4ACLFlowIcmpCode
					IntIcmpCode,
				sleV2Security4ACLFlowHdrlen
					INTEGER
			 }

		-- 1.3.6.1.4.1.6296.102.7.2.5.2.1.1.1.1
		sleV2Security4ACLFlowIndex OBJECT-TYPE
			SYNTAX INTEGER (1..1024)
			MAX-ACCESS read-only
			STATUS current
			DESCRIPTION
				"The index of flow"
			::= { sleV2Security4ACLFlowEntry 1 }

		
		-- 1.3.6.1.4.1.6296.102.7.2.5.2.1.1.1.2
		sleV2Security4ACLFlowName OBJECT-TYPE
			SYNTAX OctetName
			MAX-ACCESS read-only
			STATUS current
			DESCRIPTION
				"The name of flow"
			::= { sleV2Security4ACLFlowEntry 2 }

		
		-- 1.3.6.1.4.1.6296.102.7.2.5.2.1.1.1.3
		sleV2Security4ACLFlowSrcIpAddr OBJECT-TYPE
			SYNTAX IpAddress
			MAX-ACCESS read-only
			STATUS current
			DESCRIPTION
				"The IP address to match against the packet's source IP address.
				The value of 0.0.0.0 means any(not set)
				"
			::= { sleV2Security4ACLFlowEntry 3 }

		
		-- 1.3.6.1.4.1.6296.102.7.2.5.2.1.1.1.4
		sleV2Security4ACLFlowSrcIpAddrMask OBJECT-TYPE
			SYNTAX IntIpAddrMask
			MAX-ACCESS read-only
			STATUS current
			DESCRIPTION
				"The mask of source IP address
				The value of -1 means any(not set)
				"
			::= { sleV2Security4ACLFlowEntry 4 }

		
		-- 1.3.6.1.4.1.6296.102.7.2.5.2.1.1.1.5
		sleV2Security4ACLFlowDstIpAddr OBJECT-TYPE
			SYNTAX IpAddress
			MAX-ACCESS read-only
			STATUS current
			DESCRIPTION
				"The IP address to match against the packet's destination IP address.
				The value of 0.0.0.0 means any(not set)
				"
			::= { sleV2Security4ACLFlowEntry 5 }

		
		-- 1.3.6.1.4.1.6296.102.7.2.5.2.1.1.1.6
		sleV2Security4ACLFlowDstIpAddrMask OBJECT-TYPE
			SYNTAX IntIpAddrMask
			MAX-ACCESS read-only
			STATUS current
			DESCRIPTION
				"The mask of destination IP address
				The value of -1 means any(not set)
				"
			::= { sleV2Security4ACLFlowEntry 6 }

		
		-- 1.3.6.1.4.1.6296.102.7.2.5.2.1.1.1.7
		sleV2Security4ACLFlowProtocolType OBJECT-TYPE
			SYNTAX IntProtocolType
			MAX-ACCESS read-only
			STATUS current
			DESCRIPTION
				"The type of IP protocol
				The flat internet protocol is from sleV2QoS4FlowTcpSrcStartPort to sleV2QoS4FlowIcmpCode
				If the value is tcp(6),
				From sleV2QoS4FlowTcpSrcStartPort to sleV2QoS4FlowTcpFlag value is available
				If the value is u¿¡(17),
				From sleV2QoS4FlowUdpSrcStartPort to sleV2QoS4FlowUdpDstEndPort value is available
				If the value is icmp(1),
				The value of sleV2QoS4FlowIcmpType and sleV2QoS4FlowIcmpCode is available
				The value of -1 means any(not set)
				Otherwise, from sleV2QoS4FlowTcpSrcStartPort to sleV2QoS4FlowIcmpCode value is not available
				The value of -1 means any(not set)
				"
			::= { sleV2Security4ACLFlowEntry 7 }

		
		-- 1.3.6.1.4.1.6296.102.7.2.5.2.1.1.1.8
		sleV2Security4ACLFlowTcpSrcStartPort OBJECT-TYPE
			SYNTAX IntL4Port
			MAX-ACCESS read-only
			STATUS current
			DESCRIPTION
				"The start source port in range of source port in TCP packet
				The value of -1 means any(not set)
				"
			::= { sleV2Security4ACLFlowEntry 8 }

		
		-- 1.3.6.1.4.1.6296.102.7.2.5.2.1.1.1.9
		sleV2Security4ACLFlowTcpSrcEndPort OBJECT-TYPE
			SYNTAX IntL4Port
			MAX-ACCESS read-only
			STATUS current
			DESCRIPTION
				"The end source port in range of source port in TCP packet
				The value of -1 means any(not set)
				"
			::= { sleV2Security4ACLFlowEntry 9 }

		
		-- 1.3.6.1.4.1.6296.102.7.2.5.2.1.1.1.10
		sleV2Security4ACLFlowTcpDstStartPort OBJECT-TYPE
			SYNTAX IntL4Port
			MAX-ACCESS read-only
			STATUS current
			DESCRIPTION
				"The start destination port in range of source port in TCP packet. The value of -1 means any(not set)"
			::= { sleV2Security4ACLFlowEntry 10 }

		
		-- 1.3.6.1.4.1.6296.102.7.2.5.2.1.1.1.11
		sleV2Security4ACLFlowTcpDstEndPort OBJECT-TYPE
			SYNTAX IntL4Port
			MAX-ACCESS read-only
			STATUS current
			DESCRIPTION
				"The end destination port in range of destination port in TCP packet. The value of -1 means any(not set)"
			::= { sleV2Security4ACLFlowEntry 11 }

		
		-- 1.3.6.1.4.1.6296.102.7.2.5.2.1.1.1.12
		sleV2Security4ACLFlowTcpFlag OBJECT-TYPE
			SYNTAX BITS
				{
				reserv0(0),
				reserv1(1),
				urg(2),
				ack(3),
				psh(4),
				rst(5),
				syn(6),
				fin(7)
				}
			MAX-ACCESS read-only
			STATUS current
			DESCRIPTION
				"The flag in TCP packet"
			::= { sleV2Security4ACLFlowEntry 12 }

		
		-- 1.3.6.1.4.1.6296.102.7.2.5.2.1.1.1.13
		sleV2Security4ACLFlowUdpSrcStartPort OBJECT-TYPE
			SYNTAX IntL4Port
			MAX-ACCESS read-only
			STATUS current
			DESCRIPTION
				"The start source port in range of source port in UDP packet
				The value of -1 means any(not set)
				"
			::= { sleV2Security4ACLFlowEntry 13 }

		
		-- 1.3.6.1.4.1.6296.102.7.2.5.2.1.1.1.14
		sleV2Security4ACLFlowUdpSrcEndPort OBJECT-TYPE
			SYNTAX IntL4Port
			MAX-ACCESS read-only
			STATUS current
			DESCRIPTION
				"The end source port in range of source port in UDP packet
				The value of -1 means any(not set)
				"
			::= { sleV2Security4ACLFlowEntry 14 }

		
		-- 1.3.6.1.4.1.6296.102.7.2.5.2.1.1.1.15
		sleV2Security4ACLFlowUdpDstStartPort OBJECT-TYPE
			SYNTAX IntL4Port
			MAX-ACCESS read-only
			STATUS current
			DESCRIPTION
				"The start destination port in range of destination port in UDP packet. The value of -1 means any(not set)"
			::= { sleV2Security4ACLFlowEntry 15 }

		
		-- 1.3.6.1.4.1.6296.102.7.2.5.2.1.1.1.16
		sleV2Security4ACLFlowUdpDstEndPort OBJECT-TYPE
			SYNTAX IntL4Port
			MAX-ACCESS read-only
			STATUS current
			DESCRIPTION
				"The end destination port in range of destination port in UDP packet. The value of -1 means any(not set)"
			::= { sleV2Security4ACLFlowEntry 16 }

		
		-- 1.3.6.1.4.1.6296.102.7.2.5.2.1.1.1.17
		sleV2Security4ACLFlowIcmpType OBJECT-TYPE
			SYNTAX IntIcmpType
			MAX-ACCESS read-only
			STATUS current
			DESCRIPTION
				"The type of ICMP message
				The value of -1 means any(not set)
				"
			::= { sleV2Security4ACLFlowEntry 17 }

		
		-- 1.3.6.1.4.1.6296.102.7.2.5.2.1.1.1.18
		sleV2Security4ACLFlowIcmpCode OBJECT-TYPE
			SYNTAX IntIcmpCode
			MAX-ACCESS read-only
			STATUS current
			DESCRIPTION
				"The code of ICMP message
				The value of -1 means any(not set)
				"
			::= { sleV2Security4ACLFlowEntry 18 }

		
		-- 1.3.6.1.4.1.6296.102.7.2.5.2.1.1.1.19
		sleV2Security4ACLFlowHdrlen OBJECT-TYPE
			SYNTAX INTEGER (0 | 1..15)
			MAX-ACCESS read-only
			STATUS current
			DESCRIPTION
				"The IP header length.
				The value of 0 means any(not set)"
			::= { sleV2Security4ACLFlowEntry 19 }

		
		-- 1.3.6.1.4.1.6296.102.7.2.5.2.1.2
		sleV2Security4ACLFlowControl OBJECT IDENTIFIER::= { sleV2Security4ACLFlowInfo 2 }

		
		-- 1.3.6.1.4.1.6296.102.7.2.5.2.1.2.1
		sleV2Security4ACLFlowControlRequest OBJECT-TYPE
			SYNTAX INTEGER
				{
				createFlow(1),
				modifyFlow(2),
				destroyFlow(3),
				destroyAllFlow(4)
				}
			MAX-ACCESS read-write
			STATUS current
			DESCRIPTION
				"The request of a user command"
			::= { sleV2Security4ACLFlowControl 1 }

		
		-- 1.3.6.1.4.1.6296.102.7.2.5.2.1.2.2
		sleV2Security4ACLFlowControlStatus OBJECT-TYPE
			SYNTAX SleControlStatusType
			MAX-ACCESS read-only
			STATUS current
			DESCRIPTION
				"The status of user command"
			::= { sleV2Security4ACLFlowControl 2 }

		
		-- 1.3.6.1.4.1.6296.102.7.2.5.2.1.2.3
		sleV2Security4ACLFlowControlTimer OBJECT-TYPE
			SYNTAX Gauge32
			MAX-ACCESS read-write
			STATUS current
			DESCRIPTION
				"The maximum time for the manager for a long running user command"
			::= { sleV2Security4ACLFlowControl 3 }

		
		-- 1.3.6.1.4.1.6296.102.7.2.5.2.1.2.4
		sleV2Security4ACLFlowControlTimeStamp OBJECT-TYPE
			SYNTAX TimeTicks
			MAX-ACCESS read-only
			STATUS current
			DESCRIPTION
				"The time stamp of the last command(end of command)"
			::= { sleV2Security4ACLFlowControl 4 }

		
		-- 1.3.6.1.4.1.6296.102.7.2.5.2.1.2.5
		sleV2Security4ACLFlowControlReqResult OBJECT-TYPE
			SYNTAX SleControlRequestResultType
			MAX-ACCESS read-only
			STATUS current
			DESCRIPTION
				"The result of the last user command"
			::= { sleV2Security4ACLFlowControl 5 }

		
		-- 1.3.6.1.4.1.6296.102.7.2.5.2.1.2.6
		sleV2Security4ACLFlowControlIndex OBJECT-TYPE
			SYNTAX IntFlowIndex
			MAX-ACCESS read-write
			STATUS current
			DESCRIPTION
				"The index of flow"
			::= { sleV2Security4ACLFlowControl 6 }

		
		-- 1.3.6.1.4.1.6296.102.7.2.5.2.1.2.7
		sleV2Security4ACLFlowControlName OBJECT-TYPE
			SYNTAX OctetName
			MAX-ACCESS read-write
			STATUS current
			DESCRIPTION
				"The name of flow"
			::= { sleV2Security4ACLFlowControl 7 }

		
		-- 1.3.6.1.4.1.6296.102.7.2.5.2.1.2.8
		sleV2Security4ACLFlowControlSrcIpAddr OBJECT-TYPE
			SYNTAX IpAddress
			MAX-ACCESS read-write
			STATUS current
			DESCRIPTION
				"The IP address to match against the packet's source IP address.
				The value of 0.0.0.0 means any(not set)
				"
			::= { sleV2Security4ACLFlowControl 8 }

		
		-- 1.3.6.1.4.1.6296.102.7.2.5.2.1.2.9
		sleV2Security4ACLFlowControlSrcIpAddrMask OBJECT-TYPE
			SYNTAX IntIpAddrMask
			MAX-ACCESS read-write
			STATUS current
			DESCRIPTION
				"The mask of source IP address
				The value of -1 means any(not set)
				"
			::= { sleV2Security4ACLFlowControl 9 }

		
		-- 1.3.6.1.4.1.6296.102.7.2.5.2.1.2.10
		sleV2Security4ACLFlowControlDstIpAddr OBJECT-TYPE
			SYNTAX IpAddress
			MAX-ACCESS read-write
			STATUS current
			DESCRIPTION
				"The IP address to match against the packet's destination IP address.
				The value of 0.0.0.0 means any(not set)
				"
			::= { sleV2Security4ACLFlowControl 10 }

		
		-- 1.3.6.1.4.1.6296.102.7.2.5.2.1.2.11
		sleV2Security4ACLFlowControlDstIpAddrMask OBJECT-TYPE
			SYNTAX IntIpAddrMask
			MAX-ACCESS read-write
			STATUS current
			DESCRIPTION
				"The mask of destination IP address
				The value of -1 means any(not set)
				"
			::= { sleV2Security4ACLFlowControl 11 }

		
		-- 1.3.6.1.4.1.6296.102.7.2.5.2.1.2.12
		sleV2Security4ACLFlowControlProtocolType OBJECT-TYPE
			SYNTAX IntProtocolType
			MAX-ACCESS read-write
			STATUS current
			DESCRIPTION
				"The type of IP protocol
				The flat internet protocol is from sleV2QoS4FlowTcpSrcStartPort to sleV2QoS4FlowIcmpCode
				If the value is tcp(6),
				From sleV2QoS4FlowControlTcpSrcStartPort to sleV2QoS4FlowControlTcpFlag value is available
				If the value is u¿¡(17),
				From sleV2QoS4FlowControlUdpSrcStartPort to sleV2QoS4FlowControlUdpDstEndPort value is available
				If the value is icmp(1),
				The value of sleV2QoS4FlowControlIcmpType and sleV2QoS4FlowControlIcmpCode is available
				The value of -1 means any(not set)
				Otherwise, from sleV2QoS4FlowControlTcpSrcStartPort to sleV2QoS4FlowControlIcmpCode value is not available
				The value of -1 means any(not set)
				"
			::= { sleV2Security4ACLFlowControl 12 }

		
		-- 1.3.6.1.4.1.6296.102.7.2.5.2.1.2.13
		sleV2Security4ACLFlowControlTcpSrcStartPort OBJECT-TYPE
			SYNTAX IntL4Port
			MAX-ACCESS read-write
			STATUS current
			DESCRIPTION
				"The start source port in range of source port in TCP packet
				The value of -1 means any(not set)
				"
			::= { sleV2Security4ACLFlowControl 13 }

		
		-- 1.3.6.1.4.1.6296.102.7.2.5.2.1.2.14
		sleV2Security4ACLFlowControlTcpSrcEndPort OBJECT-TYPE
			SYNTAX IntL4Port
			MAX-ACCESS read-write
			STATUS current
			DESCRIPTION
				"The end source port in range of source port in TCP packet
				The value of -1 means any(not set)
				"
			::= { sleV2Security4ACLFlowControl 14 }

		
		-- 1.3.6.1.4.1.6296.102.7.2.5.2.1.2.15
		sleV2Security4ACLFlowControlTcpDstStartPort OBJECT-TYPE
			SYNTAX IntL4Port
			MAX-ACCESS read-write
			STATUS current
			DESCRIPTION
				"The start destination port in range of source port in TCP packet. The value of -1 means any(not set)"
			::= { sleV2Security4ACLFlowControl 15 }

		
		-- 1.3.6.1.4.1.6296.102.7.2.5.2.1.2.16
		sleV2Security4ACLFlowControlTcpDstEndPort OBJECT-TYPE
			SYNTAX IntL4Port
			MAX-ACCESS read-write
			STATUS current
			DESCRIPTION
				"The end destination port in range of destination port in TCP packet. The value of -1 means any(not set)"
			::= { sleV2Security4ACLFlowControl 16 }

		
		-- 1.3.6.1.4.1.6296.102.7.2.5.2.1.2.17
		sleV2Security4ACLFlowControlTcpFlag OBJECT-TYPE
			SYNTAX BITS
				{
				reserv0(0),
				reserv1(1),
				urg(2),
				ack(3),
				psh(4),
				rst(5),
				syn(6),
				fin(7)
				}
			MAX-ACCESS read-write
			STATUS current
			DESCRIPTION
				"The flag in TCP packet"
			::= { sleV2Security4ACLFlowControl 17 }

		
		-- 1.3.6.1.4.1.6296.102.7.2.5.2.1.2.18
		sleV2Security4ACLFlowControlUdpSrcStartPort OBJECT-TYPE
			SYNTAX IntL4Port
			MAX-ACCESS read-write
			STATUS current
			DESCRIPTION
				"The start source port in range of source port in UDP packet
				The value of -1 means any(not set)
				"
			::= { sleV2Security4ACLFlowControl 18 }

		
		-- 1.3.6.1.4.1.6296.102.7.2.5.2.1.2.19
		sleV2Security4ACLFlowControlUdpSrcEndPort OBJECT-TYPE
			SYNTAX IntL4Port
			MAX-ACCESS read-write
			STATUS current
			DESCRIPTION
				"The end source port in range of source port in UDP packet
				The value of -1 means any(not set)
				"
			::= { sleV2Security4ACLFlowControl 19 }

		
		-- 1.3.6.1.4.1.6296.102.7.2.5.2.1.2.20
		sleV2Security4ACLFlowControlUdpDstStartPort OBJECT-TYPE
			SYNTAX IntL4Port
			MAX-ACCESS read-write
			STATUS current
			DESCRIPTION
				"The start destination port in range of destination port in UDP packet. The value of -1 means any(not set)"
			::= { sleV2Security4ACLFlowControl 20 }

		
		-- 1.3.6.1.4.1.6296.102.7.2.5.2.1.2.21
		sleV2Security4ACLFlowControlUdpDstEndPort OBJECT-TYPE
			SYNTAX IntL4Port
			MAX-ACCESS read-write
			STATUS current
			DESCRIPTION
				"The end destination port in range of destination port in UDP packet. The value of -1 means any(not set)"
			::= { sleV2Security4ACLFlowControl 21 }

		
		-- 1.3.6.1.4.1.6296.102.7.2.5.2.1.2.22
		sleV2Security4ACLFlowControlIcmpType OBJECT-TYPE
			SYNTAX IntIcmpType
			MAX-ACCESS read-write
			STATUS current
			DESCRIPTION
				"The type of ICMP message
				The value of -1 means any(not set)
				"
			::= { sleV2Security4ACLFlowControl 22 }

		
		-- 1.3.6.1.4.1.6296.102.7.2.5.2.1.2.23
		sleV2Security4ACLFlowControlIcmpCode OBJECT-TYPE
			SYNTAX IntIcmpCode
			MAX-ACCESS read-write
			STATUS current
			DESCRIPTION
				"The code of ICMP message
				The value of -1 means any(not set)
				"
			::= { sleV2Security4ACLFlowControl 23 }

		
		-- 1.3.6.1.4.1.6296.102.7.2.5.2.1.2.24
		sleV2Security4ACLFlowControlHdrlen OBJECT-TYPE
			SYNTAX INTEGER (0 | 1..15)
			MAX-ACCESS read-write
			STATUS current
			DESCRIPTION
				"Description."
			::= { sleV2Security4ACLFlowControl 24 }

		
		-- 1.3.6.1.4.1.6296.102.7.2.5.2.1.3
		sleV2Security4ACLFlowNotification OBJECT IDENTIFIER::= { sleV2Security4ACLFlowInfo 3 }

		
		-- 1.3.6.1.4.1.6296.102.7.2.5.2.1.3.1
		sleACLFlowCreated NOTIFICATION-TYPE
			OBJECTS { sleV2Security4ACLFlowControlRequest, sleV2Security4ACLFlowControlTimeStamp, sleV2Security4ACLFlowControlReqResult, sleV2Security4ACLFlowName, sleV2Security4ACLFlowSrcIpAddr, 
				sleV2Security4ACLFlowSrcIpAddrMask, sleV2Security4ACLFlowDstIpAddr, sleV2Security4ACLFlowDstIpAddrMask, sleV2Security4ACLFlowProtocolType, sleV2Security4ACLFlowTcpSrcStartPort, 
				sleV2Security4ACLFlowTcpSrcEndPort, sleV2Security4ACLFlowTcpDstStartPort, sleV2Security4ACLFlowTcpDstEndPort, sleV2Security4ACLFlowTcpFlag, sleV2Security4ACLFlowUdpSrcStartPort, 
				sleV2Security4ACLFlowUdpSrcEndPort, sleV2Security4ACLFlowUdpDstStartPort, sleV2Security4ACLFlowUdpDstEndPort, sleV2Security4ACLFlowIcmpType, sleV2Security4ACLFlowIcmpCode, 
				sleV2Security4ACLFlowHdrlen }
			STATUS current
			DESCRIPTION 
				"Description."
			::= { sleV2Security4ACLFlowNotification 1 }

		
		-- 1.3.6.1.4.1.6296.102.7.2.5.2.1.3.2
		sleACLFlowChanged NOTIFICATION-TYPE
			OBJECTS { sleV2Security4ACLFlowControlRequest, sleV2Security4ACLFlowControlTimeStamp, sleV2Security4ACLFlowControlReqResult, sleV2Security4ACLFlowControlIndex, sleV2Security4ACLFlowSrcIpAddr, 
				sleV2Security4ACLFlowSrcIpAddrMask, sleV2Security4ACLFlowDstIpAddr, sleV2Security4ACLFlowDstIpAddrMask, sleV2Security4ACLFlowProtocolType, sleV2Security4ACLFlowTcpSrcStartPort, 
				sleV2Security4ACLFlowTcpSrcEndPort, sleV2Security4ACLFlowTcpDstStartPort, sleV2Security4ACLFlowTcpDstEndPort, sleV2Security4ACLFlowTcpFlag, sleV2Security4ACLFlowUdpSrcStartPort, 
				sleV2Security4ACLFlowUdpSrcEndPort, sleV2Security4ACLFlowUdpDstStartPort, sleV2Security4ACLFlowUdpDstEndPort, sleV2Security4ACLFlowIcmpType, sleV2Security4ACLFlowIcmpCode, 
				sleV2Security4ACLFlowHdrlen }
			STATUS current
			DESCRIPTION 
				"Description."
			::= { sleV2Security4ACLFlowNotification 2 }

		
		-- 1.3.6.1.4.1.6296.102.7.2.5.2.1.3.3
		sleACLFlowDestroyed NOTIFICATION-TYPE
			OBJECTS { sleV2Security4ACLFlowControlRequest, sleV2Security4ACLFlowControlTimeStamp, sleV2Security4ACLFlowControlReqResult, sleV2Security4ACLFlowControlIndex }
			STATUS current
			DESCRIPTION 
				"Description."
			::= { sleV2Security4ACLFlowNotification 3 }

		
		-- 1.3.6.1.4.1.6296.102.7.2.5.2.1.3.4
		sleACLFlowAllDestroyed NOTIFICATION-TYPE
			OBJECTS { sleV2Security4ACLFlowControlRequest, sleV2Security4ACLFlowControlTimeStamp, sleV2Security4ACLFlowControlReqResult }
			STATUS current
			DESCRIPTION 
				"Description."
			::= { sleV2Security4ACLFlowNotification 4 }

		
		-- 1.3.6.1.4.1.6296.102.7.2.5.2.2
		sleV2Security4ACLFlowClass OBJECT IDENTIFIER::= { sleV2Security4ACLFlow 2 }

		
		-- 1.3.6.1.4.1.6296.102.7.2.5.2.2.1
		sleV2Security4ACLFlowClassTable OBJECT-TYPE
			SYNTAX SEQUENCE OF SleV2Security4ACLFlowClassEntry
			MAX-ACCESS not-accessible
			STATUS current
			DESCRIPTION
				"Description."
			::= { sleV2Security4ACLFlowClass 1 }

		
		-- 1.3.6.1.4.1.6296.102.7.2.5.2.2.1.1
		sleV2Security4ACLFlowClassEntry OBJECT-TYPE
			SYNTAX SleV2Security4ACLFlowClassEntry
			MAX-ACCESS not-accessible
			STATUS current
			DESCRIPTION
				"Description."
			INDEX { sleV2Security4ACLFlowIndex, sleV2Security4ACLFlowClassIndex }
			::= { sleV2Security4ACLFlowClassTable 1 }

		
		SleV2Security4ACLFlowClassEntry ::=
			SEQUENCE { 
				sleV2Security4ACLFlowClassIndex
					IntClassIndex,
				sleV2Security4ACLFlowClassID
					IntClassIndex,
				sleV2Security4ACLFlowClassName
					OctetName
			 }

		-- 1.3.6.1.4.1.6296.102.7.2.5.2.2.1.1.1
		sleV2Security4ACLFlowClassIndex OBJECT-TYPE
			SYNTAX IntClassIndex
			MAX-ACCESS read-only
			STATUS current
			DESCRIPTION
				"The index of the class for the flow"
			::= { sleV2Security4ACLFlowClassEntry 1 }

		
		-- 1.3.6.1.4.1.6296.102.7.2.5.2.2.1.1.2
		sleV2Security4ACLFlowClassID OBJECT-TYPE
			SYNTAX IntClassIndex
			MAX-ACCESS read-only
			STATUS current
			DESCRIPTION
				"The identifier of the class"
			::= { sleV2Security4ACLFlowClassEntry 2 }

		
		-- 1.3.6.1.4.1.6296.102.7.2.5.2.2.1.1.3
		sleV2Security4ACLFlowClassName OBJECT-TYPE
			SYNTAX OctetName
			MAX-ACCESS read-only
			STATUS current
			DESCRIPTION
				"The name of the class"
			::= { sleV2Security4ACLFlowClassEntry 3 }

		
		-- 1.3.6.1.4.1.6296.102.7.2.5.2.3
		sleV2Security4ACLFlowPolicy OBJECT IDENTIFIER::= { sleV2Security4ACLFlow 3 }

		
		-- 1.3.6.1.4.1.6296.102.7.2.5.2.3.1
		sleV2QoS4ACLFlowPolicyTable OBJECT-TYPE
			SYNTAX SEQUENCE OF SleV2QoS4ACLFlowPolicyEntry
			MAX-ACCESS not-accessible
			STATUS current
			DESCRIPTION
				"Description."
			::= { sleV2Security4ACLFlowPolicy 1 }

		
		-- 1.3.6.1.4.1.6296.102.7.2.5.2.3.1.1
		sleV2QoS4ACLFlowPolicyEntry OBJECT-TYPE
			SYNTAX SleV2QoS4ACLFlowPolicyEntry
			MAX-ACCESS not-accessible
			STATUS current
			DESCRIPTION
				"Description."
			INDEX { sleV2Security4ACLFlowIndex, sleV2Security4ACLFlowPolicyIndex }
			::= { sleV2QoS4ACLFlowPolicyTable 1 }

		
		SleV2QoS4ACLFlowPolicyEntry ::=
			SEQUENCE { 
				sleV2Security4ACLFlowPolicyIndex
					IntPolicyIndex,
				sleV2Security4ACLFlowPolicyID
					IntPolicyIndex,
				sleV2Security4ACLFlowPolicyName
					OctetName
			 }

		-- 1.3.6.1.4.1.6296.102.7.2.5.2.3.1.1.1
		sleV2Security4ACLFlowPolicyIndex OBJECT-TYPE
			SYNTAX IntPolicyIndex
			MAX-ACCESS read-only
			STATUS current
			DESCRIPTION
				"The index of the policy for the flow"
			::= { sleV2QoS4ACLFlowPolicyEntry 1 }

		
		-- 1.3.6.1.4.1.6296.102.7.2.5.2.3.1.1.2
		sleV2Security4ACLFlowPolicyID OBJECT-TYPE
			SYNTAX IntPolicyIndex
			MAX-ACCESS read-only
			STATUS current
			DESCRIPTION
				"The identifier of the policy"
			::= { sleV2QoS4ACLFlowPolicyEntry 2 }

		
		-- 1.3.6.1.4.1.6296.102.7.2.5.2.3.1.1.3
		sleV2Security4ACLFlowPolicyName OBJECT-TYPE
			SYNTAX OctetName
			MAX-ACCESS read-only
			STATUS current
			DESCRIPTION
				"The name of the policy"
			::= { sleV2QoS4ACLFlowPolicyEntry 3 }

		
		-- 1.3.6.1.4.1.6296.102.7.2.5.3
		sleV2Security4ACLClass OBJECT IDENTIFIER::= { sleV2SecurityACL 3 }

		
		-- 1.3.6.1.4.1.6296.102.7.2.5.3.1
		sleV2Security4ACLClassInfo OBJECT IDENTIFIER::= { sleV2Security4ACLClass 1 }

		
		-- 1.3.6.1.4.1.6296.102.7.2.5.3.1.1
		sleV2Security4ACLClassTable OBJECT-TYPE
			SYNTAX SEQUENCE OF SleV2Security4ACLClassEntry
			MAX-ACCESS not-accessible
			STATUS current
			DESCRIPTION
				"Description."
			::= { sleV2Security4ACLClassInfo 1 }

		
		-- 1.3.6.1.4.1.6296.102.7.2.5.3.1.1.1
		sleV2Security4ACLClassEntry OBJECT-TYPE
			SYNTAX SleV2Security4ACLClassEntry
			MAX-ACCESS not-accessible
			STATUS current
			DESCRIPTION
				"Description."
			INDEX { sleV2Security4ACLClassIndex }
			::= { sleV2Security4ACLClassTable 1 }

		
		SleV2Security4ACLClassEntry ::=
			SEQUENCE { 
				sleV2Security4ACLClassIndex
					IntClassIndex,
				sleV2Security4ACLClassName
					OctetName,
				sleV2Security4ACLClassFlowCnt
					Counter32
			 }

		-- 1.3.6.1.4.1.6296.102.7.2.5.3.1.1.1.1
		sleV2Security4ACLClassIndex OBJECT-TYPE
			SYNTAX IntClassIndex
			MAX-ACCESS read-only
			STATUS current
			DESCRIPTION
				"The index of class"
			::= { sleV2Security4ACLClassEntry 1 }

		
		-- 1.3.6.1.4.1.6296.102.7.2.5.3.1.1.1.2
		sleV2Security4ACLClassName OBJECT-TYPE
			SYNTAX OctetName
			MAX-ACCESS read-only
			STATUS current
			DESCRIPTION
				"The name of class"
			::= { sleV2Security4ACLClassEntry 2 }

		
		-- 1.3.6.1.4.1.6296.102.7.2.5.3.1.1.1.3
		sleV2Security4ACLClassFlowCnt OBJECT-TYPE
			SYNTAX Counter32
			MAX-ACCESS read-only
			STATUS current
			DESCRIPTION
				"The counter of flow in class"
			::= { sleV2Security4ACLClassEntry 3 }

		
		-- 1.3.6.1.4.1.6296.102.7.2.5.3.1.2
		sleV2Security4ACLClassControl OBJECT IDENTIFIER::= { sleV2Security4ACLClassInfo 2 }

		
		-- 1.3.6.1.4.1.6296.102.7.2.5.3.1.2.1
		sleV2Security4ACLClassControlRequest OBJECT-TYPE
			SYNTAX INTEGER
				{
				createClass(1),
				destroyClass(2),
				destroyAllClass(3)
				}
			MAX-ACCESS read-write
			STATUS current
			DESCRIPTION
				"The request of a user command"
			::= { sleV2Security4ACLClassControl 1 }

		
		-- 1.3.6.1.4.1.6296.102.7.2.5.3.1.2.2
		sleV2Security4ACLClassControlStatus OBJECT-TYPE
			SYNTAX SleControlStatusType
			MAX-ACCESS read-only
			STATUS current
			DESCRIPTION
				"The status of user command"
			::= { sleV2Security4ACLClassControl 2 }

		
		-- 1.3.6.1.4.1.6296.102.7.2.5.3.1.2.3
		sleV2Security4ACLClassControlTimer OBJECT-TYPE
			SYNTAX Gauge32
			MAX-ACCESS read-write
			STATUS current
			DESCRIPTION
				"The maximum time for the manager for a long running user command"
			::= { sleV2Security4ACLClassControl 3 }

		
		-- 1.3.6.1.4.1.6296.102.7.2.5.3.1.2.4
		sleV2Security4ACLClassControlTimeStamp OBJECT-TYPE
			SYNTAX TimeTicks
			MAX-ACCESS read-only
			STATUS current
			DESCRIPTION
				"The time stamp of the last command(end of command)"
			::= { sleV2Security4ACLClassControl 4 }

		
		-- 1.3.6.1.4.1.6296.102.7.2.5.3.1.2.5
		sleV2Security4ACLClassControlReqResult OBJECT-TYPE
			SYNTAX SleControlRequestResultType
			MAX-ACCESS read-only
			STATUS current
			DESCRIPTION
				"The result of the last user command"
			::= { sleV2Security4ACLClassControl 5 }

		
		-- 1.3.6.1.4.1.6296.102.7.2.5.3.1.2.6
		sleV2Security4ACLClassControlIndex OBJECT-TYPE
			SYNTAX IntClassIndex
			MAX-ACCESS read-write
			STATUS current
			DESCRIPTION
				"The index of class"
			::= { sleV2Security4ACLClassControl 6 }

		
		-- 1.3.6.1.4.1.6296.102.7.2.5.3.1.2.7
		sleV2Security4ACLClassControlName OBJECT-TYPE
			SYNTAX OctetName
			MAX-ACCESS read-write
			STATUS current
			DESCRIPTION
				"The name of class"
			::= { sleV2Security4ACLClassControl 7 }

		
		-- 1.3.6.1.4.1.6296.102.7.2.5.3.1.3
		sleV2Security4ACLClassNotification OBJECT IDENTIFIER::= { sleV2Security4ACLClassInfo 3 }

		
		-- 1.3.6.1.4.1.6296.102.7.2.5.3.1.3.1
		sleACLClassCreated NOTIFICATION-TYPE
			OBJECTS { sleV2Security4ACLClassControlRequest, sleV2Security4ACLClassControlTimeStamp, sleV2Security4ACLClassControlReqResult, sleV2Security4ACLFlowClassName }
			STATUS current
			DESCRIPTION 
				"Description."
			::= { sleV2Security4ACLClassNotification 1 }

		
		-- 1.3.6.1.4.1.6296.102.7.2.5.3.1.3.2
		sleACLClassDestroyed NOTIFICATION-TYPE
			OBJECTS { sleV2Security4ACLClassControlRequest, sleV2Security4ACLClassControlTimeStamp, sleV2Security4ACLClassControlReqResult, sleV2Security4ACLClassControlIndex }
			STATUS current
			DESCRIPTION 
				"Description."
			::= { sleV2Security4ACLClassNotification 2 }

		
		-- 1.3.6.1.4.1.6296.102.7.2.5.3.1.3.3
		sleACLClassAllDestroyed NOTIFICATION-TYPE
			OBJECTS { sleV2Security4ACLClassControlRequest, sleV2Security4ACLClassControlTimeStamp, sleV2Security4ACLClassControlReqResult }
			STATUS current
			DESCRIPTION 
				"Description."
			::= { sleV2Security4ACLClassNotification 3 }

		
		-- 1.3.6.1.4.1.6296.102.7.2.5.3.2
		sleV2Security4ACLClassFlow OBJECT IDENTIFIER::= { sleV2Security4ACLClass 2 }

		
		-- 1.3.6.1.4.1.6296.102.7.2.5.3.2.1
		sleV2Security4ACLClassFlowTable OBJECT-TYPE
			SYNTAX SEQUENCE OF SleV2Security4ACLClassFlowEntry
			MAX-ACCESS not-accessible
			STATUS current
			DESCRIPTION
				"Description."
			::= { sleV2Security4ACLClassFlow 1 }

		
		-- 1.3.6.1.4.1.6296.102.7.2.5.3.2.1.1
		sleV2Security4ACLClassFlowEntry OBJECT-TYPE
			SYNTAX SleV2Security4ACLClassFlowEntry
			MAX-ACCESS not-accessible
			STATUS current
			DESCRIPTION
				"Description."
			INDEX { sleV2Security4ACLClassIndex, sleV2Security4ACLClassFlowIndex }
			::= { sleV2Security4ACLClassFlowTable 1 }

		
		SleV2Security4ACLClassFlowEntry ::=
			SEQUENCE { 
				sleV2Security4ACLClassFlowIndex
					IntFlowIndex,
				sleV2Security4ACLClassFlowID
					IntFlowIndex,
				sleV2Security4ACLClassFlowName
					OctetName
			 }

		-- 1.3.6.1.4.1.6296.102.7.2.5.3.2.1.1.1
		sleV2Security4ACLClassFlowIndex OBJECT-TYPE
			SYNTAX IntFlowIndex
			MAX-ACCESS read-only
			STATUS current
			DESCRIPTION
				"The index of flow in class"
			::= { sleV2Security4ACLClassFlowEntry 1 }

		
		-- 1.3.6.1.4.1.6296.102.7.2.5.3.2.1.1.2
		sleV2Security4ACLClassFlowID OBJECT-TYPE
			SYNTAX IntFlowIndex
			MAX-ACCESS read-only
			STATUS current
			DESCRIPTION
				"The identifier of flow"
			::= { sleV2Security4ACLClassFlowEntry 2 }

		
		-- 1.3.6.1.4.1.6296.102.7.2.5.3.2.1.1.3
		sleV2Security4ACLClassFlowName OBJECT-TYPE
			SYNTAX OctetName
			MAX-ACCESS read-only
			STATUS current
			DESCRIPTION
				"Description."
			::= { sleV2Security4ACLClassFlowEntry 3 }

		
		-- 1.3.6.1.4.1.6296.102.7.2.5.3.2.2
		sleV2Security4ACLClassFlowControl OBJECT IDENTIFIER::= { sleV2Security4ACLClassFlow 2 }

		
		-- 1.3.6.1.4.1.6296.102.7.2.5.3.2.2.1
		sleV2Security4ACLClassFlowControlRequest OBJECT-TYPE
			SYNTAX INTEGER
				{
				addFlow(1),
				deleteFlow(2),
				deleteAllFlow(3)
				}
			MAX-ACCESS read-write
			STATUS current
			DESCRIPTION
				"The request of a user command"
			::= { sleV2Security4ACLClassFlowControl 1 }

		
		-- 1.3.6.1.4.1.6296.102.7.2.5.3.2.2.2
		sleV2Security4ACLClassFlowControlStatus OBJECT-TYPE
			SYNTAX SleControlStatusType
			MAX-ACCESS read-only
			STATUS current
			DESCRIPTION
				"The status of user command"
			::= { sleV2Security4ACLClassFlowControl 2 }

		
		-- 1.3.6.1.4.1.6296.102.7.2.5.3.2.2.3
		sleV2Security4ACLClassFlowControlTimer OBJECT-TYPE
			SYNTAX Gauge32
			MAX-ACCESS read-write
			STATUS current
			DESCRIPTION
				"The maximum time for the manager for a long running user command"
			::= { sleV2Security4ACLClassFlowControl 3 }

		
		-- 1.3.6.1.4.1.6296.102.7.2.5.3.2.2.4
		sleV2Security4ACLClassFlowControlTimeStamp OBJECT-TYPE
			SYNTAX TimeTicks
			MAX-ACCESS read-only
			STATUS current
			DESCRIPTION
				"The time stamp of the last command(end of command)"
			::= { sleV2Security4ACLClassFlowControl 4 }

		
		-- 1.3.6.1.4.1.6296.102.7.2.5.3.2.2.5
		sleV2Security4ACLClassFlowControlReqResult OBJECT-TYPE
			SYNTAX SleControlRequestResultType
			MAX-ACCESS read-only
			STATUS current
			DESCRIPTION
				"The result of the last user command"
			::= { sleV2Security4ACLClassFlowControl 5 }

		
		-- 1.3.6.1.4.1.6296.102.7.2.5.3.2.2.6
		sleV2Security4ACLClassFlowControlClassIndex OBJECT-TYPE
			SYNTAX IntClassIndex
			MAX-ACCESS read-write
			STATUS current
			DESCRIPTION
				"The index of class"
			::= { sleV2Security4ACLClassFlowControl 6 }

		
		-- 1.3.6.1.4.1.6296.102.7.2.5.3.2.2.7
		sleV2Security4ACLClassFlowControlFlowIndex OBJECT-TYPE
			SYNTAX IntFlowIndex
			MAX-ACCESS read-write
			STATUS current
			DESCRIPTION
				"The index of flow in this class"
			::= { sleV2Security4ACLClassFlowControl 7 }

		
		-- 1.3.6.1.4.1.6296.102.7.2.5.3.2.2.8
		sleV2Security4ACLClassFlowControlFlowID OBJECT-TYPE
			SYNTAX IntFlowIndex
			MAX-ACCESS read-write
			STATUS current
			DESCRIPTION
				"The index of flow
				Refer to sleV2QoS4FlowIndex
				"
			::= { sleV2Security4ACLClassFlowControl 8 }

		
		-- 1.3.6.1.4.1.6296.102.7.2.5.3.2.3
		sleV2Security4ACLClassFlowNotification OBJECT IDENTIFIER::= { sleV2Security4ACLClassFlow 3 }

		
		-- 1.3.6.1.4.1.6296.102.7.2.5.3.2.3.1
		sleACLClassFlowAdded NOTIFICATION-TYPE
			OBJECTS { sleV2Security4ACLClassFlowControlRequest, sleV2Security4ACLClassFlowControlTimeStamp, sleV2Security4ACLClassFlowControlReqResult, sleV2Security4ACLClassFlowControlClassIndex, sleV2Security4ACLClassFlowID
				 }
			STATUS current
			DESCRIPTION 
				"Description."
			::= { sleV2Security4ACLClassFlowNotification 1 }

		
		-- 1.3.6.1.4.1.6296.102.7.2.5.3.2.3.2
		sleACLClassFlowDeleted NOTIFICATION-TYPE
			OBJECTS { sleV2Security4ACLClassFlowControlRequest, sleV2Security4ACLClassFlowControlTimeStamp, sleV2Security4ACLClassFlowControlReqResult, sleV2Security4ACLClassFlowControlClassIndex, sleV2Security4ACLClassFlowControlFlowIndex
				 }
			STATUS current
			DESCRIPTION 
				"Description."
			::= { sleV2Security4ACLClassFlowNotification 2 }

		
		-- 1.3.6.1.4.1.6296.102.7.2.5.3.2.3.3
		sleACLClassFlowAllDeleted NOTIFICATION-TYPE
			OBJECTS { sleV2Security4ACLClassFlowControlRequest, sleV2Security4ACLClassFlowControlTimeStamp, sleV2Security4ACLClassFlowControlReqResult, sleV2Security4ACLClassFlowControlClassIndex }
			STATUS current
			DESCRIPTION 
				"Description."
			::= { sleV2Security4ACLClassFlowNotification 3 }

		
		-- 1.3.6.1.4.1.6296.102.7.2.5.3.3
		sleV2Security4ACLClassPolicy OBJECT IDENTIFIER::= { sleV2Security4ACLClass 3 }

		
		-- 1.3.6.1.4.1.6296.102.7.2.5.3.3.1
		sleV2Security4ACLClassPolicyTable OBJECT-TYPE
			SYNTAX SEQUENCE OF SleV2Security4ACLClassPolicyEntry
			MAX-ACCESS not-accessible
			STATUS current
			DESCRIPTION
				"Description."
			::= { sleV2Security4ACLClassPolicy 1 }

		
		-- 1.3.6.1.4.1.6296.102.7.2.5.3.3.1.1
		sleV2Security4ACLClassPolicyEntry OBJECT-TYPE
			SYNTAX SleV2Security4ACLClassPolicyEntry
			MAX-ACCESS not-accessible
			STATUS current
			DESCRIPTION
				"Description."
			INDEX { sleV2Security4ACLClassIndex, sleV2Security4ACLClassPolicyIndex }
			::= { sleV2Security4ACLClassPolicyTable 1 }

		
		SleV2Security4ACLClassPolicyEntry ::=
			SEQUENCE { 
				sleV2Security4ACLClassPolicyIndex
					IntPolicyIndex,
				sleV2Security4ACLClassPolicyID
					IntPolicyIndex,
				sleV2Security4ACLClassPolicyName
					OctetName
			 }

		-- 1.3.6.1.4.1.6296.102.7.2.5.3.3.1.1.1
		sleV2Security4ACLClassPolicyIndex OBJECT-TYPE
			SYNTAX IntPolicyIndex
			MAX-ACCESS read-only
			STATUS current
			DESCRIPTION
				"The index of the policy for the class"
			::= { sleV2Security4ACLClassPolicyEntry 1 }

		
		-- 1.3.6.1.4.1.6296.102.7.2.5.3.3.1.1.2
		sleV2Security4ACLClassPolicyID OBJECT-TYPE
			SYNTAX IntPolicyIndex
			MAX-ACCESS read-only
			STATUS current
			DESCRIPTION
				"The identifier of the policy"
			::= { sleV2Security4ACLClassPolicyEntry 2 }

		
		-- 1.3.6.1.4.1.6296.102.7.2.5.3.3.1.1.3
		sleV2Security4ACLClassPolicyName OBJECT-TYPE
			SYNTAX OctetName
			MAX-ACCESS read-only
			STATUS current
			DESCRIPTION
				"The name of the policy"
			::= { sleV2Security4ACLClassPolicyEntry 3 }

		
		-- 1.3.6.1.4.1.6296.102.7.2.5.4
		sleV2Security4ACLPolicy OBJECT IDENTIFIER::= { sleV2SecurityACL 4 }

		
		-- 1.3.6.1.4.1.6296.102.7.2.5.4.1
		sleV2Security4ACLPolicyInfo OBJECT IDENTIFIER::= { sleV2Security4ACLPolicy 1 }

		
		-- 1.3.6.1.4.1.6296.102.7.2.5.4.1.1
		sleV2Security4ACLPolicyTable OBJECT-TYPE
			SYNTAX SEQUENCE OF SleV2Security4ACLPolicyEntry
			MAX-ACCESS not-accessible
			STATUS current
			DESCRIPTION
				"Description."
			::= { sleV2Security4ACLPolicyInfo 1 }

		
		-- 1.3.6.1.4.1.6296.102.7.2.5.4.1.1.1
		sleV2Security4ACLPolicyEntry OBJECT-TYPE
			SYNTAX SleV2Security4ACLPolicyEntry
			MAX-ACCESS not-accessible
			STATUS current
			DESCRIPTION
				"Description."
			INDEX { sleV2Security4ACLPolicyIndex }
			::= { sleV2Security4ACLPolicyTable 1 }

		
		SleV2Security4ACLPolicyEntry ::=
			SEQUENCE { 
				sleV2Security4ACLPolicyIndex
					IntPolicyIndex,
				sleV2Security4ACLPolicyName
					OctetName,
				sleV2Security4ACLPolicyFlowCnt
					Integer32,
				sleV2Security4ACLPolicyClassCnt
					Integer32,
				sleV2Security4ACLPolicyPriority
					INTEGER,
				sleV2Security4ACLPolicyMatchFlag
					IntPermit,
				sleV2Security4ACLPolicyNomatchFlag
					IntPermit
			 }

		-- 1.3.6.1.4.1.6296.102.7.2.5.4.1.1.1.1
		sleV2Security4ACLPolicyIndex OBJECT-TYPE
			SYNTAX IntPolicyIndex
			MAX-ACCESS read-only
			STATUS current
			DESCRIPTION
				"The index of policy"
			::= { sleV2Security4ACLPolicyEntry 1 }

		
		-- 1.3.6.1.4.1.6296.102.7.2.5.4.1.1.1.2
		sleV2Security4ACLPolicyName OBJECT-TYPE
			SYNTAX OctetName
			MAX-ACCESS read-only
			STATUS current
			DESCRIPTION
				"The name of policy"
			::= { sleV2Security4ACLPolicyEntry 2 }

		
		-- 1.3.6.1.4.1.6296.102.7.2.5.4.1.1.1.3
		sleV2Security4ACLPolicyFlowCnt OBJECT-TYPE
			SYNTAX Integer32
			MAX-ACCESS read-only
			STATUS current
			DESCRIPTION
				"The counter of flow that was included to policy"
			::= { sleV2Security4ACLPolicyEntry 3 }

		
		-- 1.3.6.1.4.1.6296.102.7.2.5.4.1.1.1.4
		sleV2Security4ACLPolicyClassCnt OBJECT-TYPE
			SYNTAX Integer32
			MAX-ACCESS read-only
			STATUS current
			DESCRIPTION
				"The counter of class that was included to policy"
			::= { sleV2Security4ACLPolicyEntry 4 }

		
		-- 1.3.6.1.4.1.6296.102.7.2.5.4.1.1.1.5
		sleV2Security4ACLPolicyPriority OBJECT-TYPE
			SYNTAX INTEGER
				{
				low(1),
				medium(2),
				high(3),
				highest(4)
				}
			MAX-ACCESS read-only
			STATUS current
			DESCRIPTION
				"The priority of the policy
				
				low : default value
				"
			::= { sleV2Security4ACLPolicyEntry 5 }

		
		-- 1.3.6.1.4.1.6296.102.7.2.5.4.1.1.1.6
		sleV2Security4ACLPolicyMatchFlag OBJECT-TYPE
			SYNTAX IntPermit
			MAX-ACCESS read-only
			STATUS current
			DESCRIPTION
				"The action to be apply for matched packets.
				bit 0: deny the matched packets
				bit 1: mirror the matched packets
				bit 2: copy to CPU
				bit 3: set 802.1p value to ToS precedence 
				bit 4: set ToS precedence to 802.1p value
				bit 5 : set 802.1p value from flow
				bit 6 : set TaoS precedence from flow
				"
			::= { sleV2Security4ACLPolicyEntry 6 }

		
		-- 1.3.6.1.4.1.6296.102.7.2.5.4.1.1.1.7
		sleV2Security4ACLPolicyNomatchFlag OBJECT-TYPE
			SYNTAX IntPermit
			MAX-ACCESS read-only
			STATUS current
			DESCRIPTION
				"The action to be apply for matched packets.
				bit 0: deny the nomatched packets
				bit 1: mirror the nomatched packets
				bit 2: copy to CPU
				bit 3: set 802.1p value to ToS precedence 
				bit 4: set ToS precedence to 802.1p value
				bit 5 : set 802.1p value from flow
				bit 6 : set TaoS precedence from flow
				"
			::= { sleV2Security4ACLPolicyEntry 7 }

		
		-- 1.3.6.1.4.1.6296.102.7.2.5.4.1.2
		sleV2Security4ACLPolicyControl OBJECT IDENTIFIER::= { sleV2Security4ACLPolicyInfo 2 }

		
		-- 1.3.6.1.4.1.6296.102.7.2.5.4.1.2.1
		sleV2Security4ACLPolicyControlRequest OBJECT-TYPE
			SYNTAX INTEGER
				{
				createPolicy(1),
				setPolicyInfo(2),
				setMatchAction(3),
				setNomatchAction(4),
				destroyPolicy(5)
				}
			MAX-ACCESS read-write
			STATUS current
			DESCRIPTION
				"The request of a user command"
			::= { sleV2Security4ACLPolicyControl 1 }

		
		-- 1.3.6.1.4.1.6296.102.7.2.5.4.1.2.2
		sleV2Security4ACLPolicyControlStatus OBJECT-TYPE
			SYNTAX SleControlStatusType
			MAX-ACCESS read-only
			STATUS current
			DESCRIPTION
				"The status of user command"
			::= { sleV2Security4ACLPolicyControl 2 }

		
		-- 1.3.6.1.4.1.6296.102.7.2.5.4.1.2.3
		sleV2Security4ACLPolicyControlTimer OBJECT-TYPE
			SYNTAX Gauge32
			MAX-ACCESS read-write
			STATUS current
			DESCRIPTION
				"The maximum time for the manager for a long running user command"
			::= { sleV2Security4ACLPolicyControl 3 }

		
		-- 1.3.6.1.4.1.6296.102.7.2.5.4.1.2.4
		sleV2Security4ACLPolicyControlTimeStamp OBJECT-TYPE
			SYNTAX TimeTicks
			MAX-ACCESS read-only
			STATUS current
			DESCRIPTION
				"The time stamp of the last command(end of command)"
			::= { sleV2Security4ACLPolicyControl 4 }

		
		-- 1.3.6.1.4.1.6296.102.7.2.5.4.1.2.5
		sleV2Security4ACLPolicyControlReqResult OBJECT-TYPE
			SYNTAX SleControlRequestResultType
			MAX-ACCESS read-only
			STATUS current
			DESCRIPTION
				"The result of the last user command"
			::= { sleV2Security4ACLPolicyControl 5 }

		
		-- 1.3.6.1.4.1.6296.102.7.2.5.4.1.2.6
		sleV2Security4ACLPolicyControlIndex OBJECT-TYPE
			SYNTAX IntPolicyIndex
			MAX-ACCESS read-write
			STATUS current
			DESCRIPTION
				"The index of policy"
			::= { sleV2Security4ACLPolicyControl 6 }

		
		-- 1.3.6.1.4.1.6296.102.7.2.5.4.1.2.7
		sleV2Security4ACLPolicyControlName OBJECT-TYPE
			SYNTAX OctetName
			MAX-ACCESS read-write
			STATUS current
			DESCRIPTION
				"The name of policy"
			::= { sleV2Security4ACLPolicyControl 7 }

		
		-- 1.3.6.1.4.1.6296.102.7.2.5.4.1.2.8
		sleV2Security4ACLPolicyControlPriority OBJECT-TYPE
			SYNTAX IntRulePriority
			MAX-ACCESS read-write
			STATUS current
			DESCRIPTION
				"The priority of the policy
				
				low : default
				"
			::= { sleV2Security4ACLPolicyControl 8 }

		
		-- 1.3.6.1.4.1.6296.102.7.2.5.4.1.2.9
		sleV2Security4ACLPolicyControlMatchFlag OBJECT-TYPE
			SYNTAX IntPermit
			MAX-ACCESS read-write
			STATUS current
			DESCRIPTION
				"The action to be apply for matched packets.
				bit 0: deny the matched packets
				bit 1: mirror the matched packets
				bit 2: copy to CPU
				bit 3: set 802.1p value to ToS precedence 
				bit 4: set ToS precedence to 802.1p value
				bit 5 : set 802.1p value from flow
				bit 6 : set TaoS precedence from flow
				"
			::= { sleV2Security4ACLPolicyControl 9 }

		
		-- 1.3.6.1.4.1.6296.102.7.2.5.4.1.2.10
		sleV2Security4ACLPolicyControlNomatchFlag OBJECT-TYPE
			SYNTAX IntPermit
			MAX-ACCESS read-write
			STATUS current
			DESCRIPTION
				"The action to be apply for matched packets.
				bit 0: deny the nomatched packets
				bit 1: mirror the nomatched packets
				bit 2: copy to CPU
				bit 3: set 802.1p value to ToS precedence 
				bit 4: set ToS precedence to 802.1p value
				bit 5 : set 802.1p value from flow
				bit 6 : set TaoS precedence from flow
				"
			::= { sleV2Security4ACLPolicyControl 10 }

		
		-- 1.3.6.1.4.1.6296.102.7.2.5.4.1.3
		sleV2Security4ACLPolicyNotification OBJECT IDENTIFIER::= { sleV2Security4ACLPolicyInfo 3 }

		
		-- 1.3.6.1.4.1.6296.102.7.2.5.4.1.3.1
		sleACLPolicyCreated NOTIFICATION-TYPE
			OBJECTS { sleV2Security4ACLPolicyControlRequest, sleV2Security4ACLPolicyControlTimeStamp, sleV2Security4ACLPolicyControlReqResult, sleV2Security4ACLClassPolicyName, sleV2Security4ACLPolicyPriority, 
				sleV2Security4ACLPolicyMatchFlag, sleV2Security4ACLPolicyNomatchFlag }
			STATUS current
			DESCRIPTION 
				"Description."
			::= { sleV2Security4ACLPolicyNotification 1 }

		
		-- 1.3.6.1.4.1.6296.102.7.2.5.4.1.3.2
		sleACLPolicyInfoChanged NOTIFICATION-TYPE
			OBJECTS { sleV2Security4ACLPolicyControlRequest, sleV2Security4ACLPolicyControlTimeStamp, sleV2Security4ACLPolicyControlReqResult, sleV2Security4ACLPolicyPriority }
			STATUS current
			DESCRIPTION 
				"Description."
			::= { sleV2Security4ACLPolicyNotification 2 }

		
		-- 1.3.6.1.4.1.6296.102.7.2.5.4.1.3.3
		sleACLPolicyMatchActionChanged NOTIFICATION-TYPE
			OBJECTS { sleV2Security4ACLPolicyControlRequest, sleV2Security4ACLPolicyControlTimeStamp, sleV2Security4ACLPolicyControlReqResult, sleV2Security4ACLPolicyMatchFlag }
			STATUS current
			DESCRIPTION 
				"Description."
			::= { sleV2Security4ACLPolicyNotification 3 }

		
		-- 1.3.6.1.4.1.6296.102.7.2.5.4.1.3.4
		sleACLPolicyNomatchActionChanged NOTIFICATION-TYPE
			OBJECTS { sleV2Security4ACLPolicyControlRequest, sleV2Security4ACLPolicyControlTimeStamp, sleV2Security4ACLPolicyControlReqResult, sleV2Security4ACLPolicyNomatchFlag }
			STATUS current
			DESCRIPTION 
				"Description."
			::= { sleV2Security4ACLPolicyNotification 4 }

		
		-- 1.3.6.1.4.1.6296.102.7.2.5.4.1.3.5
		sleACLPolicyDestroyed NOTIFICATION-TYPE
			OBJECTS { sleV2Security4ACLPolicyControlRequest, sleV2Security4ACLPolicyControlTimeStamp, sleV2Security4ACLPolicyControlReqResult, sleV2Security4ACLPolicyControlIndex }
			STATUS current
			DESCRIPTION 
				"Description."
			::= { sleV2Security4ACLPolicyNotification 5 }

		
		-- 1.3.6.1.4.1.6296.102.7.2.5.4.2
		sleV2Security4ACLPolicyFlowClass OBJECT IDENTIFIER::= { sleV2Security4ACLPolicy 2 }

		
		-- 1.3.6.1.4.1.6296.102.7.2.5.4.2.1
		sleV2Security4ACLPolicyFlowClassTable OBJECT-TYPE
			SYNTAX SEQUENCE OF SleV2Security4ACLPolicyFlowClassEntry
			MAX-ACCESS not-accessible
			STATUS current
			DESCRIPTION
				"Description."
			::= { sleV2Security4ACLPolicyFlowClass 1 }

		
		-- 1.3.6.1.4.1.6296.102.7.2.5.4.2.1.1
		sleV2Security4ACLPolicyFlowClassEntry OBJECT-TYPE
			SYNTAX SleV2Security4ACLPolicyFlowClassEntry
			MAX-ACCESS not-accessible
			STATUS current
			DESCRIPTION
				"Description."
			INDEX { sleV2Security4ACLPolicyIndex, sleV2Security4ACLPolicyFlowClassIndex }
			::= { sleV2Security4ACLPolicyFlowClassTable 1 }

		
		SleV2Security4ACLPolicyFlowClassEntry ::=
			SEQUENCE { 
				sleV2Security4ACLPolicyFlowClassIndex
					IntFlowIndex,
				sleV2Security4ACLPolicyFlowClassType
					IntFlowOrClass,
				sleV2Security4ACLPolicyFlowClassID
					IntFlowIndex,
				sleV2Security4ACLPolicyFlowClassName
					OctetName
			 }

		-- 1.3.6.1.4.1.6296.102.7.2.5.4.2.1.1.1
		sleV2Security4ACLPolicyFlowClassIndex OBJECT-TYPE
			SYNTAX IntFlowIndex
			MAX-ACCESS read-only
			STATUS current
			DESCRIPTION
				"The index of flow or class in policy"
			::= { sleV2Security4ACLPolicyFlowClassEntry 1 }

		
		-- 1.3.6.1.4.1.6296.102.7.2.5.4.2.1.1.2
		sleV2Security4ACLPolicyFlowClassType OBJECT-TYPE
			SYNTAX IntFlowOrClass
			MAX-ACCESS read-only
			STATUS current
			DESCRIPTION
				"The flag about flow or class"
			::= { sleV2Security4ACLPolicyFlowClassEntry 2 }

		
		-- 1.3.6.1.4.1.6296.102.7.2.5.4.2.1.1.3
		sleV2Security4ACLPolicyFlowClassID OBJECT-TYPE
			SYNTAX IntFlowIndex
			MAX-ACCESS read-only
			STATUS current
			DESCRIPTION
				"The identifier of class or flow"
			::= { sleV2Security4ACLPolicyFlowClassEntry 3 }

		
		-- 1.3.6.1.4.1.6296.102.7.2.5.4.2.1.1.4
		sleV2Security4ACLPolicyFlowClassName OBJECT-TYPE
			SYNTAX OctetName
			MAX-ACCESS read-only
			STATUS current
			DESCRIPTION
				"Description."
			::= { sleV2Security4ACLPolicyFlowClassEntry 4 }

		
		-- 1.3.6.1.4.1.6296.102.7.2.5.4.2.2
		sleV2Security4ACLPolicyFlowClassControl OBJECT IDENTIFIER::= { sleV2Security4ACLPolicyFlowClass 2 }

		
		-- 1.3.6.1.4.1.6296.102.7.2.5.4.2.2.1
		sleV2Security4ACLPolicyFlowClassControlRequest OBJECT-TYPE
			SYNTAX INTEGER
				{
				addFlowClass(1),
				deleteFlowClass(2),
				deleteAllFlow(3),
				deleteAllClass(4),
				deleteAllFlowClass(5)
				}
			MAX-ACCESS read-write
			STATUS current
			DESCRIPTION
				"The request of a user command"
			::= { sleV2Security4ACLPolicyFlowClassControl 1 }

		
		-- 1.3.6.1.4.1.6296.102.7.2.5.4.2.2.2
		sleV2Security4ACLPolicyFlowClassControlStatus OBJECT-TYPE
			SYNTAX SleControlStatusType
			MAX-ACCESS read-write
			STATUS current
			DESCRIPTION
				"The status of user command"
			::= { sleV2Security4ACLPolicyFlowClassControl 2 }

		
		-- 1.3.6.1.4.1.6296.102.7.2.5.4.2.2.3
		sleV2Security4ACLPolicyFlowClassControlTimer OBJECT-TYPE
			SYNTAX Gauge32
			MAX-ACCESS read-write
			STATUS current
			DESCRIPTION
				"The maximum time for the manager for a long running user command"
			::= { sleV2Security4ACLPolicyFlowClassControl 3 }

		
		-- 1.3.6.1.4.1.6296.102.7.2.5.4.2.2.4
		sleV2Security4ACLPolicyFlowClassControlTimeStamp OBJECT-TYPE
			SYNTAX TimeTicks
			MAX-ACCESS read-write
			STATUS current
			DESCRIPTION
				"The time stamp of the last command(end of command)"
			::= { sleV2Security4ACLPolicyFlowClassControl 4 }

		
		-- 1.3.6.1.4.1.6296.102.7.2.5.4.2.2.5
		sleV2Security4ACLPolicyFlowClassControlReqResult OBJECT-TYPE
			SYNTAX SleControlRequestResultType
			MAX-ACCESS read-write
			STATUS current
			DESCRIPTION
				"The result of the last user command"
			::= { sleV2Security4ACLPolicyFlowClassControl 5 }

		
		-- 1.3.6.1.4.1.6296.102.7.2.5.4.2.2.6
		sleV2Security4ACLPolicyFlowClassControlPolicyIndex OBJECT-TYPE
			SYNTAX IntPolicyIndex
			MAX-ACCESS read-write
			STATUS current
			DESCRIPTION
				"The index of Policy"
			::= { sleV2Security4ACLPolicyFlowClassControl 6 }

		
		-- 1.3.6.1.4.1.6296.102.7.2.5.4.2.2.7
		sleV2Security4ACLPolicyFlowClassControlIndex OBJECT-TYPE
			SYNTAX IntFlowIndex
			MAX-ACCESS read-write
			STATUS current
			DESCRIPTION
				"The index of flow or class in this policy"
			::= { sleV2Security4ACLPolicyFlowClassControl 7 }

		
		-- 1.3.6.1.4.1.6296.102.7.2.5.4.2.2.8
		sleV2Security4ACLPolicyFlowClassControlType OBJECT-TYPE
			SYNTAX IntFlowOrClass
			MAX-ACCESS read-write
			STATUS current
			DESCRIPTION
				"The type of flow or class"
			::= { sleV2Security4ACLPolicyFlowClassControl 8 }

		
		-- 1.3.6.1.4.1.6296.102.7.2.5.4.2.2.9
		sleV2Security4ACLPolicyFlowClassControlFlowID OBJECT-TYPE
			SYNTAX IntFlowIndex
			MAX-ACCESS read-write
			STATUS current
			DESCRIPTION
				"The index of flow
				Available according to sleV2QoS4PolicyFlowClassControlType.
				"
			::= { sleV2Security4ACLPolicyFlowClassControl 9 }

		
		-- 1.3.6.1.4.1.6296.102.7.2.5.4.2.2.10
		sleV2Security4ACLPolicyFlowClassControlClassID OBJECT-TYPE
			SYNTAX IntClassIndex
			MAX-ACCESS read-write
			STATUS current
			DESCRIPTION
				"The index of class
				Available according to sleV2QoS4PolicyFlowClassControlType.
				"
			::= { sleV2Security4ACLPolicyFlowClassControl 10 }

		
		-- 1.3.6.1.4.1.6296.102.7.2.5.4.2.3
		sleV2Security4ACLPolicyFlowClassNotification OBJECT IDENTIFIER::= { sleV2Security4ACLPolicyFlowClass 3 }

		
		-- 1.3.6.1.4.1.6296.102.7.2.5.4.2.3.1
		sleACLPolicyFlowAdded NOTIFICATION-TYPE
			OBJECTS { sleV2Security4ACLPolicyFlowClassControlRequest, sleV2Security4ACLPolicyFlowClassControlTimeStamp, sleV2Security4ACLPolicyFlowClassControlReqResult, sleV2Security4ACLPolicyFlowClassType, sleV2Security4ACLPolicyFlowClassID
				 }
			STATUS current
			DESCRIPTION 
				"Description."
			::= { sleV2Security4ACLPolicyFlowClassNotification 1 }

		
		-- 1.3.6.1.4.1.6296.102.7.2.5.4.2.3.2
		sleACLPolicyFlowDeleted NOTIFICATION-TYPE
			OBJECTS { sleV2Security4ACLPolicyFlowClassControlRequest, sleV2Security4ACLPolicyFlowClassControlTimeStamp, sleV2Security4ACLPolicyFlowClassControlReqResult, sleV2Security4ACLPolicyFlowClassControlPolicyIndex, sleV2Security4ACLPolicyFlowClassControlIndex
				 }
			STATUS current
			DESCRIPTION 
				"Description."
			::= { sleV2Security4ACLPolicyFlowClassNotification 2 }

		
		-- 1.3.6.1.4.1.6296.102.7.2.5.4.2.3.3
		sleACLPolicyAllFlowDeleted NOTIFICATION-TYPE
			OBJECTS { sleV2Security4ACLPolicyFlowClassControlRequest, sleV2Security4ACLPolicyFlowClassControlTimeStamp, sleV2Security4ACLPolicyFlowClassControlReqResult, sleV2Security4ACLPolicyFlowClassControlPolicyIndex }
			STATUS current
			DESCRIPTION 
				"Description."
			::= { sleV2Security4ACLPolicyFlowClassNotification 3 }

		
		-- 1.3.6.1.4.1.6296.102.7.2.5.4.2.3.4
		sleACLPolicyAllClassDeleted NOTIFICATION-TYPE
			OBJECTS { sleV2Security4ACLPolicyFlowClassControlRequest, sleV2Security4ACLPolicyFlowClassControlTimeStamp, sleV2Security4ACLPolicyFlowClassControlReqResult, sleV2Security4ACLPolicyFlowClassControlPolicyIndex }
			STATUS current
			DESCRIPTION 
				"Description."
			::= { sleV2Security4ACLPolicyFlowClassNotification 4 }

		
		-- 1.3.6.1.4.1.6296.102.7.2.5.4.2.3.5
		sleACLPolicyAllFlowClassDeleted NOTIFICATION-TYPE
			OBJECTS { sleV2Security4ACLPolicyFlowClassControlRequest, sleV2Security4ACLPolicyFlowClassControlTimeStamp, sleV2Security4ACLPolicyFlowClassControlReqResult, sleV2Security4ACLPolicyFlowClassControlPolicyIndex }
			STATUS current
			DESCRIPTION 
				"Description."
			::= { sleV2Security4ACLPolicyFlowClassNotification 5 }

		
		-- 1.3.6.1.4.1.6296.102.7.2.6
		sleV2SecuritySACL OBJECT IDENTIFIER::= { sleVSecurity4 6 }

		
		-- 1.3.6.1.4.1.6296.102.7.2.6.1
		sleV2SecuritySACLTable OBJECT-TYPE
			SYNTAX SEQUENCE OF SleV2SecuritySACLEntry
			MAX-ACCESS not-accessible
			STATUS current
			DESCRIPTION
				"Description."
			::= { sleV2SecuritySACL 1 }

		
		-- 1.3.6.1.4.1.6296.102.7.2.6.1.1
		sleV2SecuritySACLEntry OBJECT-TYPE
			SYNTAX SleV2SecuritySACLEntry
			MAX-ACCESS not-accessible
			STATUS current
			DESCRIPTION
				"Description."
			INDEX { sleV2SecuritySACLName }
			::= { sleV2SecuritySACLTable 1 }

		
		SleV2SecuritySACLEntry ::=
			SEQUENCE { 
				sleV2SecuritySACLName
					OctetName,
				sleV2SecuritySACLSrcIpaddr
					IpAddress,
				sleV2SecuritySACLSrcPrefixLength
					Integer32,
				sleV2SecuritySACLDstIpAddr
					IpAddress,
				sleV2SecuritySACLDstPrefixLength
					Integer32,
				sleV2SecuritySACLProtocolType
					IntProtocolType,
				sleV2SecuritySACLTcpflag
					BITS,
				sleV2SecuritySACLSrcL4Port
					IntL4Port,
				sleV2SecuritySACLDstL4Port
					IntL4Port,
				sleV2SecuritySACLIcmpType
					IntProtocolType,
				sleV2SecuritySACLIcmpCode
					IntProtocolType,
				sleV2SecuritySACLPriority
					INTEGER,
				sleV2SecuritySACLMatchAction
					INTEGER,
				sleV2SecuritySACLNomatchAction
					INTEGER
			 }

		-- 1.3.6.1.4.1.6296.102.7.2.6.1.1.1
		sleV2SecuritySACLName OBJECT-TYPE
			SYNTAX OctetName
			MAX-ACCESS read-only
			STATUS current
			DESCRIPTION
				"Description."
			::= { sleV2SecuritySACLEntry 1 }

		
		-- 1.3.6.1.4.1.6296.102.7.2.6.1.1.2
		sleV2SecuritySACLSrcIpaddr OBJECT-TYPE
			SYNTAX IpAddress
			MAX-ACCESS read-only
			STATUS current
			DESCRIPTION
				"Description."
			::= { sleV2SecuritySACLEntry 2 }

		
		-- 1.3.6.1.4.1.6296.102.7.2.6.1.1.3
		sleV2SecuritySACLSrcPrefixLength OBJECT-TYPE
			SYNTAX Integer32 (0..32)
			MAX-ACCESS read-only
			STATUS current
			DESCRIPTION
				"Description."
			::= { sleV2SecuritySACLEntry 3 }

		
		-- 1.3.6.1.4.1.6296.102.7.2.6.1.1.4
		sleV2SecuritySACLDstIpAddr OBJECT-TYPE
			SYNTAX IpAddress
			MAX-ACCESS read-only
			STATUS current
			DESCRIPTION
				"Description."
			::= { sleV2SecuritySACLEntry 4 }

		
		-- 1.3.6.1.4.1.6296.102.7.2.6.1.1.5
		sleV2SecuritySACLDstPrefixLength OBJECT-TYPE
			SYNTAX Integer32 (0..32)
			MAX-ACCESS read-only
			STATUS current
			DESCRIPTION
				"Description."
			::= { sleV2SecuritySACLEntry 5 }

		
		-- 1.3.6.1.4.1.6296.102.7.2.6.1.1.6
		sleV2SecuritySACLProtocolType OBJECT-TYPE
			SYNTAX IntProtocolType
			MAX-ACCESS read-only
			STATUS current
			DESCRIPTION
				"The type of IP protocol
				 	The flat internet protocol is from sleV2SecuritySACLTcpflag to sleV2SecuritySACLIcmpCode
				 	If the value is tcp(6) or udp(17),
				 	From sleV2SecuritySACLTcpflag to sleV2SecuritySACLDstL4Port value is available
				 	If the value is icmp(1),
				 	The value of sleV2SecuritySACLIcmpType and sleV2SecuritySACLIcmpCode is available
				 	The value of -1 means any(not set)
				"
			::= { sleV2SecuritySACLEntry 6 }

		
		-- 1.3.6.1.4.1.6296.102.7.2.6.1.1.7
		sleV2SecuritySACLTcpflag OBJECT-TYPE
			SYNTAX BITS
				{
				reserv(0),
				reserv1(1),
				urg(2),
				ack(3),
				psh(4),
				rst(5),
				syn(6),
				fin(7)
				}
			MAX-ACCESS read-only
			STATUS current
			DESCRIPTION
				"Description."
			::= { sleV2SecuritySACLEntry 7 }

		
		-- 1.3.6.1.4.1.6296.102.7.2.6.1.1.8
		sleV2SecuritySACLSrcL4Port OBJECT-TYPE
			SYNTAX IntL4Port
			MAX-ACCESS read-only
			STATUS current
			DESCRIPTION
				"Description."
			::= { sleV2SecuritySACLEntry 8 }

		
		-- 1.3.6.1.4.1.6296.102.7.2.6.1.1.9
		sleV2SecuritySACLDstL4Port OBJECT-TYPE
			SYNTAX IntL4Port
			MAX-ACCESS read-only
			STATUS current
			DESCRIPTION
				"Description."
			::= { sleV2SecuritySACLEntry 9 }

		
		-- 1.3.6.1.4.1.6296.102.7.2.6.1.1.10
		sleV2SecuritySACLIcmpType OBJECT-TYPE
			SYNTAX IntProtocolType
			MAX-ACCESS read-only
			STATUS current
			DESCRIPTION
				"The Type of ICMP message
				The value of -1 means any(not set)"
			::= { sleV2SecuritySACLEntry 10 }

		
		-- 1.3.6.1.4.1.6296.102.7.2.6.1.1.11
		sleV2SecuritySACLIcmpCode OBJECT-TYPE
			SYNTAX IntProtocolType
			MAX-ACCESS read-only
			STATUS current
			DESCRIPTION
				"The code of ICMP message
				The value of -1 means any(not set)"
			::= { sleV2SecuritySACLEntry 11 }

		
		-- 1.3.6.1.4.1.6296.102.7.2.6.1.1.12
		sleV2SecuritySACLPriority OBJECT-TYPE
			SYNTAX INTEGER
				{
				low(1),
				medium(2),
				high(3),
				highest(4)
				}
			MAX-ACCESS read-only
			STATUS current
			DESCRIPTION
				"Description."
			::= { sleV2SecuritySACLEntry 12 }

		
		-- 1.3.6.1.4.1.6296.102.7.2.6.1.1.13
		sleV2SecuritySACLMatchAction OBJECT-TYPE
			SYNTAX INTEGER
				{
				none(0),
				permit(1),
				deny(2)
				}
			MAX-ACCESS read-only
			STATUS current
			DESCRIPTION
				"Description."
			::= { sleV2SecuritySACLEntry 13 }

		
		-- 1.3.6.1.4.1.6296.102.7.2.6.1.1.14
		sleV2SecuritySACLNomatchAction OBJECT-TYPE
			SYNTAX INTEGER
				{
				none(0),
				permit(1),
				deny(2)
				}
			MAX-ACCESS read-only
			STATUS current
			DESCRIPTION
				"Description."
			::= { sleV2SecuritySACLEntry 14 }

		
		-- 1.3.6.1.4.1.6296.102.7.2.6.2
		sleV2SecuritySACLControl OBJECT IDENTIFIER::= { sleV2SecuritySACL 2 }

		
		-- 1.3.6.1.4.1.6296.102.7.2.6.2.1
		sleV2SecuritySACLControlRequest OBJECT-TYPE
			SYNTAX INTEGER
				{
				createSAclRule(1),
				destroySAclRule(2),
				destroyAllSAclRule(3)
				}
			MAX-ACCESS read-write
			STATUS current
			DESCRIPTION
				"Description."
			::= { sleV2SecuritySACLControl 1 }

		
		-- 1.3.6.1.4.1.6296.102.7.2.6.2.2
		sleV2SecuritySACLControlStatus OBJECT-TYPE
			SYNTAX SleControlStatusType
			MAX-ACCESS read-only
			STATUS current
			DESCRIPTION
				"Description."
			::= { sleV2SecuritySACLControl 2 }

		
		-- 1.3.6.1.4.1.6296.102.7.2.6.2.3
		sleV2SecuritySACLControlTimer OBJECT-TYPE
			SYNTAX Gauge32
			MAX-ACCESS read-write
			STATUS current
			DESCRIPTION
				"Description."
			::= { sleV2SecuritySACLControl 3 }

		
		-- 1.3.6.1.4.1.6296.102.7.2.6.2.4
		sleV2SecuritySACLControlTimeStamp OBJECT-TYPE
			SYNTAX TimeStamp
			MAX-ACCESS read-only
			STATUS current
			DESCRIPTION
				"Description."
			::= { sleV2SecuritySACLControl 4 }

		
		-- 1.3.6.1.4.1.6296.102.7.2.6.2.5
		sleV2SecuritySACLControlReqResult OBJECT-TYPE
			SYNTAX SleControlRequestResultType
			MAX-ACCESS read-only
			STATUS current
			DESCRIPTION
				"Description."
			::= { sleV2SecuritySACLControl 5 }

		
		-- 1.3.6.1.4.1.6296.102.7.2.6.2.6
		sleV2SecuritySACLControlName OBJECT-TYPE
			SYNTAX OctetName
			MAX-ACCESS read-write
			STATUS current
			DESCRIPTION
				"Description."
			::= { sleV2SecuritySACLControl 6 }

		
		-- 1.3.6.1.4.1.6296.102.7.2.6.2.7
		sleV2SecuritySACLControlSrcIpaddr OBJECT-TYPE
			SYNTAX IpAddress
			MAX-ACCESS read-write
			STATUS current
			DESCRIPTION
				"Description."
			::= { sleV2SecuritySACLControl 7 }

		
		-- 1.3.6.1.4.1.6296.102.7.2.6.2.8
		sleV2SecuritySACLControlSrcPrefixLength OBJECT-TYPE
			SYNTAX IntIpAddrMask
			MAX-ACCESS read-write
			STATUS current
			DESCRIPTION
				"Description."
			::= { sleV2SecuritySACLControl 8 }

		
		-- 1.3.6.1.4.1.6296.102.7.2.6.2.9
		sleV2SecuritySACLControlDstIpaddr OBJECT-TYPE
			SYNTAX IpAddress
			MAX-ACCESS read-write
			STATUS current
			DESCRIPTION
				"Description."
			::= { sleV2SecuritySACLControl 9 }

		
		-- 1.3.6.1.4.1.6296.102.7.2.6.2.10
		sleV2SecuritySACLControlDstPrefixLength OBJECT-TYPE
			SYNTAX IntIpAddrMask
			MAX-ACCESS read-write
			STATUS current
			DESCRIPTION
				"Description."
			::= { sleV2SecuritySACLControl 10 }

		
		-- 1.3.6.1.4.1.6296.102.7.2.6.2.11
		sleV2SecuritySACLControlProtocolType OBJECT-TYPE
			SYNTAX IntProtocolType
			MAX-ACCESS read-write
			STATUS current
			DESCRIPTION
				"Description."
			::= { sleV2SecuritySACLControl 11 }

		
		-- 1.3.6.1.4.1.6296.102.7.2.6.2.12
		sleV2SecuritySACLControlTcpflag OBJECT-TYPE
			SYNTAX BITS
				{
				reserv(0),
				reserv1(1),
				urg(2),
				ack(3),
				psh(4),
				rst(5),
				syn(6),
				fin(7)
				}
			MAX-ACCESS read-write
			STATUS current
			DESCRIPTION
				"Description."
			::= { sleV2SecuritySACLControl 12 }

		
		-- 1.3.6.1.4.1.6296.102.7.2.6.2.13
		sleV2SecuritySACLControlSrcL4Port OBJECT-TYPE
			SYNTAX IntL4Port
			MAX-ACCESS read-write
			STATUS current
			DESCRIPTION
				"Description."
			::= { sleV2SecuritySACLControl 13 }

		
		-- 1.3.6.1.4.1.6296.102.7.2.6.2.14
		sleV2SecuritySACLControlDstL4Port OBJECT-TYPE
			SYNTAX IntL4Port
			MAX-ACCESS read-write
			STATUS current
			DESCRIPTION
				"Description."
			::= { sleV2SecuritySACLControl 14 }

		
		-- 1.3.6.1.4.1.6296.102.7.2.6.2.15
		sleV2SecuritySACLControlIcmpType OBJECT-TYPE
			SYNTAX IntProtocolType
			MAX-ACCESS read-write
			STATUS current
			DESCRIPTION
				"Description."
			::= { sleV2SecuritySACLControl 15 }

		
		-- 1.3.6.1.4.1.6296.102.7.2.6.2.16
		sleV2SecuritySACLControlIcmpCode OBJECT-TYPE
			SYNTAX IntProtocolType
			MAX-ACCESS read-write
			STATUS current
			DESCRIPTION
				"Description."
			::= { sleV2SecuritySACLControl 16 }

		
		-- 1.3.6.1.4.1.6296.102.7.2.6.2.17
		sleV2SecuritySACLControlPriority OBJECT-TYPE
			SYNTAX INTEGER
				{
				low(1),
				medium(2),
				high(3),
				highest(4)
				}
			MAX-ACCESS read-write
			STATUS current
			DESCRIPTION
				"Description."
			::= { sleV2SecuritySACLControl 17 }

		
		-- 1.3.6.1.4.1.6296.102.7.2.6.2.18
		sleV2SecuritySACLControlMatchAction OBJECT-TYPE
			SYNTAX INTEGER
				{
				none(0),
				permit(1),
				deny(2)
				}
			MAX-ACCESS read-write
			STATUS current
			DESCRIPTION
				"Description."
			::= { sleV2SecuritySACLControl 18 }

		
		-- 1.3.6.1.4.1.6296.102.7.2.6.2.19
		sleV2SecuritySACLControlNomatchAction OBJECT-TYPE
			SYNTAX INTEGER
				{
				none(0),
				permit(1),
				deny(2)
				}
			MAX-ACCESS read-write
			STATUS current
			DESCRIPTION
				"Description."
			::= { sleV2SecuritySACLControl 19 }

		
		-- 1.3.6.1.4.1.6296.102.7.2.6.3
		sleV2SecuritySACLNotification OBJECT IDENTIFIER::= { sleV2SecuritySACL 3 }

		
		-- 1.3.6.1.4.1.6296.102.7.2.6.3.1
		sleSACLCreated NOTIFICATION-TYPE
			OBJECTS { sleV2SecuritySACLControlRequest, sleV2SecuritySACLControlTimeStamp, sleV2SecuritySACLControlReqResult, sleV2SecuritySACLSrcIpaddr, sleV2SecuritySACLSrcPrefixLength, 
				sleV2SecuritySACLDstIpAddr, sleV2SecuritySACLDstPrefixLength, sleV2SecuritySACLProtocolType, sleV2SecuritySACLTcpflag, sleV2SecuritySACLIcmpType, 
				sleV2SecuritySACLIcmpCode, sleV2SecuritySACLPriority, sleV2SecuritySACLMatchAction, sleV2SecuritySACLNomatchAction, sleV2SecuritySACLSrcL4Port, 
				sleV2SecuritySACLDstL4Port }
			STATUS current
			DESCRIPTION 
				"Description."
			::= { sleV2SecuritySACLNotification 1 }

		
		-- 1.3.6.1.4.1.6296.102.7.2.6.3.2
		sleSACLDestroyed NOTIFICATION-TYPE
			OBJECTS { sleV2SecuritySACLControlRequest, sleV2SecuritySACLControlTimeStamp, sleV2SecuritySACLControlName, sleV2SecuritySACLControlReqResult }
			STATUS current
			DESCRIPTION 
				"Description."
			::= { sleV2SecuritySACLNotification 2 }

		
		-- 1.3.6.1.4.1.6296.102.7.2.6.3.3
		sleSACLAllDestroyed NOTIFICATION-TYPE
			OBJECTS { sleV2SecuritySACLControlRequest, sleV2SecuritySACLControlTimeStamp, sleV2SecuritySACLControlReqResult }
			STATUS current
			DESCRIPTION 
				"Description."
			::= { sleV2SecuritySACLNotification 3 }

		
		-- 1.3.6.1.4.1.6296.102.7.2.7
		sleV2SecurityACLStatistics OBJECT IDENTIFIER::= { sleVSecurity4 7 }

		
		-- 1.3.6.1.4.1.6296.102.7.2.7.1
		sleV2SecurityACLStatisticsBase OBJECT IDENTIFIER::= { sleV2SecurityACLStatistics 1 }

		
		-- 1.3.6.1.4.1.6296.102.7.2.7.1.1
		sleV2SecurityACLStatisticsBaseInfo OBJECT IDENTIFIER::= { sleV2SecurityACLStatisticsBase 1 }

		
		-- 1.3.6.1.4.1.6296.102.7.2.7.1.1.1
		sleV2SecurityACLStatisticsSyslogStatus OBJECT-TYPE
			SYNTAX INTEGER
				{
				enable(1),
				disable(2)
				}
			MAX-ACCESS read-only
			STATUS current
			DESCRIPTION
				"Description."
			::= { sleV2SecurityACLStatisticsBaseInfo 1 }

		
		-- 1.3.6.1.4.1.6296.102.7.2.7.1.2
		sleV2SecurityACLStatisticsBaseControl OBJECT IDENTIFIER::= { sleV2SecurityACLStatisticsBase 2 }

		
		-- 1.3.6.1.4.1.6296.102.7.2.7.1.2.1
		sleV2SecurityACLStatisticsBaseControlRequest OBJECT-TYPE
			SYNTAX INTEGER { aclSyslogModeChange(1) }
			MAX-ACCESS read-write
			STATUS current
			DESCRIPTION
				"Description."
			::= { sleV2SecurityACLStatisticsBaseControl 1 }

		
		-- 1.3.6.1.4.1.6296.102.7.2.7.1.2.2
		sleV2SecurityACLStatisticsBaseControlStatus OBJECT-TYPE
			SYNTAX SleControlStatusType
			MAX-ACCESS read-only
			STATUS current
			DESCRIPTION
				"Description."
			::= { sleV2SecurityACLStatisticsBaseControl 2 }

		
		-- 1.3.6.1.4.1.6296.102.7.2.7.1.2.3
		sleV2SecurityACLStatisticsBaseControlTimer OBJECT-TYPE
			SYNTAX Gauge32
			MAX-ACCESS read-write
			STATUS current
			DESCRIPTION
				"Description."
			::= { sleV2SecurityACLStatisticsBaseControl 3 }

		
		-- 1.3.6.1.4.1.6296.102.7.2.7.1.2.4
		sleV2SecurityACLStatisticsBaseControlTimeStamp OBJECT-TYPE
			SYNTAX TimeStamp
			MAX-ACCESS read-only
			STATUS current
			DESCRIPTION
				"Description."
			::= { sleV2SecurityACLStatisticsBaseControl 4 }

		
		-- 1.3.6.1.4.1.6296.102.7.2.7.1.2.5
		sleV2SecurityACLStatisticsBaseControlReqResult OBJECT-TYPE
			SYNTAX SleControlRequestResultType
			MAX-ACCESS read-only
			STATUS current
			DESCRIPTION
				"Description."
			::= { sleV2SecurityACLStatisticsBaseControl 5 }

		
		-- 1.3.6.1.4.1.6296.102.7.2.7.1.2.6
		sleV2SecurityACLStatisticsBaseControlSyslogMode OBJECT-TYPE
			SYNTAX INTEGER
				{
				enable(1),
				disable(2)
				}
			MAX-ACCESS read-write
			STATUS current
			DESCRIPTION
				"Description."
			::= { sleV2SecurityACLStatisticsBaseControl 6 }

		
		-- 1.3.6.1.4.1.6296.102.7.2.7.1.3
		sleV2SecurityACLStatisticsBaseNotification OBJECT IDENTIFIER::= { sleV2SecurityACLStatisticsBase 3 }

		
		-- 1.3.6.1.4.1.6296.102.7.2.7.1.3.1
		sleV2SecurityACLStatisticsSyslogModeChanged NOTIFICATION-TYPE
			OBJECTS { sleV2SecurityACLStatisticsBaseControlRequest, sleV2SecurityACLStatisticsBaseControlTimeStamp, sleV2SecurityACLStatisticsBaseControlReqResult, sleV2SecurityACLStatisticsBaseControlSyslogMode }
			STATUS current
			DESCRIPTION 
				"Description."
			::= { sleV2SecurityACLStatisticsBaseNotification 1 }

		
		-- 1.3.6.1.4.1.6296.102.7.2.7.2
		sleV2SecurityACLStatisticsPacketHistory OBJECT IDENTIFIER::= { sleV2SecurityACLStatistics 2 }

		
		-- 1.3.6.1.4.1.6296.102.7.2.7.2.1
		sleV2SecurityACLPacketCountTable OBJECT-TYPE
			SYNTAX SEQUENCE OF SleV2SecurityACLPacketCountEntry
			MAX-ACCESS not-accessible
			STATUS current
			DESCRIPTION
				"Description."
			::= { sleV2SecurityACLStatisticsPacketHistory 1 }

		
		-- 1.3.6.1.4.1.6296.102.7.2.7.2.1.1
		sleV2SecurityACLPacketCountEntry OBJECT-TYPE
			SYNTAX SleV2SecurityACLPacketCountEntry
			MAX-ACCESS not-accessible
			STATUS current
			DESCRIPTION
				"Description."
			INDEX { sleV2SecuritySACLName }
			::= { sleV2SecurityACLPacketCountTable 1 }

		
		SleV2SecurityACLPacketCountEntry ::=
			SEQUENCE { 
				sleV2SecurityACLTotalPacket
					Counter64
			 }

		-- 1.3.6.1.4.1.6296.102.7.2.7.2.1.1.1
		sleV2SecurityACLTotalPacket OBJECT-TYPE
			SYNTAX Counter64
			MAX-ACCESS read-only
			STATUS current
			DESCRIPTION
				"Description."
			::= { sleV2SecurityACLPacketCountEntry 1 }

		
		-- 1.3.6.1.4.1.6296.102.7.2.7.2.2
		sleV2SecurityACLSrcHistoryTable OBJECT-TYPE
			SYNTAX SEQUENCE OF SleV2SecurityACLSrcHistoryEntry
			MAX-ACCESS not-accessible
			STATUS current
			DESCRIPTION
				"Description."
			::= { sleV2SecurityACLStatisticsPacketHistory 2 }

		
		-- 1.3.6.1.4.1.6296.102.7.2.7.2.2.1
		sleV2SecurityACLSrcHistoryEntry OBJECT-TYPE
			SYNTAX SleV2SecurityACLSrcHistoryEntry
			MAX-ACCESS not-accessible
			STATUS current
			DESCRIPTION
				"Description."
			INDEX { sleV2SecuritySACLName, sleV2SecurityACLSrcHistoryIndex }
			::= { sleV2SecurityACLSrcHistoryTable 1 }

		
		SleV2SecurityACLSrcHistoryEntry ::=
			SEQUENCE { 
				sleV2SecurityACLSrcHistoryIndex
					Integer32,
				sleV2SecurityACLSrcHistoryIpAddr
					IpAddress
			 }

		-- 1.3.6.1.4.1.6296.102.7.2.7.2.2.1.1
		sleV2SecurityACLSrcHistoryIndex OBJECT-TYPE
			SYNTAX Integer32 (1..1024)
			MAX-ACCESS read-only
			STATUS current
			DESCRIPTION
				"Description."
			::= { sleV2SecurityACLSrcHistoryEntry 1 }

		
		-- 1.3.6.1.4.1.6296.102.7.2.7.2.2.1.2
		sleV2SecurityACLSrcHistoryIpAddr OBJECT-TYPE
			SYNTAX IpAddress
			MAX-ACCESS read-only
			STATUS current
			DESCRIPTION
				"Description."
			::= { sleV2SecurityACLSrcHistoryEntry 2 }

		
		-- 1.3.6.1.4.1.6296.102.7.2.7.2.3
		sleV2SecurityACLStatisticsControl OBJECT IDENTIFIER::= { sleV2SecurityACLStatisticsPacketHistory 3 }

		
		-- 1.3.6.1.4.1.6296.102.7.2.7.2.3.1
		sleV2SecurityACLStatisticsControlRequest OBJECT-TYPE
			SYNTAX INTEGER { clearAruleStatus(1) }
			MAX-ACCESS read-write
			STATUS current
			DESCRIPTION
				"Description."
			::= { sleV2SecurityACLStatisticsControl 1 }

		
		-- 1.3.6.1.4.1.6296.102.7.2.7.2.3.2
		sleV2SecurityACLStatisticsControlStatus OBJECT-TYPE
			SYNTAX SleControlStatusType
			MAX-ACCESS read-only
			STATUS current
			DESCRIPTION
				"Description."
			::= { sleV2SecurityACLStatisticsControl 2 }

		
		-- 1.3.6.1.4.1.6296.102.7.2.7.2.3.3
		sleV2SecurityACLStatisticsControlTimer OBJECT-TYPE
			SYNTAX Gauge32
			MAX-ACCESS read-write
			STATUS current
			DESCRIPTION
				"Description."
			::= { sleV2SecurityACLStatisticsControl 3 }

		
		-- 1.3.6.1.4.1.6296.102.7.2.7.2.3.4
		sleV2SecurityACLStatisticsControlTimeStamp OBJECT-TYPE
			SYNTAX TimeStamp
			MAX-ACCESS read-only
			STATUS current
			DESCRIPTION
				"Description."
			::= { sleV2SecurityACLStatisticsControl 4 }

		
		-- 1.3.6.1.4.1.6296.102.7.2.7.2.3.5
		sleV2SecurityACLStatisticsControlReqResult OBJECT-TYPE
			SYNTAX SleControlRequestResultType
			MAX-ACCESS read-only
			STATUS current
			DESCRIPTION
				"Description."
			::= { sleV2SecurityACLStatisticsControl 5 }

		
		-- 1.3.6.1.4.1.6296.102.7.2.7.2.3.6
		sleV2SecurityACLStatisticsControlName OBJECT-TYPE
			SYNTAX OctetName
			MAX-ACCESS read-write
			STATUS current
			DESCRIPTION
				"Description."
			::= { sleV2SecurityACLStatisticsControl 6 }

		
		-- 1.3.6.1.4.1.6296.102.7.2.7.2.4
		sleV2SecurityACLStatisticsNotification OBJECT IDENTIFIER::= { sleV2SecurityACLStatisticsPacketHistory 4 }

		
		-- 1.3.6.1.4.1.6296.102.7.2.7.2.4.1
		sleV2SecurityACLStatisticsCleared NOTIFICATION-TYPE
			OBJECTS { sleV2SecurityACLStatisticsControlRequest, sleV2SecurityACLStatisticsControlTimeStamp, sleV2SecurityACLStatisticsControlReqResult, sleV2SecurityACLStatisticsControlName }
			STATUS current
			DESCRIPTION 
				"Description."
			::= { sleV2SecurityACLStatisticsNotification 1 }

		
		-- 1.3.6.1.4.1.6296.102.7.3
		sleV2Security6 OBJECT IDENTIFIER::= { sleV2Security 3 }

		
		-- 1.3.6.1.4.1.6296.102.7.4
		sleV2SecurityGroup OBJECT-GROUP
			OBJECTS { sleV2Security4ACLFlowIndex, sleV2Security4ACLFlowName, sleV2Security4ACLFlowSrcIpAddr, sleV2Security4ACLFlowSrcIpAddrMask, sleV2Security4ACLFlowDstIpAddr, 
				sleV2Security4ACLFlowDstIpAddrMask, sleV2Security4ACLFlowProtocolType, sleV2Security4ACLFlowTcpSrcStartPort, sleV2Security4ACLFlowTcpSrcEndPort, sleV2Security4ACLFlowTcpDstStartPort, 
				sleV2Security4ACLFlowTcpDstEndPort, sleV2Security4ACLFlowTcpFlag, sleV2Security4ACLFlowUdpSrcStartPort, sleV2Security4ACLFlowUdpSrcEndPort, sleV2Security4ACLFlowUdpDstStartPort, 
				sleV2Security4ACLFlowUdpDstEndPort, sleV2Security4ACLFlowIcmpType, sleV2Security4ACLFlowIcmpCode, sleV2Security4ACLFlowControlTcpFlag, sleV2Security4ACLFlowClassIndex, 
				sleV2Security4ACLFlowClassID, sleV2Security4ACLFlowClassName, sleV2Security4ACLFlowPolicyIndex, sleV2Security4ACLFlowPolicyID, sleV2Security4ACLFlowPolicyName, 
				sleV2Security4ACLClassIndex, sleV2Security4ACLClassName, sleV2Security4ACLClassFlowCnt, sleV2Security4ACLClassFlowIndex, sleV2Security4ACLClassFlowID, 
				sleV2Security4ACLClassFlowName, sleV2Security4ACLClassPolicyIndex, sleV2Security4ACLClassPolicyID, sleV2Security4ACLClassPolicyName, sleV2Security4ACLPolicyIndex, 
				sleV2Security4ACLPolicyName, sleV2Security4ACLPolicyFlowCnt, sleV2Security4ACLPolicyClassCnt, sleV2Security4ACLPolicyPriority, sleV2Security4ACLPolicyMatchFlag, 
				sleV2Security4ACLPolicyNomatchFlag, sleV2Security4ACLPolicyFlowClassIndex, sleV2Security4ACLPolicyFlowClassType, sleV2Security4ACLPolicyFlowClassID, sleV2Security4ACLFlowControlRequest, 
				sleV2Security4ACLFlowControlStatus, sleV2Security4ACLFlowControlTimer, sleV2Security4ACLFlowControlTimeStamp, sleV2Security4ACLFlowControlReqResult, sleV2Security4ACLFlowControlIndex, 
				sleV2Security4ACLFlowControlName, sleV2Security4ACLFlowControlSrcIpAddr, sleV2Security4ACLFlowControlSrcIpAddrMask, sleV2Security4ACLFlowControlDstIpAddr, sleV2Security4ACLFlowControlDstIpAddrMask, 
				sleV2Security4ACLFlowControlProtocolType, sleV2Security4ACLFlowControlTcpSrcStartPort, sleV2Security4ACLFlowControlTcpSrcEndPort, sleV2Security4ACLFlowControlTcpDstStartPort, sleV2Security4ACLFlowControlTcpDstEndPort, 
				sleV2Security4ACLFlowControlUdpSrcStartPort, sleV2Security4ACLFlowControlUdpSrcEndPort, sleV2Security4ACLFlowControlUdpDstStartPort, sleV2Security4ACLFlowControlUdpDstEndPort, sleV2Security4ACLFlowControlIcmpType, 
				sleV2Security4ACLFlowControlIcmpCode, sleV2Security4ACLFlowControlHdrlen, sleV2Security4ACLClassControlRequest, sleV2Security4ACLClassControlStatus, sleV2Security4ACLClassControlTimer, 
				sleV2Security4ACLClassControlTimeStamp, sleV2Security4ACLClassControlReqResult, sleV2Security4ACLClassControlIndex, sleV2Security4ACLClassControlName, sleV2Security4ACLClassFlowControlRequest, 
				sleV2Security4ACLClassFlowControlStatus, sleV2Security4ACLClassFlowControlTimer, sleV2Security4ACLClassFlowControlTimeStamp, sleV2Security4ACLClassFlowControlReqResult, sleV2Security4ACLClassFlowControlClassIndex, 
				sleV2Security4ACLClassFlowControlFlowIndex, sleV2Security4ACLClassFlowControlFlowID, sleV2Security4ACLPolicyControlRequest, sleV2Security4ACLPolicyControlStatus, sleV2Security4ACLPolicyControlTimer, 
				sleV2Security4ACLPolicyControlTimeStamp, sleV2Security4ACLPolicyControlReqResult, sleV2Security4ACLPolicyControlIndex, sleV2Security4ACLPolicyControlName, sleV2Security4ACLPolicyControlPriority, 
				sleV2Security4ACLPolicyControlMatchFlag, sleV2Security4ACLPolicyControlNomatchFlag, sleV2Security4ACLPolicyFlowClassControlRequest, sleV2Security4ACLPolicyFlowClassControlStatus, sleV2Security4ACLPolicyFlowClassControlTimer, 
				sleV2Security4ACLPolicyFlowClassControlTimeStamp, sleV2Security4ACLPolicyFlowClassControlReqResult, sleV2Security4ACLPolicyFlowClassControlPolicyIndex, sleV2Security4ACLPolicyFlowClassControlIndex, sleV2Security4ACLPolicyFlowClassControlType, 
				sleV2Security4ACLPolicyFlowClassControlFlowID, sleV2Security4ACLPolicyFlowClassControlClassID, sleV2SecuritySACLName, sleV2SecuritySACLSrcIpaddr, sleV2SecuritySACLSrcPrefixLength, 
				sleV2SecuritySACLDstIpAddr, sleV2SecuritySACLDstPrefixLength, sleV2SecuritySACLProtocolType, sleV2SecuritySACLTcpflag, sleV2SecuritySACLIcmpType, 
				sleV2SecuritySACLIcmpCode, sleV2SecuritySACLPriority, sleV2SecuritySACLMatchAction, sleV2SecuritySACLNomatchAction, sleV2SecuritySACLControlRequest, 
				sleV2SecuritySACLControlStatus, sleV2SecuritySACLControlTimer, sleV2SecuritySACLControlTimeStamp, sleV2SecuritySACLControlReqResult, sleV2SecuritySACLControlName, 
				sleV2SecuritySACLControlSrcIpaddr, sleV2SecuritySACLControlSrcPrefixLength, sleV2SecuritySACLControlDstIpaddr, sleV2SecuritySACLControlDstPrefixLength, sleV2SecuritySACLControlProtocolType, 
				sleV2SecuritySACLControlTcpflag, sleV2SecuritySACLControlIcmpType, sleV2SecuritySACLControlIcmpCode, sleV2SecuritySACLControlPriority, sleV2SecuritySACLControlMatchAction, 
				sleV2SecuritySACLControlNomatchAction, sleV2Security4ACLPolicyFlowClassName, sleV2Security4ACLFlowHdrlen, sleV2SecuritySACLDstL4Port, sleV2SecuritySACLSrcL4Port, 
				sleV2SecuritySACLControlSrcL4Port, sleV2SecuritySACLControlDstL4Port, sleV2SecurityACLTotalPacket, sleV2SecurityACLSrcHistoryIpAddr, sleV2SecurityACLStatisticsControlRequest, 
				sleV2SecurityACLStatisticsControlStatus, sleV2SecurityACLStatisticsControlTimer, sleV2SecurityACLStatisticsControlTimeStamp, sleV2SecurityACLStatisticsControlReqResult, sleV2SecurityACLStatisticsBaseControlTimer, 
				sleV2SecurityACLStatisticsBaseControlStatus, sleV2SecurityACLStatisticsBaseControlRequest, sleV2SecurityACLStatisticsControlName, sleV2SecurityACLSrcHistoryIndex, sleV2SecurityACLStatisticsBaseControlTimeStamp, 
				sleV2SecurityACLStatisticsBaseControlReqResult, sleV2SecurityACLStatisticsBaseControlSyslogMode, sleV2SecurityACLStatisticsSyslogStatus }
			STATUS current
			DESCRIPTION 
				"Description."
			::= { sleV2Security 4 }

		
		-- 1.3.6.1.4.1.6296.102.7.5
		sleV2SecurityNotificationGroup NOTIFICATION-GROUP
			NOTIFICATIONS { sleACLFlowCreated, sleACLFlowChanged, sleACLFlowDestroyed, sleACLFlowAllDestroyed, sleACLClassCreated, 
				sleACLClassDestroyed, sleACLClassAllDestroyed, sleACLClassFlowAdded, sleACLClassFlowDeleted, sleACLClassFlowAllDeleted, 
				sleACLPolicyCreated, sleACLPolicyInfoChanged, sleACLPolicyMatchActionChanged, sleACLPolicyNomatchActionChanged, sleACLPolicyDestroyed, 
				sleACLPolicyFlowAdded, sleACLPolicyFlowDeleted, sleACLPolicyAllFlowDeleted, sleACLPolicyAllClassDeleted, sleACLPolicyAllFlowClassDeleted, 
				sleSACLCreated, sleSACLDestroyed, sleSACLAllDestroyed, sleV2SecurityACLStatisticsSyslogModeChanged, sleV2SecurityACLStatisticsCleared
				 }
			STATUS current
			DESCRIPTION 
				"Description."
			::= { sleV2Security 5 }

		
	
	END

--
-- SLEV2-Security-MIB.my
--
