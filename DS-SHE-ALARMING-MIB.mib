--
-- she-alarming-mib.mib
-- MIB generated by MG-SOFT Visual MIB Builder Version 5.0  Build 250
-- Monday, June 11, 2007 at 15:21:58
--

	DS-SHE-ALARMING-MIB DEFINITIONS ::= BEGIN
 
		IMPORTS
			she			
				FROM AN-MIB
			dsShe
				FROM DASAN-SMI						
			SheControlStatusType			
				FROM DS-SHE-TC-MIB			
			OBJECT-GROUP, MODULE-COMPLIANCE, NOTIFICATION-GROUP			
				FROM SNMPv2-CONF			
			TimeTicks, Unsigned32, OBJECT-TYPE, MODULE-IDENTITY, NOTIFICATION-TYPE			
				FROM SNMPv2-SMI			
			TruthValue, TEXTUAL-CONVENTION			
				FROM SNMPv2-TC;
	
	
		sheAlarming MODULE-IDENTITY 
			LAST-UPDATED "200706111000Z"		-- June 11, 2007 at 10:00 GMT
			ORGANIZATION 
				"Nokia Siemens Networks"
			CONTACT-INFO 
				"Gerd Barchmann
				COO BBA DSLAM RD SDE
				
				gerd.barchmann@nsn.com
				+49 3834 555654"
			DESCRIPTION 
				"The MIB module representing multiple logical
				entities for the SHE alarm management. "
			REVISION "200410061109Z"		-- October 06, 2004 at 11:09 GMT
			DESCRIPTION 
				"First Release"
			REVISION "200411231109Z"		-- November 23, 2004 at 11:09 GMT
			DESCRIPTION 
				"Correct controlgroup sheAlarmControl.
				ProfileIndex, AlarmID and Serverity are 
				read/write."
			REVISION "200501071110Z"		-- January 07, 2005 at 11:10 GMT
			DESCRIPTION 
				"Strip ControlRequestType and ControlRequestResultType.
				Each of this types should only contain Request's or Result's."
			REVISION "200504211110Z"		-- April 21, 2005 at 11:10 GMT
			DESCRIPTION 
				"Change syntax for ...ControlTimeStamp."
			REVISION "200608101111Z"		-- August 10, 2006 at 11:11 GMT
			DESCRIPTION 
				"Add new enum value to ReportingSourceType for l2cp."
			REVISION "200703281111Z"		-- March 28, 2007 at 11:11 GMT
			DESCRIPTION 
				"Add configuration of alarm history table.
				Add alarm history table."
			REVISION "200704161030Z"		-- April 16, 2007 at 10:30 GMT
			DESCRIPTION 
				"Add new value to sheReportingSourceType for SyncSource(11)."
			REVISION "200706111337Z"		-- June 11, 2007 at 13:37 GMT
			DESCRIPTION 
				"Add timestamp for last overwritten Alarm to sheAlarmHistoryBase (with R2.6 RP2)."
			::= { dsShe 3 }

		
	
--
-- Textual conventions
--
	
		SheReportingSourceType ::= TEXTUAL-CONVENTION
			STATUS current
			DESCRIPTION 
				" The type to identify the type of failed component
				reporting the alarm. "
			SYNTAX INTEGER
				{
				physicalEntity(1),
				interface(2),
				vccTp(3),
				vlan(4),
				bridgePort(5),
				erpDomain(6),
				voip(7),
				vccTpShdsl(8),
				vccTpVdsl(9),
				l2cp(10),
				syncSource(11),
				unknown(20)
				}

		SheAlarmSeverityType ::= TEXTUAL-CONVENTION
			STATUS current
			DESCRIPTION 
				" The type for alarm severities. "
			SYNTAX INTEGER
				{
				critical(1),
				major(2),
				minor(3),
				warning(4),
				cleared(5)
				}

		SheAlarmSevProfileIndex ::= TEXTUAL-CONVENTION
			STATUS current
			DESCRIPTION 
				" The type for the alarm severity profile index. 
				Currently 10 profiles are supported. "
			SYNTAX INTEGER (1..10)

		SheAlarmControlRequestType ::= TEXTUAL-CONVENTION
			STATUS current
			DESCRIPTION 
				"The type for alarm control commands."
			SYNTAX INTEGER
				{
				modifyAlarmSeverity(1),
				updateAlarmList(2),
				setAlarmHistoryEnabled(5),
				setAlarmHistoryBase(6),
				clearAlarmHistory(7)
				}

		SheAlarmControlRequestResultType ::= TEXTUAL-CONVENTION
			STATUS current
			DESCRIPTION 
				"The result type for alarm control commands."
			SYNTAX INTEGER
				{
				commExecStarted(30),
				paramFaulty(31),
				requestBusy(32),
				setDataFailed(34),
				aswTimeout(35),
				commandFailed(36),
				commandSucceeded(37)
				}

	
--
-- Node definitions
--
	
		sheAlarmNotificationObjects OBJECT IDENTIFIER ::= { sheAlarming 1 }

		
		sheAlarmTimeAndDate OBJECT-TYPE
			SYNTAX TimeTicks
			MAX-ACCESS read-only
			STATUS current
			DESCRIPTION
				" Indicates the time stamp when the alarm notification was sent. "
			::= { sheAlarmNotificationObjects 1 }

		
		sheAlarmReportingSource OBJECT-TYPE
			SYNTAX Unsigned32
			MAX-ACCESS read-only
			STATUS current
			DESCRIPTION
				" Indicates the failed component which reports the alarm.
				It is the entPhysicalIndex in case of a card is reporting. "
			::= { sheAlarmNotificationObjects 2 }

		
		sheAlarmReportingSourceType OBJECT-TYPE
			SYNTAX SheReportingSourceType
			MAX-ACCESS read-only
			STATUS current
			DESCRIPTION
				" Indicates the type of failed component.
				It allows to interprete the sheAlarmReportingSource,
				e.g. in case of type is 
				- physicalEntity then the sheAlarmReportingSource is entPhysicalIndex,
				- interface the sheAlarmReportingSource is a ifIndex,
				- vccTp the sheAlarmReportingSource is a VccTp index. "
			::= { sheAlarmNotificationObjects 3 }

		
		sheAlarmSeverity OBJECT-TYPE
			SYNTAX SheAlarmSeverityType
			MAX-ACCESS read-only
			STATUS current
			DESCRIPTION
				" The alarm severity. 
				cleared indicates the clearing of alarm.
				Other values indicate that the alarm is present. "
			::= { sheAlarmNotificationObjects 4 }

		
		sheAlarmConfigurationObjects OBJECT IDENTIFIER ::= { sheAlarming 2 }

		
		sheAlarmSeverityProfileTable OBJECT-TYPE
			SYNTAX SEQUENCE OF SheAlarmSeverityProfileEntry
			MAX-ACCESS not-accessible
			STATUS current
			DESCRIPTION
				" The table of alarm severity profiles.
				SHE supports 10 profiles. 
				Profiles cannot be created or deleted dynamically.
				Profile 1 is the default profile.
				Each entry associates a profile index and AlarmID pairs with severities to be
				used within alarm traps. 
				Alarm severities can be modified by command. "
			::= { sheAlarmConfigurationObjects 1 }

		
		sheAlarmSeverityProfileEntry OBJECT-TYPE
			SYNTAX SheAlarmSeverityProfileEntry
			MAX-ACCESS not-accessible
			STATUS current
			DESCRIPTION
				" Entry of the alarm severity profile table. "
			INDEX { sheAlarmSevProfileIndex, sheAlarmSevProfileAlarmID }
			::= { sheAlarmSeverityProfileTable 1 }

		
		SheAlarmSeverityProfileEntry ::=
			SEQUENCE { 
				sheAlarmSevProfileIndex
					SheAlarmSevProfileIndex,
				sheAlarmSevProfileAlarmID
					OBJECT IDENTIFIER,
				sheAlarmSevProfileSeverity
					SheAlarmSeverityType
			 }

		sheAlarmSevProfileIndex OBJECT-TYPE
			SYNTAX SheAlarmSevProfileIndex
			MAX-ACCESS read-only
			STATUS current
			DESCRIPTION
				" A number identifying this alarm severity profile. "
			::= { sheAlarmSeverityProfileEntry 1 }

		
		sheAlarmSevProfileAlarmID OBJECT-TYPE
			SYNTAX OBJECT IDENTIFIER
			MAX-ACCESS read-only
			STATUS current
			DESCRIPTION
				" The OID of alarm. "
			::= { sheAlarmSeverityProfileEntry 2 }

		
		sheAlarmSevProfileSeverity OBJECT-TYPE
			SYNTAX SheAlarmSeverityType
			MAX-ACCESS read-only
			STATUS current
			DESCRIPTION
				" The severity of alarm. "
			::= { sheAlarmSeverityProfileEntry 3 }

		
		sheAlarmControl OBJECT IDENTIFIER ::= { sheAlarmConfigurationObjects 4 }

		
		sheAlarmControlRequest OBJECT-TYPE
			SYNTAX SheAlarmControlRequestType
			MAX-ACCESS read-write
			STATUS current
			DESCRIPTION
				" This attribute identifies the control commands.
				modifyAlarmSeverity: 
				   modifies the severity of an alarm in specific profile. 
				   Profile 1 is the default profile and its severities cannot be modified.
				updateAlarmList:
				   the NE updates entries of alarms in the sheAlarmTable
				   after having changed alarm severities of alarms 
				   (due to change profile pointers in
				   managed entities or after modification of alarm severities 
				   in profiles). This command should be applied once after having 
				   finished modifications of severties.
				
				Notifications : none "
			::= { sheAlarmControl 1 }

		
		sheAlarmControlStatus OBJECT-TYPE
			SYNTAX SheControlStatusType
			MAX-ACCESS read-only
			STATUS current
			DESCRIPTION
				" The status of a control request. "
			::= { sheAlarmControl 2 }

		
		sheAlarmControlSevProfileIndex OBJECT-TYPE
			SYNTAX SheAlarmSevProfileIndex
			MAX-ACCESS read-write
			STATUS current
			DESCRIPTION
				" A number identifying this alarm severity profile. "
			::= { sheAlarmControl 3 }

		
		sheAlarmControlAlarmID OBJECT-TYPE
			SYNTAX OBJECT IDENTIFIER
			MAX-ACCESS read-write
			STATUS current
			DESCRIPTION
				" The OID of alarm. "
			::= { sheAlarmControl 4 }

		
		sheAlarmControlSeverity OBJECT-TYPE
			SYNTAX SheAlarmSeverityType
			MAX-ACCESS read-write
			STATUS current
			DESCRIPTION
				" The severity of alarm. "
			::= { sheAlarmControl 5 }

		
		sheAlarmControlTimer OBJECT-TYPE
			SYNTAX Unsigned32
			MAX-ACCESS read-only
			STATUS current
			DESCRIPTION
				" The maximum wait time for the manager for command ending.
				For long running commands.
				The manager reads this value from the DSLAM. "
			::= { sheAlarmControl 6 }

		
		sheAlarmControlReqResult OBJECT-TYPE
			SYNTAX SheAlarmControlRequestResultType
			MAX-ACCESS read-only
			STATUS current
			DESCRIPTION
				" The result of the last user command. "
			::= { sheAlarmControl 7 }

		
		sheAlarmControlTimeStamp OBJECT-TYPE
			SYNTAX Unsigned32
			UNITS "sec"
			MAX-ACCESS read-only
			STATUS current
			DESCRIPTION
				" The time stamp of the last command (end of command). "
			::= { sheAlarmControl 8 }

		
		sheAlarmListTable OBJECT-TYPE
			SYNTAX SEQUENCE OF SheAlarmListEntry
			MAX-ACCESS not-accessible
			STATUS current
			DESCRIPTION
				" The alarm list table is used to store all reported alarms. "
			::= { sheAlarmConfigurationObjects 5 }

		
		sheAlarmListEntry OBJECT-TYPE
			SYNTAX SheAlarmListEntry
			MAX-ACCESS not-accessible
			STATUS current
			DESCRIPTION
				" Entry of the alarm lis table. "
			INDEX { sheAlarmListIndex }
			::= { sheAlarmListTable 1 }

		
		SheAlarmListEntry ::=
			SEQUENCE { 
				sheAlarmListIndex
					Unsigned32,
				sheAlarmListTimeAndDate
					TimeTicks,
				sheAlarmListAlarmID
					OBJECT IDENTIFIER,
				sheAlarmListReportingSource
					Unsigned32,
				sheAlarmListReportingSourceType
					SheReportingSourceType,
				sheAlarmListSeverity
					SheAlarmSeverityType
			 }

		sheAlarmListIndex OBJECT-TYPE
			SYNTAX Unsigned32 (1..65535)
			MAX-ACCESS read-only
			STATUS current
			DESCRIPTION
				" The index of table. "
			::= { sheAlarmListEntry 1 }

		
		sheAlarmListTimeAndDate OBJECT-TYPE
			SYNTAX TimeTicks
			MAX-ACCESS read-only
			STATUS current
			DESCRIPTION
				" The time and date when the alarm notification was sent. "
			::= { sheAlarmListEntry 2 }

		
		sheAlarmListAlarmID OBJECT-TYPE
			SYNTAX OBJECT IDENTIFIER
			MAX-ACCESS read-only
			STATUS current
			DESCRIPTION
				" The OID of alarm. "
			::= { sheAlarmListEntry 3 }

		
		sheAlarmListReportingSource OBJECT-TYPE
			SYNTAX Unsigned32
			MAX-ACCESS read-only
			STATUS current
			DESCRIPTION
				" The failed component which reports the alarm,
				e.g. the entPhysicalIndex in case of a card is 
				reporting the alarm. "
			::= { sheAlarmListEntry 4 }

		
		sheAlarmListReportingSourceType OBJECT-TYPE
			SYNTAX SheReportingSourceType
			MAX-ACCESS read-only
			STATUS current
			DESCRIPTION
				" The type of failed component. "
			::= { sheAlarmListEntry 5 }

		
		sheAlarmListSeverity OBJECT-TYPE
			SYNTAX SheAlarmSeverityType
			MAX-ACCESS read-only
			STATUS current
			DESCRIPTION
				" The alarm severity of alarm. "
			::= { sheAlarmListEntry 6 }

		
-- 1.3.6.1.4.1.231.7.1.2.2.1.3.2.6
-- New supported with SHE R2.6 RP2.
		sheAlarmHistory OBJECT IDENTIFIER ::= { sheAlarmConfigurationObjects 6 }

		
-- --------------------------------------------------------------
-- Alarm history base group 
-- --------------------------------------------------------------
-- 1.3.6.1.4.1.231.7.1.2.2.1.3.2.6.1
		sheAlarmHistoryBase OBJECT IDENTIFIER ::= { sheAlarmHistory 1 }

		
-- 1.3.6.1.4.1.231.7.1.2.2.1.3.2.6.1.1
		sheAlarmHistoryEnabled OBJECT-TYPE
			SYNTAX TruthValue
			MAX-ACCESS read-only
			STATUS current
			DESCRIPTION
				"Enable/ disable alarm history in NE. 
				Default: false"
			::= { sheAlarmHistoryBase 1 }

		
-- 1.3.6.1.4.1.231.7.1.2.2.1.3.2.6.1.2
		sheAlarmHistoryEntryNumber OBJECT-TYPE
			SYNTAX Unsigned32 (1..1000)
			MAX-ACCESS read-only
			STATUS current
			DESCRIPTION
				"The maximum number of the alarm history entries to keep.
				Default: 100"
			::= { sheAlarmHistoryBase 2 }

		
-- 1.3.6.1.4.1.231.7.1.2.2.1.3.2.6.1.3
		sheAlarmHistorySeverityLevel OBJECT-TYPE
			SYNTAX SheAlarmSeverityType
			MAX-ACCESS read-only
			STATUS current
			DESCRIPTION
				"This attribute defines the minimum level of alarms which should be stored in 
				alarm history. All alarms of higher priority will also be stored in that case.
				
				If set to critical(1) only critical alarms will be stored. 
				If set to warning(4) all alarms will be stored. 
				The level cleared(5) is not a valid configuration!  
				
				Default: critical(1)"
			::= { sheAlarmHistoryBase 3 }

		
		sheAlarmHistoryLatestOverwriteTimeAndDate OBJECT-TYPE
			SYNTAX TimeTicks
			MAX-ACCESS read-only
			STATUS current
			DESCRIPTION
				"If the sheAlarmHistoryTable wrap around, because the configured maximum level
				was reached, the latest timestamp of the overwritten entrys are stored here for
				management system recovery.
				1.If the overwritten alarm was cleared, the clearing time will be compared 
				with the currently stored value.
				2.If the overwritten alarm was not cleared, the arising time will be compared 
				with the currently stored value.
				3.The latest timestamp will be stored or maybe the currently stored value 
				will be keeped.
				"
			::= { sheAlarmHistoryBase 4 }

		
-- 1.3.6.1.4.1.231.7.1.2.2.1.3.2.6.2
		sheAlarmHistoryControl OBJECT IDENTIFIER ::= { sheAlarmHistory 2 }

		
-- 1.3.6.1.4.1.231.7.1.2.2.1.3.2.6.2.1
		sheAlarmHistoryControlRequest OBJECT-TYPE
			SYNTAX SheAlarmControlRequestType
			MAX-ACCESS read-write
			STATUS current
			DESCRIPTION
				"Alarm history global user commands.
				
				setAlarmHistoryEnabled(5):
				sheAlarmHistoryControlEnabled
				
				setAlarmHistoryBase(6):
				sheAlarmHistoryControlEntryNumber
				sheAlarmHistoryControlSeverityLevel
				
				clearAlarmHistory(7):
				
				"
			::= { sheAlarmHistoryControl 1 }

		
-- 1.3.6.1.4.1.231.7.1.2.2.1.3.2.6.2.2
		sheAlarmHistoryControlStatus OBJECT-TYPE
			SYNTAX SheAlarmControlRequestResultType
			MAX-ACCESS read-only
			STATUS current
			DESCRIPTION
				" The status of a control request. "
			::= { sheAlarmHistoryControl 2 }

		
-- 1.3.6.1.4.1.231.7.1.2.2.1.3.2.6.2.3
		sheAlarmHistoryControlTimer OBJECT-TYPE
			SYNTAX Unsigned32
			MAX-ACCESS read-only
			STATUS current
			DESCRIPTION
				"The maximum wait time for the manager for command ending.
				For long running commands.
				The manager reads this value from the DSLAM. "
			::= { sheAlarmHistoryControl 3 }

		
-- 1.3.6.1.4.1.231.7.1.2.2.1.3.2.6.2.4
		sheAlarmHistoryControlTimeStamp OBJECT-TYPE
			SYNTAX Unsigned32
			UNITS "sec"
			MAX-ACCESS read-only
			STATUS current
			DESCRIPTION
				"The time stamp of the last command (end of command). "
			::= { sheAlarmHistoryControl 4 }

		
-- 1.3.6.1.4.1.231.7.1.2.2.1.3.2.6.2.5
		sheAlarmHistoryControlReqResult OBJECT-TYPE
			SYNTAX SheAlarmControlRequestResultType
			MAX-ACCESS read-only
			STATUS current
			DESCRIPTION
				"The result of the last user command."
			::= { sheAlarmHistoryControl 5 }

		
-- 1.3.6.1.4.1.231.7.1.2.2.1.3.2.6.2.6
		sheAlarmHistoryControlEnabled OBJECT-TYPE
			SYNTAX TruthValue
			MAX-ACCESS read-write
			STATUS current
			DESCRIPTION
				"Enable/ disable alarm history in NE. "
			::= { sheAlarmHistoryControl 6 }

		
-- 1.3.6.1.4.1.231.7.1.2.2.1.3.2.6.2.7
		sheAlarmHistoryControlEntryNumber OBJECT-TYPE
			SYNTAX Unsigned32 (1..1000)
			MAX-ACCESS read-write
			STATUS current
			DESCRIPTION
				"The maximum number of the alarm history entries to keep."
			::= { sheAlarmHistoryControl 7 }

		
-- 1.3.6.1.4.1.231.7.1.2.2.1.3.2.6.2.8
		sheAlarmHistoryControlSeverityLevel OBJECT-TYPE
			SYNTAX SheAlarmSeverityType
			MAX-ACCESS read-write
			STATUS current
			DESCRIPTION
				"This attribute defines the minimum level of alarms which should be stored in 
				alarm history. All alarms of higher priority will also be stored in that case.
				
				If set to critical(1) only critical alarms will be stored. 
				If set to warning(4) all alarms will be stored. 
				The level cleared(5) is not a valid configuration!"
			::= { sheAlarmHistoryControl 8 }

		
-- 1.3.6.1.4.1.231.7.1.2.2.1.3.2.6.3
		sheAlarmHistoryNotifications OBJECT IDENTIFIER ::= { sheAlarmHistory 3 }

		
		sheAlarmHistoryEnabledChanged NOTIFICATION-TYPE
			OBJECTS { sheAlarmHistoryEnabled, sheAlarmHistoryControlTimeStamp }
			STATUS current
			DESCRIPTION 
				"Alarm history enabled changed."
			::= { sheAlarmHistoryNotifications 1 }

		
-- 1.3.6.1.4.1.231.7.1.2.2.1.3.2.6.3.1
		sheAlarmHistoryBaseChanged NOTIFICATION-TYPE
			OBJECTS { sheAlarmHistoryEntryNumber, sheAlarmHistorySeverityLevel, sheAlarmHistoryControlTimeStamp }
			STATUS current
			DESCRIPTION 
				"Alarm history base parameter changed."
			::= { sheAlarmHistoryNotifications 2 }

		
-- 1.3.6.1.4.1.231.7.1.2.2.1.3.2.6.3.2
		sheAlarmHistoryCleared NOTIFICATION-TYPE
			OBJECTS { sheAlarmHistoryControlTimeStamp }
			STATUS current
			DESCRIPTION 
				"Alarm hsitory table cleared."
			::= { sheAlarmHistoryNotifications 3 }

		
-- 1.3.6.1.4.1.231.7.1.2.2.1.3.2.6.4
		sheAlarmHistoryTable OBJECT-TYPE
			SYNTAX SEQUENCE OF SheAlarmHistoryEntry
			MAX-ACCESS not-accessible
			STATUS current
			DESCRIPTION
				"The alarm history table is used to store all reported alarms. "
			::= { sheAlarmHistory 4 }

		
-- 1.3.6.1.4.1.231.7.1.2.2.1.3.2.6.4.1
		sheAlarmHistoryEntry OBJECT-TYPE
			SYNTAX SheAlarmHistoryEntry
			MAX-ACCESS not-accessible
			STATUS current
			DESCRIPTION
				"Entry of the alarm history table."
			INDEX { sheAlarmHistoryIndex }
			::= { sheAlarmHistoryTable 1 }

		
		SheAlarmHistoryEntry ::=
			SEQUENCE { 
				sheAlarmHistoryIndex
					Unsigned32,
				sheAlarmHistoryArisalTimeAndDate
					TimeTicks,
				sheAlarmHistoryClearingTimeAndDate
					TimeTicks,
				sheAlarmHistoryAlarmID
					OBJECT IDENTIFIER,
				sheAlarmHistoryReportingSource
					Unsigned32,
				sheAlarmHistoryReportingSourceType
					SheReportingSourceType,
				sheAlarmHistorySeverity
					SheAlarmSeverityType
			 }

-- 1.3.6.1.4.1.231.7.1.2.2.1.3.2.6.4.1.1
		sheAlarmHistoryIndex OBJECT-TYPE
			SYNTAX Unsigned32 (1..1000)
			MAX-ACCESS read-only
			STATUS current
			DESCRIPTION
				" The index of table. The range depends on setting of sheAlarmHistoryEntryNumber."
			::= { sheAlarmHistoryEntry 1 }

		
-- 1.3.6.1.4.1.231.7.1.2.2.1.3.2.6.4.1.2
		sheAlarmHistoryArisalTimeAndDate OBJECT-TYPE
			SYNTAX TimeTicks
			MAX-ACCESS read-only
			STATUS current
			DESCRIPTION
				"The time and date when the alarm notification was sent. "
			::= { sheAlarmHistoryEntry 2 }

		
-- 1.3.6.1.4.1.231.7.1.2.2.1.3.2.6.4.1.3
		sheAlarmHistoryClearingTimeAndDate OBJECT-TYPE
			SYNTAX TimeTicks
			MAX-ACCESS read-only
			STATUS current
			DESCRIPTION
				"The time and date when the alarm clearing notification was sent. "
			::= { sheAlarmHistoryEntry 3 }

		
-- 1.3.6.1.4.1.231.7.1.2.2.1.3.2.6.4.1.4
		sheAlarmHistoryAlarmID OBJECT-TYPE
			SYNTAX OBJECT IDENTIFIER
			MAX-ACCESS read-only
			STATUS current
			DESCRIPTION
				" The OID of alarm. "
			::= { sheAlarmHistoryEntry 4 }

		
-- 1.3.6.1.4.1.231.7.1.2.2.1.3.2.6.4.1.5
		sheAlarmHistoryReportingSource OBJECT-TYPE
			SYNTAX Unsigned32
			MAX-ACCESS read-only
			STATUS current
			DESCRIPTION
				" The failed component which reports the alarm,
				e.g. the entPhysicalIndex in case of a card is 
				reporting the alarm. "
			::= { sheAlarmHistoryEntry 5 }

		
-- 1.3.6.1.4.1.231.7.1.2.2.1.3.2.6.4.1.6
		sheAlarmHistoryReportingSourceType OBJECT-TYPE
			SYNTAX SheReportingSourceType
			MAX-ACCESS read-only
			STATUS current
			DESCRIPTION
				" The type of failed component. "
			::= { sheAlarmHistoryEntry 6 }

		
-- 1.3.6.1.4.1.231.7.1.2.2.1.3.2.6.4.1.7
		sheAlarmHistorySeverity OBJECT-TYPE
			SYNTAX SheAlarmSeverityType
			MAX-ACCESS read-only
			STATUS current
			DESCRIPTION
				" The alarm severity of alarm. "
			::= { sheAlarmHistoryEntry 7 }

		
		sheAlarmingConformance OBJECT IDENTIFIER ::= { sheAlarming 100 }

		
		sheAlarmingCompliances OBJECT IDENTIFIER ::= { sheAlarmingConformance 1 }

		
		sheAlarmingCompliance MODULE-COMPLIANCE
			STATUS current
			DESCRIPTION 
				"Description."
			MODULE -- this module
				MANDATORY-GROUPS { sheAlarmingNotificationGroup, sheAlarmingConfigurationGroup, sheAlarmHistoryGroup, sheAlarmHistoryNotificationGroup }
			::= { sheAlarmingCompliances 1 }

		
		sheAlarmingGroups OBJECT IDENTIFIER ::= { sheAlarmingConformance 2 }

		
		sheAlarmingNotificationGroup OBJECT-GROUP
			OBJECTS { sheAlarmTimeAndDate, sheAlarmReportingSource, sheAlarmReportingSourceType, sheAlarmSeverity }
			STATUS current
			DESCRIPTION 
				"Description."
			::= { sheAlarmingGroups 1 }

		
		sheAlarmingConfigurationGroup OBJECT-GROUP
			OBJECTS { sheAlarmSevProfileIndex, sheAlarmSevProfileAlarmID, sheAlarmSevProfileSeverity, sheAlarmControlRequest, sheAlarmControlStatus, 
				sheAlarmControlSevProfileIndex, sheAlarmControlAlarmID, sheAlarmControlSeverity, sheAlarmControlTimer, sheAlarmControlReqResult, 
				sheAlarmControlTimeStamp, sheAlarmListIndex, sheAlarmListTimeAndDate, sheAlarmListAlarmID, sheAlarmListReportingSource, 
				sheAlarmListReportingSourceType, sheAlarmListSeverity }
			STATUS current
			DESCRIPTION 
				"Description."
			::= { sheAlarmingGroups 2 }

		
		sheAlarmHistoryGroup OBJECT-GROUP
			OBJECTS { sheAlarmHistoryEnabled, sheAlarmHistoryEntryNumber, sheAlarmHistorySeverityLevel, sheAlarmHistoryControlRequest, sheAlarmHistoryControlStatus, 
				sheAlarmHistoryControlTimer, sheAlarmHistoryControlTimeStamp, sheAlarmHistoryControlReqResult, sheAlarmHistoryControlEnabled, sheAlarmHistoryControlEntryNumber, 
				sheAlarmHistoryControlSeverityLevel, sheAlarmHistoryIndex, sheAlarmHistoryArisalTimeAndDate, sheAlarmHistoryClearingTimeAndDate, sheAlarmHistoryAlarmID, 
				sheAlarmHistoryReportingSource, sheAlarmHistoryReportingSourceType, sheAlarmHistorySeverity, sheAlarmHistoryLatestOverwriteTimeAndDate }
			STATUS current
			DESCRIPTION 
				"Description."
			::= { sheAlarmingGroups 3 }

		
		sheAlarmHistoryNotificationGroup NOTIFICATION-GROUP
			NOTIFICATIONS { sheAlarmHistoryEnabledChanged, sheAlarmHistoryBaseChanged, sheAlarmHistoryCleared }
			STATUS current
			DESCRIPTION 
				"Description."
			::= { sheAlarmingGroups 4 }

		
	
	END

--
-- she-alarming-mib.mib
--
