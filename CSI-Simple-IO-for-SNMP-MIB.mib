CSI-Simple-IO-for-SNMP-MIB 
-- ******************************************************
--Control Solutions, Inc., SNMP  MIB
--Prefix for private enterprises:  1.3.6.1.4.1	
--Control Solutions, Inc. private enterprize number:  3815
--
-- The following MIB is the definition of the SNMP based implementation
-- of Simple I/O for SNMP. This MIB provides access to discrete inputs and outputs,
-- and analog inputs and outputs. 	
--
--
--
-- ************************************************************

DEFINITIONS ::= BEGIN

IMPORTS  
	MODULE-IDENTITY, OBJECT-TYPE, Integer32 
		FROM SNMPv2-SMI
	MODULE-COMPLIANCE, OBJECT-GROUP
		FROM SNMPv2-CONF
	bb100modbus, bb100modbusV1 
		FROM Control-Solutions-MIB-Registrations;


sys700v1Module MODULE-IDENTITY
	LAST-UPDATED "200507050000Z"
	ORGANIZATION "Control Solutions, Inc."
	CONTACT-INFO
		"Jim Hogenson
		Control Solutions, Inc.
		2179 Fourth Street, Suite 2-G
		PO Box 10789
		White Bear Lake, MN 55110
		jimhogenson@csimn.com
		Voice: 651-426-4410
		Fax: 651-426-4418"
	DESCRIPTION
		"The following MIB is the definition of SNMP access to
		Simple I/O for SNMP based on Control Solutions BAS-7050
		Ethernet processor and BAS-700 series I/O modules."
	REVISION "200507050000Z"
	DESCRIPTION
		"Initial draft."
	::= { snmp7050v1 1 }


-- Major object categories for Simple I/O for SNMP

sioObjects	OBJECT IDENTIFIER ::= { snmpio7050 1 }

discreteOutput	OBJECT IDENTIFIER ::= { sioObjects 1 }		-- 3815.1.1.2.1.1
discreteInput	OBJECT IDENTIFIER ::= { sioObjects 2 }		-- 3815.1.1.2.1.2
analogInput 	OBJECT IDENTIFIER ::= { sioObjects 3 }		-- 3815.1.1.2.1.3
analogOutput	OBJECT IDENTIFIER ::= { sioObjects 4 }		-- 3815.1.1.2.1.4

-- ******************************************************
--
-- DISCRETE OUTPUT TABLE
-- 
-- ******************************************************

discOutTable OBJECT-TYPE
	SYNTAX	SEQUENCE OF DiscOutEntry
	MAX-ACCESS	not-accessible
	STATUS	current
	DESCRIPTION
		"Discrete output data table."
	::= { discreteOutput 1 }

discOutEntry OBJECT-TYPE
	SYNTAX	DiscOutEntry
	MAX-ACCESS	not-accessible
	STATUS	current
	DESCRIPTION
		"Discrete output data table entry."
	INDEX	{ discOutIndex }
	::= { discOutTable 1 }

DiscOutEntry ::= SEQUENCE {
	discOutIndex		INTEGER,
	discOutData			INTEGER
	}

discOutIndex OBJECT-TYPE
	SYNTAX	INTEGER 
	MAX-ACCESS	not-accessible
	STATUS	current
	DESCRIPTION
		"Index into discrete output data table."
	::= { discOutEntry 1 }

discOutData OBJECT-TYPE
	SYNTAX	INTEGER {
		off(0),
		on(1)
	}	
	MAX-ACCESS	read-write
	STATUS	current
	DESCRIPTION
		"State of discrete output."
	::= { discOutEntry 2 }

-- ******************************************************
--
-- DISCRETE INPUT TABLE
-- 
-- ******************************************************

discInTable OBJECT-TYPE
	SYNTAX	SEQUENCE OF DiscInEntry
	MAX-ACCESS	not-accessible
	STATUS	current
	DESCRIPTION
		"Discrete input data table."
	::= { discreteInput 1 }

discInEntry OBJECT-TYPE
	SYNTAX	DiscInEntry
	MAX-ACCESS	not-accessible
	STATUS	current
	DESCRIPTION
		"Discrete input data table entry."
	INDEX	{ discInIndex }
	::= { discInTable 1 }

DiscInEntry ::= SEQUENCE {
	discInIndex		INTEGER,
	discInData		INTEGER
	}

discInIndex OBJECT-TYPE
	SYNTAX	INTEGER 
	MAX-ACCESS	not-accessible
	STATUS	current
	DESCRIPTION
		"Index into discrete input data table."
	::= { discInEntry 1 }

discInData OBJECT-TYPE
	SYNTAX	INTEGER {
		off(0),
		on(1)
	}	
	MAX-ACCESS	read-only
	STATUS	current
	DESCRIPTION
		"State of discrete input."
	::= { discInEntry 2 }

-- **
-- Configuration table for discrete inputs
-- **

discInCfgTable OBJECT-TYPE
	SYNTAX	SEQUENCE OF DiscInCfgEntry
	MAX-ACCESS	not-accessible
	STATUS	current
	DESCRIPTION
		"Discrete input event configuration table."
	::= { discreteInput 2 }

discInCfgEntry OBJECT-TYPE
	SYNTAX	DiscInCfgEntry
	MAX-ACCESS	not-accessible
	STATUS	current
	DESCRIPTION
		"Discrete input configuration table entry."
	INDEX	{ discInCfgIndex }
	::= { discInCfgTable 1 }

DiscInCfgEntry ::= SEQUENCE {
	discInCfgIndex			INTEGER,
	discInActiveEnable		INTEGER,
	discInActiveDelay		INTEGER,
	discInInactiveEnable	INTEGER,
	discInInactiveDelay		INTEGER,
	discInTrapRepeat		INTEGER
	}

discInCfgIndex OBJECT-TYPE
	SYNTAX	INTEGER 
	MAX-ACCESS	not-accessible
	STATUS	current
	DESCRIPTION
		"Index into discrete input configuration table."
	::= { discInCfgEntry 1 }

discInActiveEnable OBJECT-TYPE
	SYNTAX	INTEGER {
		disable(0),
		enable(1)
	}	
	MAX-ACCESS	read-write
	STATUS	current
	DESCRIPTION
		"Enables or disables trap on input active."
	::= { discInCfgEntry 2 }

discInActiveDelay OBJECT-TYPE
	SYNTAX	INTEGER
	MAX-ACCESS	read-write
	STATUS	current
	DESCRIPTION
		"Delay in seconds after physical input becomes
		active before trap is sent."
	::= { discInCfgEntry 3 }

discInInactiveEnable OBJECT-TYPE
	SYNTAX	INTEGER {
		disable(0),
		enable(1)
	}	
	MAX-ACCESS	read-write
	STATUS	current
	DESCRIPTION
		"Enables or disables trap on input inactive."
	::= { discInCfgEntry 4 }

discInInactiveDelay OBJECT-TYPE
	SYNTAX	INTEGER
	MAX-ACCESS	read-write
	STATUS	current
	DESCRIPTION
		"Delay in seconds after physical input becomes
		inactive before trap is sent."
	::= { discInCfgEntry 5 }

discInTrapRepeat OBJECT-TYPE
	SYNTAX	INTEGER
	MAX-ACCESS	read-write
	STATUS	current
	DESCRIPTION
		"Trap will be repeated every this many seconds,
		or sent only once if zero."
	::= { discInCfgEntry 6 }

-- ******************************************************
--
-- ANALOG INPUT TABLE
-- 
-- ******************************************************

analogInTable OBJECT-TYPE
	SYNTAX	SEQUENCE OF AnalogInEntry
	MAX-ACCESS	not-accessible
	STATUS	current
	DESCRIPTION
		"Analog input data table."
	::= { analogInput 1 }

analogInEntry OBJECT-TYPE
	SYNTAX	AnalogInEntry
	MAX-ACCESS	not-accessible
	STATUS	current
	DESCRIPTION
		"Analog input data table entry."
	INDEX	{ analogInIndex }
	::= { analogInTable 1 }

AnalogInEntry ::= SEQUENCE {
	analogInIndex		INTEGER,
	analogInData		INTEGER,
	analogInStatus		INTEGER
	}

analogInIndex OBJECT-TYPE
	SYNTAX	INTEGER 
	MAX-ACCESS	not-accessible
	STATUS	current
	DESCRIPTION
		"Index into analog input data table."
	::= { analogInEntry 1 }

analogInData OBJECT-TYPE
	SYNTAX	INTEGER 
	MAX-ACCESS	read-only
	STATUS	current
	DESCRIPTION
		"Scaled level of analog input."
	::= { analogInEntry 2 }

analogInStatus OBJECT-TYPE
	SYNTAX	INTEGER {
		normal(0),
		low_limit(1),
		high_limit(2),
		all_limits(3)
	}
	MAX-ACCESS	read-only
	STATUS	current
	DESCRIPTION
		"Event condition, 0=no limits exceeded,
		1=low limit exceeded, 2=high limite exceeded,
		3=both limits exceeded (result of overlap)."
	::= { analogInEntry 3 }

-- **
-- Configuration table for analog inputs
-- **

analogInCfgTable OBJECT-TYPE
	SYNTAX	SEQUENCE OF AnalogInCfgEntry
	MAX-ACCESS	not-accessible
	STATUS	current
	DESCRIPTION
		"Analog input event configuration table."
	::= { analogInput 2 }

analogInCfgEntry OBJECT-TYPE
	SYNTAX	AnalogInCfgEntry
	MAX-ACCESS	not-accessible
	STATUS	current
	DESCRIPTION
		"Analog input configuration table entry."
	INDEX	{ analogInCfgIndex }
	::= { analogInCfgTable 1 }

AnalogInCfgEntry ::= SEQUENCE {
	analogInCfgIndex		INTEGER
	analogInHiLimEnable		INTEGER,
	analogInHiLimit			INTEGER,
	analogInHiHyst			INTEGER,
	analogInLoLimEnable		INTEGER,
	analogInLoLimit			INTEGER,
	analogInLoHyst			INTEGER,
	analogInTrapRepeat		INTEGER
}

analogInCfgIndex OBJECT-TYPE
	SYNTAX	INTEGER 
	MAX-ACCESS	not-accessible
	STATUS	current
	DESCRIPTION
		"Index into analog input configuration table."
	::= { analogInCfgEntry 1 }

analogInHiLimEnable OBJECT-TYPE
	SYNTAX	INTEGER {
		disable(0),
		enable(1)
	}	
	MAX-ACCESS	read-write
	STATUS	current
	DESCRIPTION
		"Enables or disables trap on input above high limit."
	::= { analogInCfgEntry 2 }

analogInHiLimit OBJECT-TYPE
	SYNTAX	INTEGER
	MAX-ACCESS	read-write
	STATUS	current
	DESCRIPTION
		"Input level above which trap should be active."
	::= { analogInCfgEntry 3 }

analogInHiHyst OBJECT-TYPE
	SYNTAX	INTEGER
	MAX-ACCESS	read-write
	STATUS	current
	DESCRIPTION
		"Hysteresis for high limit. Traps will continue until
		actual level falls below high limit by this amount."
	::= { analogInCfgEntry 4 }

analogInLoLimEnable OBJECT-TYPE
	SYNTAX	INTEGER {
		disable(0),
		enable(1)
	}	
	MAX-ACCESS	read-write
	STATUS	current
	DESCRIPTION
		"Enables or disables trap on input below low limit."
	::= { analogInCfgEntry 5 }

analogInLoLimit OBJECT-TYPE
	SYNTAX	INTEGER
	MAX-ACCESS	read-write
	STATUS	current
	DESCRIPTION
		"Input level below which trap should be active."
	::= { analogInCfgEntry 6 }

analogInLoHyst OBJECT-TYPE
	SYNTAX	INTEGER
	MAX-ACCESS	read-write
	STATUS	current
	DESCRIPTION
		"Hysteresis for low limit. Traps will continue until
		actual level rises above low limit by this amount."
	::= { analogInCfgEntry 7 }


analogInTrapRepeat OBJECT-TYPE
	SYNTAX	INTEGER
	MAX-ACCESS	read-write
	STATUS	current
	DESCRIPTION
		"Trap will be repeated every this many seconds,
		or sent only once if zero."
	::= { analogInCfgEntry 8 }

-- ******************************************************
--
-- ANALOG OUTPUT TABLE
-- 
-- ******************************************************

analogOutTable OBJECT-TYPE
	SYNTAX	SEQUENCE OF AnalogOutEntry
	MAX-ACCESS	not-accessible
	STATUS	current
	DESCRIPTION
		"Analog output data table."
	::= { analogOutput 1 }

analogOutEntry OBJECT-TYPE
	SYNTAX	AnalogOutEntry
	MAX-ACCESS	not-accessible
	STATUS	current
	DESCRIPTION
		"Analog output data table entry."
	INDEX	{ analogOutIndex }
	::= { analogOutTable 1 }

AnalogOutEntry ::= SEQUENCE {
	analogOutIndex			INTEGER,
	analogOutData			INTEGER
	}

analogOutIndex OBJECT-TYPE
	SYNTAX	INTEGER 
	MAX-ACCESS	not-accessible
	STATUS	current
	DESCRIPTION
		"Index into analog output data table."
	::= { analogOutEntry 1 }

analogOutData OBJECT-TYPE
	SYNTAX	INTEGER 
	MAX-ACCESS	read-write
	STATUS	current
	DESCRIPTION
		"Scaled level of analog output."
	::= { analogOutEntry 2 }


-- ******************************************************
--
-- SIMPLE I/O FOR SNMP NOTIFICATIONS
-- 
-- ******************************************************

sioTrapPrefix	OBJECT IDENTIFIER ::= { snmpio7050 2 }
sioTraps		OBJECT IDENTIFIER ::= { sioTrapPrefix 0 }

sioStateChange	NOTIFICATION-TYPE
	OBJECTS {
		discInData
	}
	STATUS	 	current
	DESCRIPTION
		"This trap is sent when a discrete input changes state
		if notifications are enabled for the object that changed."
	::= { sioTraps 1 }

sioLevelChange	NOTIFICATION-TYPE
	OBJECTS {
		analogInData, analogInStatus
	}
	STATUS		current
	DESCRIPTION
		"This trap is sent when an analog input exceeds a
		set limit and notifications are enabled for that object."
	::= { sioTraps 2 }


-- ******************************************************
--
-- SIMPLE I/O FOR SNMP COMPLIANCE
-- 
-- ******************************************************

sioConformance	OBJECT IDENTIFIER ::= { snmpio7050 3 }

sioGroups		OBJECT IDENTIFIER ::= { sioConformance 1 }
sioCompliances  OBJECT IDENTIFIER ::= { sioConformance 2 }

sioCompliance MODULE-COMPLIANCE
	STATUS 	current
	DESCRIPTION
		"The compliance statement for SNMPv2 entities which
		implement BAS-7050 based Simple I/O for SNMP."
	MODULE
	MANDATORY-GROUPS
		{ sioDiscOutGroup, sioDiscInGroup, sioAnalogInGroup, 
		  sioAnalogOutGroup, sioNotificationGroup }
	::= { sioCompliances 1 }

sioDiscOutGroup	OBJECT-GROUP
	OBJECTS {
		discOutData
	}
	STATUS 	current
	DESCRIPTION
		"Group of objects that define discrete outputs."
	::= { sioGroups 1 }

sioDiscIn	OBJECT-GROUP
	OBJECTS { 	   
		discInData,
		discInActiveEnable,
		discInActiveDelay,
		discInInactiveEnable,
		discInInactiveDelay,
		discInTrapRepeat
	}
	STATUS	current
	DESCRIPTION
		"Group of objects that define discrete inputs."
	::= { sioGroups 2 }

sioAnalogInGroup	OBJECT-GROUP
	OBJECTS {
		analogInData,
		analogInStatus,
		analogInHiLimEnable,
		analogInHiLimit,
		analogInHiHyst,
		analogInLoLimEnable,
		analogInLoLimit,
		analogInLoHyst,
		analogInTrapRepeat,
	}
	STATUS current
	DESCRIPTION
		"Group of objects that define analog inputs."
	::= { sioGroups 3 }

sioAnalogOutGroup	OBJECT-GROUP
	OBJECTS { 
		analogOutData
	}
	STATUS current
	DESCRIPTION
		"Group of objects that define analog outputs."
	::= { sioGroups 4 }

sioNotificationGroup	OBJECT-GROUP
	OBJECTS { 
		sioStateChange, 
		sioLevelChange 
	}
	STATUS current
	DESCRIPTION
		"Group of objects that define analog outputs."
	::= { sioGroups 4 }

END
